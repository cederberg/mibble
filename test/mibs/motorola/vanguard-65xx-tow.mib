-- Version 1.4, modified 02/12/98

        TOW-OPT-MIB DEFINITIONS ::= BEGIN

        IMPORTS
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

        -- Textual Conventions

        DisplayString ::= OCTET STRING

        -- The TOW Configuration Table
        -- This table contains the Configuration parameters
        -- for Time Of Week.

        cdx6500TOWCfgTable OBJECT-TYPE
            SYNTAX SEQUENCE OF Cdx6500TOWCfgEntry
            ACCESS not-accessible
            STATUS mandatory
            DESCRIPTION
                "This table contains the configuration parameters for TOW."
        ::= { cdx6500CfgGeneralGroup 22 }

        cdx6500TOWCfgEntry OBJECT-TYPE
            SYNTAX Cdx6500TOWCfgEntry
            ACCESS not-accessible
            STATUS mandatory
            DESCRIPTION
                "Configuration parameters for each TOW entry."
            INDEX { cdx6500TowCfgEntryNum }
        ::= { cdx6500TOWCfgTable 1 }

        Cdx6500TOWCfgEntry ::=
            SEQUENCE {
                cdx6500TowCfgEntryNum
                    INTEGER,
                cdx6500TowCfgEntryName
                    DisplayString,
                cdx6500TowCfgInt1StartTime
                    DisplayString,
                cdx6500TowCfgInt1Duration
                    DisplayString,
                cdx6500TowCfgInt1StartDays
                    DisplayString,
                cdx6500TowCfgInt2StartTime
                    DisplayString,
                cdx6500TowCfgInt2Duration
                    DisplayString,
                cdx6500TowCfgInt2StartDays
                    DisplayString,
                cdx6500TowCfgInt3StartTime
                    DisplayString,
                cdx6500TowCfgInt3Duration
                    DisplayString,
                cdx6500TowCfgInt3StartDays
                    DisplayString,
                cdx6500TowCfgInt4StartTime
                    DisplayString,
                cdx6500TowCfgInt4Duration
                    DisplayString,
                cdx6500TowCfgInt4StartDays
                    DisplayString,
                cdx6500TowCfgInt5StartTime
                    DisplayString,
                cdx6500TowCfgInt5Duration
                    DisplayString,
                cdx6500TowCfgInt5StartDays
                    DisplayString,
                cdx6500TowCfgInt6StartTime
                    DisplayString,
                cdx6500TowCfgInt6Duration
                    DisplayString,
                cdx6500TowCfgInt6StartDays
                    DisplayString,
                cdx6500TowCfgInt7StartTime
                    DisplayString,
                cdx6500TowCfgInt7Duration
                    DisplayString,
                cdx6500TowCfgInt7StartDays
                    DisplayString,
                cdx6500TowCfgInt8StartTime
                    DisplayString,
                cdx6500TowCfgInt8Duration
                    DisplayString,
                cdx6500TowCfgInt8StartDays
                    DisplayString,
                cdx6500TowCfgInt9StartTime
                    DisplayString,
                cdx6500TowCfgInt9Duration
                    DisplayString,
                cdx6500TowCfgInt9StartDays
                    DisplayString,
                cdx6500TowCfgInt10StartTime
                    DisplayString,
                cdx6500TowCfgInt10Duration
                    DisplayString,
                cdx6500TowCfgInt10StartDays
                    DisplayString
                 }

        cdx6500TowCfgEntryNum OBJECT-TYPE
            SYNTAX INTEGER (1..10)
            ACCESS read-only
            STATUS mandatory
            DESCRIPTION
                "Entry number used to reference this table record."
        ::= { cdx6500TOWCfgEntry 1 }

        cdx6500TowCfgEntryName OBJECT-TYPE
            SYNTAX DisplayString (SIZE(0..20))
            ACCESS read-only
            STATUS mandatory
            DESCRIPTION
                "Range   = 0-20 alphanumeric characters, use the space
                 character to blank field."
        ::= { cdx6500TOWCfgEntry 2 }

        cdx6500TowCfgInt1StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 3 }

        cdx6500TowCfgInt1Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 4 }

        cdx6500TowCfgInt1StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 5 }

        cdx6500TowCfgInt2StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 6 }

        cdx6500TowCfgInt2Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 7 }

        cdx6500TowCfgInt2StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 8 }

        cdx6500TowCfgInt3StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 9 }

        cdx6500TowCfgInt3Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 10 }

        cdx6500TowCfgInt3StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 11 }

        cdx6500TowCfgInt4StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 12 }

        cdx6500TowCfgInt4Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 13 }

        cdx6500TowCfgInt4StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 14 }

        cdx6500TowCfgInt5StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 15 }

        cdx6500TowCfgInt5Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 16 }

        cdx6500TowCfgInt5StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 17 }

        cdx6500TowCfgInt6StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 18 }

        cdx6500TowCfgInt6Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 19 }

        cdx6500TowCfgInt6StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 20 }

        cdx6500TowCfgInt7StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 21 }

        cdx6500TowCfgInt7Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 22 }

        cdx6500TowCfgInt7StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 23 }

        cdx6500TowCfgInt8StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 24 }

        cdx6500TowCfgInt8Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 25 }

        cdx6500TowCfgInt8StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 26 }

        cdx6500TowCfgInt9StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 27 }

        cdx6500TowCfgInt9Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 28 }

        cdx6500TowCfgInt9StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 29 }

        cdx6500TowCfgInt10StartTime OBJECT-TYPE
            SYNTAX DisplayString (SIZE(5))
            ACCESS read-only
            STATUS mandatory
            DESCRIPTION
                "This parameter specifies the start time of the interval.
                 Format      : hh:mm
                 hh          : Is the start hour  , with range 00 to 23.
                 mm          : Is the start minute, with range 00 to 59.
                 This parameter specifies the start time of the interval.
                 All the intervals configured in an entry do not overlap.
                 Intervals configured in different entries can overlap."
        ::= { cdx6500TOWCfgEntry 30 }

        cdx6500TowCfgInt10Duration OBJECT-TYPE
            SYNTAX DisplayString (SIZE(8))
            ACCESS read-only
            STATUS mandatory
            DESCRIPTION
                "Format      : dd:hh:mm
                 dd          : Days . Range 00 to 06.
                 hh          : Hours. Range 00 to 23.
                 mm          : minutes. Range 00 to 59.
                 This parameter specifies the duration of the interval
                 starting from the start time configured. To check if
                 the end time of the interval is as desired, check the
                 Time of Week intervals under the statistics menu."
        ::= { cdx6500TOWCfgEntry 31 }

        cdx6500TowCfgInt10StartDays OBJECT-TYPE
            SYNTAX DisplayString (SIZE(0..27))
            ACCESS read-only
            STATUS mandatory
            DESCRIPTION
                "DDD         : This specifies the day. Range is one of
                               MON TUE WED THU FRI SAT SUN.
                 DDD+DDD+DDD : This specifies that the interval has to
                               start on each of these days. The `+' 
                               operator implies AND.
                               A maximum of 7 days can be specified.
                               This parameter specifies the days on which
                               the interval has to be applied. That is,
                               the intervals would start on each of these
                               days."
        ::= { cdx6500TOWCfgEntry 32 }

        END
