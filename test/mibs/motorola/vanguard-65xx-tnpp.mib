-- Version 1.3, modified 02/12/98

        TNPP-OPT-MIB DEFINITIONS ::= BEGIN

        IMPORTS
            Counter
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Conventions

        DisplayString ::= OCTET STRING

        -- The TNPP Port Configuration Table
        -- This table contains Configuration parameters related to 
        -- a TNPP PAD port. 

        cdx6500PPCTTNPPPortTable OBJECT-TYPE
            SYNTAX SEQUENCE OF Cdx6500PPCTTNPPPortEntry    
            ACCESS not-accessible
            STATUS mandatory
            DESCRIPTION
                "This table contains the TNPP port configuration 
                 parameters." 
        ::= { cdx6500PCTPortProtocolGroup 32 }              
  
        cdx6500PPCTTNPPPortEntry OBJECT-TYPE 
            SYNTAX Cdx6500PPCTTNPPPortEntry 
            ACCESS not-accessible
            STATUS mandatory
            DESCRIPTION
                "Entries in the TNPP port configuration table."
            INDEX { tnppPCfgPortNumber }
        ::= { cdx6500PPCTTNPPPortTable 1 }

       
        Cdx6500PPCTTNPPPortEntry ::= 
            SEQUENCE {
                tnppPCfgPortNumber
                    INTEGER,
                tnppPCfgPortType
                    INTEGER,
                tnppPCfgPortSpeed
                    INTEGER,
                tnppPCfgCallControl
                    INTEGER,
                tnppPCfgCRCOption
                    INTEGER,
                tnppPCfgTANControl
                    INTEGER,
                tnppPCfgCANReports
                    INTEGER,
                tnppPCfgRSCount
                    INTEGER,
                tnppPCfgMaxRSCount
                    INTEGER,
                tnppPCfgRSSupport
                    INTEGER,
                tnppPCfgAutocallMnemonic
                    DisplayString,
                tnppPCfgAutocallTimeout
                    INTEGER,
                tnppPCfgMaxAutocallAttempt
                    INTEGER,
                tnppPCfgProtectionLevel
                    INTEGER,
                tnppPCfgReconnTimeout
                    INTEGER,
                tnppPCfgMaxReconnAttempt
                    INTEGER
                }

        tnppPCfgPortNumber OBJECT-TYPE
            SYNTAX INTEGER (1..54)
            ACCESS read-only
            STATUS mandatory
            DESCRIPTION
                "Port Number of the TNPP port."
        ::= { cdx6500PPCTTNPPPortEntry 1 }    

        tnppPCfgPortType OBJECT-TYPE
            SYNTAX INTEGER {
                    tnpp (37)
                    }
            ACCESS read-only
            STATUS mandatory
            DESCRIPTION
                "Specifies the type of access protocol for
                 this port."
        ::= { cdx6500PPCTTNPPPortEntry 2 }  

        tnppPCfgPortSpeed OBJECT-TYPE
            SYNTAX INTEGER {
                    speed300   (3),
                    speed1200  (4),
                    speed2400  (13),
                    speed4800  (14),
                    speed9600  (15),
                    speed19200 (16)
                    }
            ACCESS read-only
            STATUS mandatory
            DESCRIPTION
                "Specifies port speed in bits per second.
                 speed300   : 300  bits per second.
                 speed1200  : 1200 bits per second.
                 speed2400  : 2400 bits per second.
                 speed4800  : 4800 bits per second.
                 speed9600  : 9600 bits per second.
                 speed19200 : 19200 bits per second."
        ::= { cdx6500PPCTTNPPPortEntry 3 }
      
        tnppPCfgCallControl OBJECT-TYPE
            SYNTAX INTEGER { 
                    dtr     (2),
                    dataDrv (3),
                    powerOn (4),
                    nc      (100)
                    }
            ACCESS read-only
            STATUS mandatory
            DESCRIPTION
                "Specifies the mode for X.25 call generation.
                 dtr     - X.25 call is generated when DTR is up.
                           Connection type between TNPP PAD and
                           Paging Terminal is DTR.
                 dataDrv - X.25 call is generated on incoming data.
                           Connection type between TNPP PAD and 
                           Paging Terminal is SIMP.
                 powerOn - X.25 call is generated on Node Boot/Power On. 
                           Connection type between TNPP PAD and 
                           Paging Terminal is SIMP.
                 nc      - Skipped during configuration."
        ::= { cdx6500PPCTTNPPPortEntry 4 }

        tnppPCfgCRCOption OBJECT-TYPE
            SYNTAX INTEGER {
                    normal (1),
                    transp (2),
                    nc     (100)
                    }
            ACCESS read-only
            STATUS mandatory
            DESCRIPTION
                "Specifies the CRC option.
                 normal - 2 bytes binary CRC.
                 transp - 4 bytes ASCII CRC. 
                 nc     - Skipped during configuration."
        ::= { cdx6500PPCTTNPPPortEntry 5 }             


        tnppPCfgTANControl OBJECT-TYPE
            SYNTAX INTEGER {
                    mps2000Mode (1),
                    unipageMode (2),
                    nc          (100)
                    }
            ACCESS read-only
            STATUS mandatory
            DESCRIPTION
                "Specifies whether to accept control characters(ACK/NAK)
                 in the frame.
                 mps2000Mode  - Do not accept embedded control characters
                                in the frame.
                 unipageMode  - Accept embedded control characters 
                                in the frame.
                 nc           - Skipped during configuration."
        ::= { cdx6500PPCTTNPPPortEntry 6 } 
         
        tnppPCfgCANReports OBJECT-TYPE
            SYNTAX INTEGER {
                    no  (1),
                    yes (2),
                    nc  (100)
                    }
            ACCESS read-only
            STATUS mandatory
            DESCRIPTION
                "Specifies whether to log reports generated by TNPP PAD.
                 no     - Reports generated due to CANcel frame will not
                          be logged.
                 yes    - Reports generated due to CANcel frame will be
                          logged which will be controlled by node 
                          parameter. 
                 nc     - Skipped during configuration."
        ::= { cdx6500PPCTTNPPPortEntry 7 } 

        tnppPCfgRSCount OBJECT-TYPE
            SYNTAX INTEGER (1..10)
            ACCESS read-only
            STATUS mandatory
            DESCRIPTION
                "TNPP PAD port will flow control the X.25 channel when 
                 the number of RSed frames on hold remains at or above
                 the configured value of this parameter.
                 Specifies the limit for RS support by TNPP PAD."
        ::= { cdx6500PPCTTNPPPortEntry 8 }   

        tnppPCfgMaxRSCount OBJECT-TYPE
            SYNTAX INTEGER (1..10)
            ACCESS read-only
            STATUS mandatory
            DESCRIPTION
                "TNPP PAD port will stop transmission of any new frame
                 to the paging terminal if the number of frames on hold 
                 remains above the value of this parameter. Transmission
                 of control frames and retransmission of RS timed out 
                 frames will continue. 
                 Specifies the maximum number of RS that can be received
                 before the TNPP PAD stops transmission." 
        ::= { cdx6500PPCTTNPPPortEntry 9 }

        tnppPCfgRSSupport OBJECT-TYPE 
            SYNTAX INTEGER {
                    no  (1),
                    yes (2),
                    nc  (100)
                    }
            ACCESS read-only
            STATUS mandatory
            DESCRIPTION
                "Specifies whether to respond with RS to local paging 
                 terminal in case of X25 link being blocked.
                 no  - RS is not transmitted.
                 yes - RS is transmitted. 
                 nc  - Skipped during configuration."
        ::= { cdx6500PPCTTNPPPortEntry 10 } 
     
        tnppPCfgAutocallMnemonic OBJECT-TYPE
            SYNTAX DisplayString (SIZE(0..8)) 
            ACCESS read-only
            STATUS mandatory
            DESCRIPTION
                "This parameter refers to the remote address which
                 will be called by the TNPP PAD port.
                 Specifies the Mnemonic Address for Autocall."
        ::= { cdx6500PPCTTNPPPortEntry 11 }

        tnppPCfgAutocallTimeout OBJECT-TYPE
            SYNTAX INTEGER (5..255)
            ACCESS read-only
            STATUS mandatory
            DESCRIPTION
                "This parameter is the time interval in seconds 
                 between call attempts when auto calling. 
                 Specifies the time value for retrying AUTOCALL
                 in seconds."
        ::= { cdx6500PPCTTNPPPortEntry 12 }

        tnppPCfgMaxAutocallAttempt OBJECT-TYPE
            SYNTAX INTEGER  (0..20)
            ACCESS read-only
            STATUS mandatory
            DESCRIPTION
                "Specifies the number of Autocall attempts.
                 0 - No Autocall retry limit."
        ::= { cdx6500PPCTTNPPPortEntry 13 }

     
        tnppPCfgProtectionLevel OBJECT-TYPE
            SYNTAX INTEGER {
                    none    (1),
                    cpOnly  (2),
                    fullDcp (3),
                    nc      (100)
                    }
            ACCESS read-only
            STATUS mandatory
            DESCRIPTION
                "This specifies the level of data or connection 
                 protection which will be applied to calls to or
                 from this port. The actual level for a call will
                 be negotiated to the lesser of this level and the
                 level configured for the other end of the call.
                 none     - No protection.
                 cpOnly   - Connection protection only.
                 fullDcp  - Full data and connection protection.
                 nc       - Skipped during configuration."
        ::= { cdx6500PPCTTNPPPortEntry 14 }
       
        tnppPCfgReconnTimeout OBJECT-TYPE
            SYNTAX INTEGER (1..128) 
            ACCESS read-only
            STATUS mandatory
            DESCRIPTION 
                "This specifies the number of seconds that DCP on the
                 originating side will wait between reconnection 
                 attempts."
        ::= { cdx6500PPCTTNPPPortEntry 15 }

        tnppPCfgMaxReconnAttempt OBJECT-TYPE
            SYNTAX INTEGER (0..127)  
            ACCESS read-only
            STATUS mandatory
            DESCRIPTION
                "This specifies the number of times that DCP on the 
                 orginating side will attempt to reconnect before 
                 clearing the call. If the value is zero no attempt 
                 to reconnect will be made."
        ::= { cdx6500PPCTTNPPPortEntry 16 }

        -- TNPP Port Statistics
   
        cdx6500PPSTTNPPPStatTable OBJECT IDENTIFIER ::=
            { cdx6500PSTPortProtocolGroup 33 }

        tnppPGenStatTable OBJECT-TYPE
            SYNTAX SEQUENCE OF TNPPPGenStatEntry
            ACCESS not-accessible
            STATUS mandatory
            DESCRIPTION
                "This table contains the  port statistics
                 general parameters."
        ::= { cdx6500PPSTTNPPPStatTable 1 }
             
        tnppPGenStatEntry OBJECT-TYPE
            SYNTAX TNPPPGenStatEntry
            ACCESS not-accessible
            STATUS mandatory
            DESCRIPTION
                "Entries in the TNPP port statistics  
                 general parameters table."
            INDEX  { tnppPGStatPortNumber }
        ::= { tnppPGenStatTable 1 }

        TNPPPGenStatEntry ::= 
            SEQUENCE {
                tnppPGStatPortNumber
                    INTEGER,
                tnppPGStatPortType
                    INTEGER,
                tnppPGStatPortStatus
                    INTEGER,
                tnppPGStatPortSpeed
                    INTEGER,
                tnppPGStatPortUtilIn
                    INTEGER,
                tnppPGStatPortUtilOut
                    INTEGER,
                tnppPGStatParityErrors
                    Counter,
                tnppPGStatOverrunErrors
                    Counter,
                tnppPGStatFramingErrors
                    Counter,
                tnppPGStatLocalDTEState
                    INTEGER,
                tnppPGStatRemoteDTEState
                    INTEGER,
                tnppPGStatRemotePadQ
                    INTEGER,
                tnppPGStatLocalTerminalQ
                    INTEGER,
                tnppPGStatReadyQ
                    INTEGER,
                tnppPGStatHoldQ
                    INTEGER
                }

        tnppPGStatPortNumber OBJECT-TYPE
            SYNTAX INTEGER (1..54)
            ACCESS read-only
            STATUS mandatory
            DESCRIPTION
                "Port Number of the TNPP port."
        ::= { tnppPGenStatEntry 1 }
    
        tnppPGStatPortType OBJECT-TYPE
            SYNTAX INTEGER {
                    tnpp (36)
                    }
            ACCESS read-only
            STATUS mandatory
            DESCRIPTION
                "This indicates the type of access protocol 
                 for this port."
        ::= { tnppPGenStatEntry 2 }
    
        tnppPGStatPortStatus OBJECT-TYPE
            SYNTAX INTEGER {
                   disabled (1),
                   up       (2),
                   na       (100)
                   }
            ACCESS read-only
            STATUS mandatory
            DESCRIPTION
                "This indicates the operational status of the port.
                 disabled : port is disabled.
                 up       : port is up.
                 na       : Value not available."
        ::= { tnppPGenStatEntry 3 } 

    
        tnppPGStatPortSpeed OBJECT-TYPE
            SYNTAX INTEGER 
            ACCESS read-only
            STATUS mandatory
            DESCRIPTION
                "This indicates the port speed in bits per second."
        ::= { tnppPGenStatEntry 4 } 

        tnppPGStatPortUtilIn OBJECT-TYPE
            SYNTAX INTEGER
            ACCESS read-only
            STATUS mandatory
            DESCRIPTION
                "This indicates the port utilization for the line to 
                 port direction."
        ::= { tnppPGenStatEntry 5 }
     
        tnppPGStatPortUtilOut OBJECT-TYPE
            SYNTAX INTEGER
            ACCESS read-only
            STATUS mandatory
            DESCRIPTION
                "This indicates the port utilization for the port to
                 line direction."
        ::= { tnppPGenStatEntry 6 } 

        tnppPGStatParityErrors OBJECT-TYPE
            SYNTAX Counter
            ACCESS read-only
            STATUS mandatory
            DESCRIPTION
                "This indicates the number of parity errors counted
                 by the I/O driver."
        ::= { tnppPGenStatEntry 7 }

        tnppPGStatOverrunErrors OBJECT-TYPE
            SYNTAX Counter
            ACCESS read-only
            STATUS mandatory
            DESCRIPTION
                "This indicates  number of overrun errors 
                 detected by the I/O driver."
        ::= { tnppPGenStatEntry 8 } 

        tnppPGStatFramingErrors OBJECT-TYPE
            SYNTAX Counter
            ACCESS read-only
            STATUS mandatory
            DESCRIPTION
                "This indicates number of framing errors
                 detected by the I/O driver." 
        ::= { tnppPGenStatEntry 9 }

        tnppPGStatLocalDTEState OBJECT-TYPE
            SYNTAX INTEGER {
                    down   (1),
                    active (2),
                    na     (100)
                    }
            ACCESS read-only 
            STATUS mandatory
            DESCRIPTION
                "This indicates the local DTE state.
                 active  -  DTE is active.
                 down    -  DTE is down.
                 na      -  Value not available."
        ::= { tnppPGenStatEntry 10 }

        tnppPGStatRemoteDTEState OBJECT-TYPE
            SYNTAX INTEGER {
                    down   (1),
                    active (2),
                    na     (100)
                    }
            ACCESS read-only
            STATUS mandatory
            DESCRIPTION
                "This indicates the remote DTE state. 
                 active  -  DTE is active.
                 down    -  DTE is down.
                 na      -  Value not available."
        ::= { tnppPGenStatEntry 11 }
                   
        tnppPGStatRemotePadQ OBJECT-TYPE
            SYNTAX INTEGER
            ACCESS read-only
            STATUS mandatory
            DESCRIPTION 
                "This indicates the size of the remote
                 TNPP PAD queue."
        ::= { tnppPGenStatEntry 12 }

        tnppPGStatLocalTerminalQ OBJECT-TYPE
            SYNTAX INTEGER
            ACCESS read-only
            STATUS mandatory
            DESCRIPTION 
                "This indicates the size of the Local Terminal queue."
        ::= { tnppPGenStatEntry 13 }

        tnppPGStatReadyQ OBJECT-TYPE
            SYNTAX INTEGER
            ACCESS read-only
            STATUS mandatory
            DESCRIPTION
                "This indicates the size of the Ready Queue."
        ::= { tnppPGenStatEntry 14 } 

        tnppPGStatHoldQ OBJECT-TYPE
            SYNTAX INTEGER
            ACCESS read-only
            STATUS mandatory
            DESCRIPTION
                "This indicates the size of the Hold Queue."
        ::= { tnppPGenStatEntry 15 }    


        tnppPDataSummaryStatTable OBJECT-TYPE
            SYNTAX SEQUENCE OF TNPPPDataSummaryStatEntry
            ACCESS not-accessible
            STATUS mandatory
            DESCRIPTION
                "This table contains the TNPP port statistics
                 data summary parameters."
        ::= { cdx6500PPSTTNPPPStatTable 2 } 

        tnppPDataSummaryStatEntry OBJECT-TYPE
            SYNTAX TNPPPDataSummaryStatEntry
            ACCESS not-accessible
            STATUS mandatory
            DESCRIPTION
                "Entries in the TNPP port statistics data summary table."
            INDEX  { tnppPDSStatPortNumber }
        ::= { tnppPDataSummaryStatTable 1 }


        TNPPPDataSummaryStatEntry  ::=
            SEQUENCE {
                tnppPDSStatPortNumber
                    INTEGER,
                tnppPDSStatTotalCharIn
                    Counter,
                tnppPDSStatTotalCharOut
                    Counter,
                tnppPDSStatTotalFramesIn
                    Counter,
                tnppPDSStatTotalFramesOut
                    Counter,
                tnppPDSStatCharInPerSec
                    INTEGER,
                tnppPDSStatCharOutPerSec
                    INTEGER,
                tnppPDSStatFramesInPerSec
                    INTEGER,
                tnppPDSStatFramesOutPerSec
                    INTEGER 
                } 

        tnppPDSStatPortNumber OBJECT-TYPE
            SYNTAX INTEGER (1..54)
            ACCESS read-only
            STATUS mandatory
            DESCRIPTION
                "Port Number of the TNPP port."
        ::= { tnppPDataSummaryStatEntry 1 }

        tnppPDSStatTotalCharIn OBJECT-TYPE
            SYNTAX Counter
            ACCESS read-only
            STATUS mandatory
            DESCRIPTION
                "This indicates the total number of characters
                 that have been received by the port."
        ::= { tnppPDataSummaryStatEntry 2 }

        tnppPDSStatTotalCharOut OBJECT-TYPE
            SYNTAX Counter
            ACCESS read-only
            STATUS mandatory
            DESCRIPTION
                "This indicates the total number of characters
                 that have been transmitted by the port."
        ::= { tnppPDataSummaryStatEntry 3 }

        tnppPDSStatTotalFramesIn OBJECT-TYPE
            SYNTAX Counter
            ACCESS read-only
            STATUS mandatory
            DESCRIPTION
                "This indicates the total number of frames that
                 have been received by the port."
        ::= { tnppPDataSummaryStatEntry 4 }

        tnppPDSStatTotalFramesOut OBJECT-TYPE
            SYNTAX Counter
            ACCESS read-only
            STATUS mandatory
            DESCRIPTION
                "This indicates the total  number of frames
                 that have been transmitted by the port."
        ::= { tnppPDataSummaryStatEntry 5 }

        tnppPDSStatCharInPerSec OBJECT-TYPE
            SYNTAX INTEGER
            ACCESS read-only
            STATUS mandatory
            DESCRIPTION
                "This indicates the rate at which characters
                 have been received by the port per second."
        ::= { tnppPDataSummaryStatEntry 6 }

        tnppPDSStatCharOutPerSec OBJECT-TYPE
            SYNTAX INTEGER 
            ACCESS read-only
            STATUS mandatory
            DESCRIPTION
                "This indicates the rate at which characters
                 have been transmitted by the port per second."
        ::= { tnppPDataSummaryStatEntry 7 }

        tnppPDSStatFramesInPerSec OBJECT-TYPE
            SYNTAX INTEGER
            ACCESS read-only
            STATUS mandatory
            DESCRIPTION
                "This indicates the rate at which frames have 
                 been received by the port per second."
        ::= { tnppPDataSummaryStatEntry 8 }

        tnppPDSStatFramesOutPerSec OBJECT-TYPE
            SYNTAX INTEGER
            ACCESS read-only
            STATUS mandatory
            DESCRIPTION
                "This indicates the rate at which frames have 
                 been transmitted by the port per second."
        ::= { tnppPDataSummaryStatEntry 9 } 


        tnppPFrameSummaryStatTable OBJECT-TYPE
            SYNTAX SEQUENCE OF TNPPPFrameSummaryStatEntry
            ACCESS not-accessible
            STATUS mandatory
            DESCRIPTION
                "This table contains the TNPP port statistics 
                 frame summary parameters."
        ::= { cdx6500PPSTTNPPPStatTable 3 }
             
        tnppPFrameSummaryStatEntry OBJECT-TYPE
            SYNTAX TNPPPFrameSummaryStatEntry
            ACCESS not-accessible
            STATUS mandatory
            DESCRIPTION
                "Entries in the TNPP port statistics frame summary table."
            INDEX { tnppPFSStatPortNumber }
        ::= { tnppPFrameSummaryStatTable  1 }


        TNPPPFrameSummaryStatEntry  ::=
            SEQUENCE {
                tnppPFSStatPortNumber
                    INTEGER,
                tnppPFSStatLinkState
                    INTEGER,
                tnppPFSStatCRCErrors
                    Counter,
                tnppPFSStatLinkFramingErrors
                    Counter,
                tnppPFSStatProtocolErrors
                    Counter,
                tnppPFSStatACKFramesIn
                    Counter,
                tnppPFSStatACKFramesOut
                    Counter,
                tnppPFSStatNAKFramesIn
                    Counter,
                tnppPFSStatNAKFramesOut
                    Counter,
                tnppPFSStatRSFramesIn
                    Counter,
                tnppPFSStatRSFramesOut
                    Counter,
                tnppPFSStatCANFramesIn
                    Counter,
                tnppPFSStatCANFramesOut
                    Counter,
                tnppPFSStatEOTFramesIn
                    Counter,
                tnppPFSStatEOTFramesOut
                    Counter,
                tnppPFSStatENQFramesIn
                    Counter,
                tnppPFSStatENQFramesOut
                    Counter,
                tnppPFSStatDataFramesInPassed
                    Counter,
                tnppPFSStatDataFramesOutPassed
                    Counter,
                tnppPFSStatDataFramesInDiscarded
                    Counter,
                tnppPFSStatDataFramesOutDiscarded
                    Counter
                }

        tnppPFSStatPortNumber OBJECT-TYPE
            SYNTAX INTEGER (1..54)
            ACCESS read-only
            STATUS mandatory
            DESCRIPTION
                "Port number of the TNPP port."
        ::= {  tnppPFrameSummaryStatEntry 1 }

        tnppPFSStatLinkState OBJECT-TYPE 
            SYNTAX INTEGER {
                   init            (1),
                   awaitEnqResp    (2),
                   ready           (3),
                   transmitting    (4),
                   trnsmitResponse (5),
                   na              (100)
                   }
            ACCESS read-only
            STATUS mandatory
            DESCRIPTION
                "This indicates the current link state.
                 init               -   Initialization state.
                 awaitEnqResp       -   Await enquiry response state.
                 ready              -   Ready to communicate state.
                 transmitting       -   Transmitting state.
                 transmitResponse   -   Transmit response state.
                 na                 -   Value not available."
        ::= {  tnppPFrameSummaryStatEntry 2 }

        tnppPFSStatCRCErrors OBJECT-TYPE  
            SYNTAX Counter
            ACCESS read-only
            STATUS mandatory
            DESCRIPTION
                "This indicates the total number of TNPP frames 
                 received with Cyclic Redundancy Check errors ."
        ::= {  tnppPFrameSummaryStatEntry 3 }

        tnppPFSStatLinkFramingErrors OBJECT-TYPE
            SYNTAX Counter
            ACCESS read-only
            STATUS mandatory
            DESCRIPTION
                "This indicates the total number of TNPP framing 
                 errors occured (Invalid Header, Invalid Control 
                 character, Frame Size Exceeded, Incomplete Frame, 
                 etc.,) ."
        ::= {  tnppPFrameSummaryStatEntry 4 } 

        tnppPFSStatProtocolErrors OBJECT-TYPE
            SYNTAX Counter
            ACCESS read-only
            STATUS mandatory
            DESCRIPTION
                "This indicates the number of protocol errors
                 due to unexpected events."
        ::= {  tnppPFrameSummaryStatEntry 5 } 

        tnppPFSStatACKFramesIn OBJECT-TYPE
            SYNTAX Counter
            ACCESS read-only
            STATUS mandatory
            DESCRIPTION
                "This indicates the total number of Acknowledgment 
                 frames received by the port."
        ::= { tnppPFrameSummaryStatEntry 6 } 

        tnppPFSStatACKFramesOut OBJECT-TYPE
            SYNTAX Counter
            ACCESS read-only
            STATUS mandatory
            DESCRIPTION
                "This indicates the total number of Acknowledgment
                 frames transmitted by the port."
        ::= { tnppPFrameSummaryStatEntry 7 }

        tnppPFSStatNAKFramesIn OBJECT-TYPE
            SYNTAX Counter
            ACCESS read-only
            STATUS mandatory
            DESCRIPTION
                "This indicates the total number of Negative 
                 Acknowledgment frames received by the port."
        ::= { tnppPFrameSummaryStatEntry 8 } 

        tnppPFSStatNAKFramesOut OBJECT-TYPE
            SYNTAX Counter
            ACCESS read-only
            STATUS mandatory
            DESCRIPTION
                "This indicates the total number of Negative 
                 Acknowledgment frames transmitted by the port." 
        ::= { tnppPFrameSummaryStatEntry 9 }

        tnppPFSStatRSFramesIn OBJECT-TYPE
            SYNTAX Counter
            ACCESS read-only
            STATUS mandatory
            DESCRIPTION
                "This indicates the total number of Request to Stop
                 frames received by the port."
        ::= { tnppPFrameSummaryStatEntry 10 } 

        tnppPFSStatRSFramesOut OBJECT-TYPE
            SYNTAX Counter
            ACCESS read-only
            STATUS mandatory
            DESCRIPTION
                "This indicates the total number of Request to Stop
                 frames transmitted by the port."
        ::= { tnppPFrameSummaryStatEntry 11 } 

        tnppPFSStatCANFramesIn OBJECT-TYPE
            SYNTAX Counter
            ACCESS read-only
            STATUS mandatory
            DESCRIPTION
                "This indicates the total number of CANcel report 
                 frames received by the port."
        ::= { tnppPFrameSummaryStatEntry 12 } 

        tnppPFSStatCANFramesOut OBJECT-TYPE
            SYNTAX Counter
            ACCESS read-only
            STATUS mandatory
            DESCRIPTION
                "This indicates the total number of CANcel report
                 frames transmitted by the port."
        ::= { tnppPFrameSummaryStatEntry 13 }

        tnppPFSStatEOTFramesIn OBJECT-TYPE
            SYNTAX Counter
            ACCESS read-only
            STATUS mandatory
            DESCRIPTION
                "This indicates the total number of End of Transmission 
                 frames received by the port."
        ::= { tnppPFrameSummaryStatEntry 14 } 

        tnppPFSStatEOTFramesOut OBJECT-TYPE
            SYNTAX Counter 
            ACCESS read-only
            STATUS mandatory
            DESCRIPTION
                "This indicates the total number of End of Transmission  
                 frames transmitted by the port." 
        ::= { tnppPFrameSummaryStatEntry 15 }

        tnppPFSStatENQFramesIn OBJECT-TYPE
            SYNTAX Counter
            ACCESS read-only
            STATUS mandatory
            DESCRIPTION
                "This indicates the total number of  Enquiry 
                 frames received by the port."
        ::= { tnppPFrameSummaryStatEntry 16 } 

        tnppPFSStatENQFramesOut OBJECT-TYPE
            SYNTAX Counter
            ACCESS read-only
            STATUS mandatory
            DESCRIPTION
                "This indicates the total number of  Enquiry
                 frames transmitted by the port." 
        ::= { tnppPFrameSummaryStatEntry 17 }

        tnppPFSStatDataFramesInPassed OBJECT-TYPE
            SYNTAX Counter
            ACCESS read-only
            STATUS mandatory
            DESCRIPTION
                "This indicates the total number of valid
                 data frames received by the port."
        ::= { tnppPFrameSummaryStatEntry 18 } 

        tnppPFSStatDataFramesOutPassed OBJECT-TYPE
            SYNTAX Counter
            ACCESS read-only
            STATUS mandatory
            DESCRIPTION
                "This indicates the total number of valid
                 data frames transmitted by the port."
        ::= { tnppPFrameSummaryStatEntry 19 } 

        tnppPFSStatDataFramesInDiscarded OBJECT-TYPE
            SYNTAX Counter
            ACCESS read-only
            STATUS mandatory
            DESCRIPTION
                "This indicates the total number of data frames
                 received by the  port and discarded."
        ::= { tnppPFrameSummaryStatEntry 20 }
        
        tnppPFSStatDataFramesOutDiscarded OBJECT-TYPE
            SYNTAX Counter
            ACCESS read-only
            STATUS mandatory
            DESCRIPTION
                "This indicates the total number of data frames
                 transmitted by the port and discarded."
        ::= { tnppPFrameSummaryStatEntry 21 }

        -- TNPP Control Objects

        cdx6500ContTNPPTable OBJECT IDENTIFIER ::=     
            { cdx6500Controls 15 }  

        -- The TNPP Port Control Table 
        -- This table contains the port control parameters
        -- specified for TNPP

        cdx6500ContTNPPPortTable OBJECT-TYPE
            SYNTAX SEQUENCE OF Cdx6500ContTNPPPortEntry
            ACCESS not-accessible
            STATUS mandatory
            DESCRIPTION
                "This table contains the TNPP Port Control parameters."
        ::= { cdx6500ContTNPPTable 1 }

        cdx6500ContTNPPPortEntry OBJECT-TYPE
            SYNTAX Cdx6500ContTNPPPortEntry
            ACCESS not-accessible
            STATUS mandatory
            DESCRIPTION
                "Entries in the TNPP Port Control Table."
            INDEX  { tnppPContPortNumber }
        ::= { cdx6500ContTNPPPortTable 1 }

        Cdx6500ContTNPPPortEntry ::=
            SEQUENCE {
                tnppPContPortNumber
                    INTEGER,
                tnppPContPortControl
                    INTEGER
            }

        tnppPContPortNumber OBJECT-TYPE
            SYNTAX INTEGER (1..54)
            ACCESS not-accessible
            STATUS mandatory
            DESCRIPTION
                "Port number of the TNPP port."
        ::= { cdx6500ContTNPPPortEntry 1 }

        tnppPContPortControl OBJECT-TYPE
            SYNTAX INTEGER {
                   boot       (1),
                   enable     (2),
                   disable    (3),
                   busyout    (4),
                   resetstats (5)
                   }
            ACCESS write-only
            STATUS mandatory
            DESCRIPTION
                "Control operations for the specified TNPP port.
                 boot       - Boots the TNPP Port.
                 enable     - Enables the TNPP Port.
                 disable    - Disables the TNPP Port.
                 busyout    - Busyout the  TNPP Port.
                 resetstats - Resets the TNPP port statistics."
        ::= { cdx6500ContTNPPPortEntry 2 }

        END
