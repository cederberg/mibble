-- Version 1.3,  modified  02/12/98

        WAN-OPT-MIB DEFINITIONS ::= BEGIN

        IMPORTS
            IpAddress, Counter
                FROM RFC1155-SMI

            OBJECT-TYPE
                FROM RFC-1212;

        -- Codex MIB Group definitions

                       codex OBJECT IDENTIFIER ::= { enterprises 449 }
          cdxProductSpecific OBJECT IDENTIFIER ::= { codex 2 }
                     cdx6500 OBJECT IDENTIFIER ::= { cdxProductSpecific 1 }

       cdx6500Configuration  OBJECT IDENTIFIER ::= { cdx6500 2 }
      cdx6500CfgGeneralGroup OBJECT IDENTIFIER ::= { cdx6500Configuration 2 }

           cdx6500Statistics OBJECT IDENTIFIER ::= { cdx6500 3 }
    cdx6500StatProtocolGroup OBJECT IDENTIFIER ::= { cdx6500Statistics 1 }
cdx6500PSTLANConnectionGroup OBJECT IDENTIFIER ::= { cdx6500StatProtocolGroup 6 }

             cdx6500Controls OBJECT IDENTIFIER ::= { cdx6500 4 }
       cdx6500ContWANAdaptor OBJECT IDENTIFIER ::= { cdx6500Controls 1 }

        -- Textual conventions

        Counter8  ::= INTEGER (0..255)

        Counter16 ::= INTEGER (0..65535)

        DisplayString ::= OCTET STRING

        -- The Wan Adaptor group

        -- The Wan Adaptor configuration table for LAN Connections.
      
        cdx6500GCTLANConnectionTable OBJECT-TYPE
            SYNTAX SEQUENCE OF Cdx6500GCTLANConnectionEntry
            ACCESS not-accessible
            STATUS mandatory
            DESCRIPTION
                "A list of parameters for configuring LAN Connections."
        ::= { cdx6500CfgGeneralGroup 16 }

        cdx6500GCTLANConnectionEntry OBJECT-TYPE
            SYNTAX Cdx6500GCTLANConnectionEntry
            ACCESS not-accessible
            STATUS mandatory
            DESCRIPTION
                "Each entry contains the Configuration parameters 
                 for each LAN Connection."
            INDEX { cdx6500WAEntryNumber }
        ::= { cdx6500GCTLANConnectionTable 1 }

        Cdx6500GCTLANConnectionEntry ::=
            SEQUENCE {
                cdx6500WAEntryNumber
                    INTEGER,
                cdx6500WALanForwarderType
                    INTEGER,
                cdx6500WABridgeLinkNumber
                    INTEGER,
                cdx6500WARouterInterfaceNum
                    INTEGER,
                cdx6500WACfgEncapsulationType
                    INTEGER,
                cdx6500WAAutocallMnemonic
                    DisplayString,
                cdx6500WAAutocallTimeout
                    INTEGER,
                cdx6500WAMaxAutocallAttempts
                    INTEGER,
                cdx6500WARemoteConnectionId
                    INTEGER,
                cdx6500WABillingRecords
                    INTEGER,
                cdx6500WADataPassingPriority
                    INTEGER,
                cdx6500WALCONQueueLimit
                    INTEGER,
                cdx6500WACfgEncapType
                    INTEGER,
                cdx6500WACfgOnDemand
                    INTEGER, 
                cdx6500WACfgIdleTimeout
                    INTEGER,
                cdx6500WACfgLanConnectionType
                    INTEGER,
                cdx6500WACfgNexthopIpAddress
                    IpAddress,
                cdx6500WACfgNexthopIpxNodeNumber
                    INTEGER,
                cdx6500WACfgParallelSvc
                    INTEGER,
                cdx6500WACfgParallelThreshold
                    INTEGER,
                cdx6500WACfgParallelPort
                    DisplayString,     
                cdx6500WACfgBroadcast
                    INTEGER
                }               

        cdx6500WAEntryNumber OBJECT-TYPE
            SYNTAX INTEGER (1..32)
            ACCESS read-only
            STATUS mandatory
            DESCRIPTION
                "This is a standard table entry number. 
                 It identifies a specific LAN Connection Record
                 within the table."
        ::= { cdx6500GCTLANConnectionEntry 1 }

        cdx6500WALanForwarderType OBJECT-TYPE
            SYNTAX INTEGER {
                    brid       (0),
                    rout       (1),
                    brout      (2),
                    newvalBrid (50),
                    nc         (100)
                    }
            ACCESS read-only
            STATUS mandatory
            DESCRIPTION
                "This parameter specifies the type of forwarders 
                 communicating over this LAN Connection.
                 brid  - Bridging Forwarders.
                 rout  - Routing Forwarders.
                 brout - Bridging and Routing Forwarders.
                 nc    - Skipped during  configuration.
                 newvalBrid - same functionality as 'brid', new enumeration
                         added for RFC1155 compatibility."
        ::= { cdx6500GCTLANConnectionEntry 2 }

        cdx6500WABridgeLinkNumber OBJECT-TYPE
            SYNTAX INTEGER (5..36)
            ACCESS read-only
            STATUS mandatory
            DESCRIPTION
                "This parameter specifies the Bridge-Link that is
                 using this LAN Connection."
        ::= { cdx6500GCTLANConnectionEntry 3 }

        cdx6500WARouterInterfaceNum OBJECT-TYPE
            SYNTAX INTEGER (5..36)
            ACCESS read-only
            STATUS mandatory
            DESCRIPTION
                "This parameter specifies the Router Interface 
                 that is using this LAN Connection."
        ::= { cdx6500GCTLANConnectionEntry 4 }

        cdx6500WACfgEncapsulationType OBJECT-TYPE
            SYNTAX INTEGER {
                    deprecatedObj (1)
                    }
            ACCESS read-only
            STATUS deprecated
            DESCRIPTION
                "This parameter specifies the data encapsulation 
                 type used over this LAN Connection.
                 This object has been deprecated, use cdx6500WACfgEncapType 
                 instead."
        ::= { cdx6500GCTLANConnectionEntry 5 }

        cdx6500WAAutocallMnemonic OBJECT-TYPE
            SYNTAX DisplayString
            ACCESS read-only
            STATUS mandatory
            DESCRIPTION
                "If configured, the Autocall Mnemonic references 
                 a remote address which will be called by the 
                 LAN Connection."
        ::= { cdx6500GCTLANConnectionEntry 6 }

        cdx6500WAAutocallTimeout OBJECT-TYPE
            SYNTAX INTEGER (5..255)
            ACCESS read-only
            STATUS mandatory
            DESCRIPTION
                "This is the time interval in seconds between 
                 call attempts when auto calling."
        ::= { cdx6500GCTLANConnectionEntry 7 }

        cdx6500WAMaxAutocallAttempts OBJECT-TYPE
            SYNTAX INTEGER (0..255)
            ACCESS read-only
            STATUS mandatory
            DESCRIPTION
                "This parameter is used to specify the number 
                 of times that the LAN Connection will attempt 
                 to autocall a remote destination. A value of 
                 zero will allow unlimited attempts."
        ::= { cdx6500GCTLANConnectionEntry 8 }

        cdx6500WARemoteConnectionId OBJECT-TYPE
            SYNTAX INTEGER (1..32)
            ACCESS read-only
            STATUS mandatory
            DESCRIPTION
                "This parameter specifies the number of the remote
                 LAN Connection or the FRA Station number that
                 this LAN connection will attempt to connect to 
                 if configured for autocall."
        ::= { cdx6500GCTLANConnectionEntry 9 }

        cdx6500WABillingRecords OBJECT-TYPE
            SYNTAX INTEGER {
                    off       (0),
                    on        (1),
                    newvalOff (50),
                    nc        (100)
                    }
            ACCESS read-only
            STATUS mandatory
            DESCRIPTION
                "This controls whether billing (accounting)
                 records will be created for calls on this 
                 LAN Connection.
                 off    :   Billing records will not be created.
                 on     :   Billing records will be created.
                 nc     :   Skipped during configuration.
                 newvalOff : same functionality as 'off', new
                            enumeration added for RFC1155 compatibility."
        ::= { cdx6500GCTLANConnectionEntry 10 }

        cdx6500WADataPassingPriority OBJECT-TYPE
            SYNTAX INTEGER {
                    low       (0),
                    med       (1),
                    high      (2),
                    exp       (3),
                    newvalLow (50),
                    nc        (100)
                    }
            ACCESS read-only
            STATUS mandatory
            DESCRIPTION
                "This parameter specifies the Traffic Priority
                 of this LAN Connection.
                 low  - Low Priority.
                 med  - Medium Priority.
                 high - High Priority.
                 exp  - Expedite Priority.
                 nc   - Skipped during configuration.
                 newvalLow - same functionality as 'low', new
                        enumeration added for RFC1155 compatibility."
        ::= { cdx6500GCTLANConnectionEntry 11 }

        cdx6500WALCONQueueLimit OBJECT-TYPE
            SYNTAX INTEGER (0..65535)
            ACCESS read-only
            STATUS mandatory
            DESCRIPTION
                "This parameter specifies the maximum number of bytes that 
                 will be queued for this LCON befor transmission on the WAN 
                 link. It is recommended that this parameter be set for two 
                 seconds of data on the WAN link."
        ::= { cdx6500GCTLANConnectionEntry 12 }

        cdx6500WACfgEncapType OBJECT-TYPE
            SYNTAX INTEGER {
                    codex       (0),
                    rfc1294     (1),
                    rfc877      (2),
                    newvalCodex (50),
                    nc          (100)
                    }
            ACCESS read-only
            STATUS mandatory
            DESCRIPTION
                "This parameter specifies the data encapsulation 
                 type used over this LAN Connection.
                 codex   - Codex Proprietary Encapsulation.
                 rfc1294 - RFC 1294 Multiprotocol Encapsulation.
                 rfc877  - RFC 877 Multiprotocol Encapsulation.
                 nc      - Skipped during configuration.
                 newvalCodex - same functionality as 'codex', new
                           enumeration added for RFC1155 compatibility."
        ::= { cdx6500GCTLANConnectionEntry 13 }

        cdx6500WACfgOnDemand OBJECT-TYPE
            SYNTAX INTEGER {
                    disabled       (0),
                    enabled        (1),
                    newvalDisabled (50),
                    nc             (100)
                    }
            ACCESS read-only
            STATUS mandatory
            DESCRIPTION
                "This parameter controls whether the circuit is established
                 at startup or established when required for data passing.
                 disabled   -  Circuit is established at start up.
                 enabled    -  Circuit is established on demand.
                 nc         -  Skipped during configuration.
                 newvalDisabled - same functionality as 'disabled', new
                               enumeration added for RFC1155 compatibility."
        ::= { cdx6500GCTLANConnectionEntry 14 }

        cdx6500WACfgIdleTimeout OBJECT-TYPE
            SYNTAX INTEGER (0..65535)
            ACCESS read-only
            STATUS mandatory
            DESCRIPTION
                "This parameter specifies the amount of time in seconds the
                 circuit will remain connected without passing any data
                 before being brought down. Setting the parameter to zero
                 keeps the circuit up indefinitely"
        ::= { cdx6500GCTLANConnectionEntry 15 }


        cdx6500WACfgLanConnectionType OBJECT-TYPE
            SYNTAX INTEGER {
                    ptToPt       (0),
                    group        (1),
                    newvalPtToPt (50),
                    nc           (100)
                    }
            ACCESS read-only
            STATUS mandatory
            DESCRIPTION
                "This parameter specifies whether the LAN Connection defines
                 a point to point connection across the WAN, or is part of 
                 a group of LAN Connections.
                 ptToPt - Point to Point LAN Connection.
                 group  - Member of a LAN Connection Group.
                 nc     - Skipped during configuration.
                 newvalPtToPt - same functionality as 'ptToPt', new
                          enumeration added for RFC1155 compatibility."
        ::= { cdx6500GCTLANConnectionEntry 16 }
              
        cdx6500WACfgNexthopIpAddress OBJECT-TYPE
            SYNTAX IpAddress
            ACCESS read-only
            STATUS mandatory
            DESCRIPTION
                "This parameter specifies the IP address of the Router 
                 Interface on the other end of this LAN Connection, which 
                 is the next hop on the path to the final destination. A 
                 setting of 0.0.0.0 causes this  parameter to be ignored."
        ::= { cdx6500GCTLANConnectionEntry 17 }

        cdx6500WACfgNexthopIpxNodeNumber OBJECT-TYPE
            SYNTAX INTEGER (0..4294967295)
            ACCESS read-only
            STATUS mandatory
            DESCRIPTION
                "This parameter specifies the IPX node number of the Router 
                 on the other end of this LAN Connection, which is the next 
                 hop on the path to the final destination. A setting of 0 
                 causes this parameter to be ignored."
        ::= { cdx6500GCTLANConnectionEntry 18 }

        cdx6500WACfgParallelSvc OBJECT-TYPE
            SYNTAX INTEGER (0..3)
            ACCESS read-only
            STATUS mandatory
            DESCRIPTION
                "This parameter specifies the maximum number of parallel 
                 connections that can be established to the remote destination.
                 Parallel SVCs are established when congestion thresholds are 
                 reached on active connections."
        ::= { cdx6500GCTLANConnectionEntry 19 }

        cdx6500WACfgParallelThreshold OBJECT-TYPE
            SYNTAX INTEGER (0..65535)
            ACCESS read-only
            STATUS mandatory
            DESCRIPTION
                "This parameter specifies the number of outstanding data 
                 bytes that will trigger the establishment of a Parallel SVC. 
                 If this number of data bytes has been transmitted without 
                 acknowledgment, the receipt of additional data for 
                 transmission will trigger Parallel SVC establishment. 
                 Note that this parameter must be configured with a value 
                 less than the LCON Queue Limit parameter."
        ::= { cdx6500GCTLANConnectionEntry 20 }

        cdx6500WACfgParallelPort OBJECT-TYPE
            SYNTAX DisplayString
            ACCESS read-only
            STATUS mandatory
            DESCRIPTION
                "This parameter specifies the port that Parallel 
                 SVCs should be brought up over. The parameter 
                 can be in two forms. It can be in the form of a port
                 identifier string. For example, to bring Parallel
                 SVCs up over X25 port number 8, enter the string 
                 X25-8. It can also be in the form of a Switched 
                 Services Table destination name, if the port that 
                 the Parallel SVCs are to come up over is a dial on 
                 demand port. A value of (blank) will cause Parallel 
                 SVCs to be brought up over the same port as the main 
                 connection."
        ::= { cdx6500GCTLANConnectionEntry 21 }

        cdx6500WACfgBroadcast OBJECT-TYPE
            SYNTAX INTEGER {
                    disabled       (0),
                    enabled        (1),
                    newvalDisabled (50),
                    nc             (100)
                    }
            ACCESS read-only
            STATUS mandatory
            DESCRIPTION
                "This parameter specifies whether broadcast datagrams
                 should be transmitted over this LAN Connection to 
                 the remote destination.
                 disabled   :  Broadcast datagrams will not be transmitted 
                               over this LAN Connection.
                 enabled    :  Broadcast datagrams will be transmitted
                               over this LAN Connection.
                 nc         :  Skipped during  configuration.
                 newvalDisabled : same functionality as 'disabled', new
                               enumeration added for RFC1155 compatibility."
        ::= { cdx6500GCTLANConnectionEntry 22}

        cdx6500GCTWanAdaptorGroup OBJECT IDENTIFIER 
            ::= { cdx6500CfgGeneralGroup 17 }

        cdx6500GCMaxLCON OBJECT-TYPE
            SYNTAX INTEGER
            ACCESS read-only
            STATUS mandatory
            DESCRIPTION
                "Defines the maximum number of LAN Connections
                 that may be configured."
        ::= { cdx6500GCTWanAdaptorGroup 1 }


        -- The Wan Adaptor statistics tables for LAN Connection.
        -- Data Summary Statistics.

        cdx6500LCTDataSummaryStats OBJECT-TYPE
            SYNTAX SEQUENCE OF Cdx6500WADataStatEntry
            ACCESS not-accessible
            STATUS mandatory
            DESCRIPTION
                "Data summary statstics provides the information on
                 data packets transmitted, received, queued and discarded."
        ::= { cdx6500PSTLANConnectionGroup 1 }

        cdx6500WADataStatEntry OBJECT-TYPE
            SYNTAX Cdx6500WADataStatEntry
            ACCESS not-accessible
            STATUS mandatory
            DESCRIPTION
                "LAN Connection Record number."
            INDEX { cdx6500WALanConnNumberData }
        ::= { cdx6500LCTDataSummaryStats 1 }

        Cdx6500WADataStatEntry ::=
            SEQUENCE {
                cdx6500WALanConnNumberData
                    INTEGER,
                cdx6500WALastStatResetTime
                    DisplayString,
                cdx6500WAAvgPktSizeTx
                    Counter16,
                cdx6500WACurTxQueueDepth
                    Counter,
                cdx6500WAMaxTxQueueDepth
                    Counter,
                cdx6500WAMaxTxQDepthTime
                    DisplayString,
                cdx6500WAAvgPktSizeRcv
                    Counter16,
                cdx6500WATxPktDiscardFrwdReq
                    Counter,
                cdx6500WATxPktDiscardTransDelay
                    Counter,
                cdx6500WATxPktDiscardCong
                    Counter,
                cdx6500WATxPktDiscardMaxFrame
                    Counter,
                cdx6500WATxPktDiscardCLrReq
                    Counter,
                cdx6500WATxPktDiscardCallEstab
                    Counter,
                cdx6500WABytesOutstanding
                    Counter
                }

        cdx6500WALanConnNumberData OBJECT-TYPE
            SYNTAX INTEGER (1..32)
            ACCESS read-only
            STATUS mandatory
            DESCRIPTION
                "It identifies a specific LAN Connection Record."
        ::= { cdx6500WADataStatEntry 1 }

        cdx6500WALastStatResetTime OBJECT-TYPE
            SYNTAX DisplayString
            ACCESS read-only
            STATUS mandatory
            DESCRIPTION
                "The date and time of the last statistics reset."
        ::= { cdx6500WADataStatEntry 2 }

        cdx6500WAAvgPktSizeTx OBJECT-TYPE
            SYNTAX Counter16
            ACCESS read-only
            STATUS mandatory
            DESCRIPTION
                "Specifies the average size of the packets sent on 
                 the WAN, in bytes."
        ::= { cdx6500WADataStatEntry 3 }

        cdx6500WACurTxQueueDepth OBJECT-TYPE
            SYNTAX Counter
            ACCESS read-only
            STATUS mandatory
            DESCRIPTION
                "Specifies the current number of packets queued 
                 awaiting transmission on the WAN, in packets."
        ::= { cdx6500WADataStatEntry 4 }

        cdx6500WAMaxTxQueueDepth OBJECT-TYPE
            SYNTAX Counter
            ACCESS read-only
            STATUS mandatory
            DESCRIPTION
                "Specifies the maximum number of packets queued 
                 awaiting transmission on the WAN, in packets."
        ::= { cdx6500WADataStatEntry 5 }

        cdx6500WAMaxTxQDepthTime OBJECT-TYPE
            SYNTAX DisplayString
            ACCESS read-only
            STATUS mandatory
            DESCRIPTION
                "The date and time when the number of packets queued 
                 awaiting transmission on the WAN reached its maximum."
        ::= { cdx6500WADataStatEntry 6 }

        cdx6500WAAvgPktSizeRcv OBJECT-TYPE
            SYNTAX Counter16
            ACCESS read-only
            STATUS mandatory
            DESCRIPTION
                "Specifies the average size of the packets received on 
                 the WAN, in bytes."
        ::= { cdx6500WADataStatEntry 7 }

        cdx6500WATxPktDiscardFrwdReq OBJECT-TYPE
            SYNTAX Counter
            ACCESS read-only
            STATUS deprecated
            DESCRIPTION
                "This is a non-supported object."
        ::= { cdx6500WADataStatEntry 8 }

        cdx6500WATxPktDiscardTransDelay OBJECT-TYPE
            SYNTAX Counter
            ACCESS read-only
            STATUS mandatory
            DESCRIPTION
                "Specifies the number of packets discarded due to 
                 packets exceeding the maximum allowed delay through 
                 the node."
        ::= { cdx6500WADataStatEntry 9 }

        cdx6500WATxPktDiscardCong OBJECT-TYPE
            SYNTAX Counter
            ACCESS read-only
            STATUS mandatory
            DESCRIPTION
                "Specifies the number of packets discarded due to 
                 severe congestion."
        ::= { cdx6500WADataStatEntry 10 }

        cdx6500WATxPktDiscardMaxFrame OBJECT-TYPE
            SYNTAX Counter
            ACCESS read-only
            STATUS mandatory
            DESCRIPTION
                "Specifies the number of packets discarded due to 
                 packets exceeding the maximum allowed frame size."
        ::= { cdx6500WADataStatEntry 11 }

        cdx6500WATxPktDiscardCLrReq OBJECT-TYPE
            SYNTAX Counter
            ACCESS read-only
            STATUS mandatory
            DESCRIPTION
                "Specifies the number of packets discarded due to 
                 Clear Requests Received."
        ::= { cdx6500WADataStatEntry 12 }

        cdx6500WATxPktDiscardCallEstab OBJECT-TYPE
            SYNTAX Counter
            ACCESS read-only
            STATUS mandatory
            DESCRIPTION
                "Specifies the number of packets discarded due to 
                 Call Establishment Failure."
        ::= { cdx6500WADataStatEntry 13 }

        cdx6500WABytesOutstanding OBJECT-TYPE
            SYNTAX Counter
            ACCESS read-only
            STATUS mandatory
            DESCRIPTION
                "Count of outstanding transmit bytes ."
        ::= { cdx6500WADataStatEntry 14 } 

        -- Call Summary Statistics.

        cdx6500LCTCallSummaryStats OBJECT-TYPE
            SYNTAX SEQUENCE OF Cdx6500WACallStatEntry
            ACCESS not-accessible
            STATUS mandatory
            DESCRIPTION
                "A list of Call Summary Statistics for LAN connection."
        ::= { cdx6500PSTLANConnectionGroup 2 }

        cdx6500WACallStatEntry OBJECT-TYPE
            SYNTAX Cdx6500WACallStatEntry
            ACCESS not-accessible
            STATUS mandatory
            DESCRIPTION
                "LAN Connection Record number."
            INDEX { cdx6500WALanConnNumberCall }
        ::= { cdx6500LCTCallSummaryStats 1 }

        Cdx6500WACallStatEntry ::=
            SEQUENCE {
                cdx6500WALanConnNumberCall
                    INTEGER,
                cdx6500WAConnectionType
                    DisplayString,
                cdx6500WAStatEncapsulationType
                    INTEGER,
                cdx6500WAConnectionState
                    INTEGER,
                cdx6500WAForwardersConnected
                    DisplayString,
                cdx6500WARemoteAddress
                    DisplayString,
                cdx6500WANumAutocallAttempts
                    Counter8,
                cdx6500WALastClearCauseCode
                    INTEGER,
                cdx6500WALastClearDiagCode
                    INTEGER,
                cdx6500WAParallelSvcsEstab
                    Counter16, 
                cdx6500WAParallelSvcsConfigured
                    Counter8
                }

        cdx6500WALanConnNumberCall OBJECT-TYPE
            SYNTAX INTEGER (1..32)
            ACCESS read-only
            STATUS mandatory
            DESCRIPTION
                "It identifies a specific LAN Connection Record."
        ::= { cdx6500WACallStatEntry 1 }

        cdx6500WAConnectionType OBJECT-TYPE
            SYNTAX DisplayString
            ACCESS read-only
            STATUS mandatory
            DESCRIPTION
                "Specifies whether the connection is a Permanent Virtual 
                 Circuit (PVC) or a Switched Virtual Circuit (SVC)."
        ::= { cdx6500WACallStatEntry 2 }

        cdx6500WAStatEncapsulationType OBJECT-TYPE
            SYNTAX INTEGER {
                    codex       (0),
                    rfc1294     (1),
                    rfc877      (2),
                    newvalCodex (50)
                    }
            ACCESS read-only
            STATUS mandatory
            DESCRIPTION
                "This parameter specifies the data encapsulation 
                 type used over this LAN Connection.
                 codex   - Codex Proprietary Encapsulation.
                 rfc1294 - RFC 1294 Multiprotocol Encapsulation.
                 rfc877  - RFC 877 Multiprotocol Encapsulation.
                 newvalCodex - same functionality as 'codex', new
                           enumeration added for RFC1155 compatibility."
        ::= { cdx6500WACallStatEntry 3 }

        cdx6500WAConnectionState OBJECT-TYPE
            SYNTAX INTEGER {
                    unconfigured       (0),
                    backinHeap         (1),
                    notConnected       (2),
                    disabled           (3),
                    handshaking        (4),
                    waitForCall        (6),
                    wfccRecall         (7),
                    wfccWaitForCall    (8),
                    wfccDisabled       (9),
                    calling            (11),
                    connected          (17),
                    connectedCongested (18),
                    newvalUnconfigured (50)
                    }
            ACCESS read-only
            STATUS mandatory
            DESCRIPTION
                "Specifies the current state of the Permanent Virtual
                 Circuit (PVC) or a Switched Virtual Circuit (SVC).
                 unconfigured       : Init state.
                 backinHeap         : LCONCB has been returned to memory heap.
                 notConnected       : Completed Init, waiting for startup,
                                      or failed autocall SVC.
                 disabled           : Connection is Disabled.
                 calling            : Autocall SVC trying to complete call.
                 waitForCall        : Non-autocall SVC waiting for call.
                 handshaking        : PVC in reset handshake process.
                 connected          : Connection is established.
                 connectedCongested : Connection has reached congestion thresh.
                 wfccRecall         : Wait for Clr Conf Re-Call, autocall SVC.
                 wfccWaitForCall    : Wait for Clr Conf Wait for Call non-auto
                                    : calling SVC.
                 wfccDisabled       : Wait for Clr Conf goto Disabled.
                 newvalUnconfigured : same functionality as 'unconfigured', new
                                      enumeration added for RFC1155 compatibility."
        ::= { cdx6500WACallStatEntry 4 }

        cdx6500WAForwardersConnected OBJECT-TYPE
            SYNTAX DisplayString
            ACCESS read-only
            STATUS mandatory
            DESCRIPTION
                "Specifies which forwarders are currently connected 
                 to this LAN Connection ."
        ::= { cdx6500WACallStatEntry 5 }

        cdx6500WARemoteAddress OBJECT-TYPE
            SYNTAX DisplayString
            ACCESS read-only
            STATUS mandatory
            DESCRIPTION
                "Specifies the called address of the remote WAN Adaptor
                 LAN Connection for connected SVCs."
        ::= { cdx6500WACallStatEntry 6 }

        cdx6500WANumAutocallAttempts OBJECT-TYPE
            SYNTAX Counter8
            ACCESS read-only
            STATUS mandatory
            DESCRIPTION
                "Specifies the number of times attempted to autocall
                 before either succeeded or failed in establishing the
                 connection."
        ::= { cdx6500WACallStatEntry 7 }

        cdx6500WALastClearCauseCode OBJECT-TYPE
            SYNTAX INTEGER
            ACCESS read-only
            STATUS mandatory
            DESCRIPTION
                "This is the cause code in the call clear packet last
                 received by the LAN connection and explains why the 
                 last call was cleared."
        ::= { cdx6500WACallStatEntry 8 }

        cdx6500WALastClearDiagCode OBJECT-TYPE
            SYNTAX INTEGER
            ACCESS read-only
            STATUS mandatory
            DESCRIPTION
                "This is the diagnostic code in the call clear packet 
                 last received by the LAN connection and explains why 
                 the last call was cleared."
        ::= { cdx6500WACallStatEntry 9 }

        cdx6500WAParallelSvcsEstab OBJECT-TYPE
            SYNTAX Counter16
            ACCESS read-only
            STATUS mandatory
            DESCRIPTION
                "Count of parallel SVCs with calls established."
        ::= { cdx6500WACallStatEntry 10 }

        cdx6500WAParallelSvcsConfigured OBJECT-TYPE
            SYNTAX Counter8
            ACCESS read-only
            STATUS mandatory
            DESCRIPTION
                "Number of Parallel SVCs."
        ::= { cdx6500WACallStatEntry 11 }

        -- Packet Summary Statistics.

        cdx6500LCTPacketSummaryStats OBJECT-TYPE
            SYNTAX SEQUENCE OF Cdx6500WAPktStatEntry
            ACCESS not-accessible
            STATUS mandatory
            DESCRIPTION
                "A list of Packet Summary Statistics for LAN connection."
        ::= { cdx6500PSTLANConnectionGroup 3 }

        cdx6500WAPktStatEntry OBJECT-TYPE
            SYNTAX Cdx6500WAPktStatEntry
            ACCESS not-accessible
            STATUS mandatory
            DESCRIPTION
                "LAN Connection Record number."
            INDEX { cdx6500WALanConnNumberPkt }
        ::= { cdx6500LCTPacketSummaryStats 1 }

        Cdx6500WAPktStatEntry ::=
            SEQUENCE {
                cdx6500WALanConnNumberPkt
                    INTEGER,
                cdx6500WADataPktTx
                    Counter,
                cdx6500WADataPktRcv
                    Counter,
                cdx6500WACallReqPktsTx
                    Counter,
                cdx6500WACallReqPktsRcv
                    Counter,
                cdx6500WACallAcceptPktsTx
                    Counter,
                cdx6500WACallAcceptPktsRcv
                    Counter,
                cdx6500WAClearReqPktsTx
                    Counter,
                cdx6500WAClearReqPktsRcv
                    Counter,
                cdx6500WAClearConfPktsTx
                    Counter,
                cdx6500WAClearConfPktsRcv
                    Counter,
                cdx6500WAResetReqPktsTx
                    Counter,
                cdx6500WAResetReqPktsRcv
                    Counter,
                cdx6500WAResetConfPktsTx
                    Counter,
                cdx6500WAResetConfPktsRcv
                    Counter
                }

        cdx6500WALanConnNumberPkt OBJECT-TYPE
            SYNTAX INTEGER (1..32)
            ACCESS read-only
            STATUS mandatory
            DESCRIPTION
                "It identifies a specific LAN Connection Record."
        ::= { cdx6500WAPktStatEntry 1 }

        cdx6500WADataPktTx OBJECT-TYPE
            SYNTAX Counter
            ACCESS read-only
            STATUS mandatory
            DESCRIPTION
                "Specifies the total number of Data Packets sent on the WAN."
        ::= { cdx6500WAPktStatEntry 2 }

        cdx6500WADataPktRcv OBJECT-TYPE
            SYNTAX Counter
            ACCESS read-only
            STATUS mandatory
            DESCRIPTION
                "Specifies the total number of Data Packets received
                 from the WAN."
        ::= { cdx6500WAPktStatEntry 3 }

        cdx6500WACallReqPktsTx OBJECT-TYPE
            SYNTAX Counter
            ACCESS read-only
            STATUS mandatory
            DESCRIPTION
                "Specifies the total number of Call Request Packets 
                 sent on the WAN."
        ::= { cdx6500WAPktStatEntry 4 }

        cdx6500WACallReqPktsRcv OBJECT-TYPE
            SYNTAX Counter
            ACCESS read-only
            STATUS mandatory
            DESCRIPTION
                "Specifies the total number of Call Request Packets 
                 received from the WAN."
        ::= { cdx6500WAPktStatEntry 5 }

        cdx6500WACallAcceptPktsTx OBJECT-TYPE
            SYNTAX Counter
            ACCESS read-only
            STATUS mandatory
            DESCRIPTION
                "Specifies the total number of Call Accept Packets 
                 sent on the WAN."
        ::= { cdx6500WAPktStatEntry 6 }

        cdx6500WACallAcceptPktsRcv OBJECT-TYPE
            SYNTAX Counter
            ACCESS read-only
            STATUS mandatory
            DESCRIPTION
                "Specifies the total number of Call Accept Packets 
                 received from the WAN."
        ::= { cdx6500WAPktStatEntry 7 }

        cdx6500WAClearReqPktsTx OBJECT-TYPE
            SYNTAX Counter
            ACCESS read-only
            STATUS mandatory
            DESCRIPTION
                "Specifies the total number of Clear Request Packets  
                 sent on the WAN."
        ::= { cdx6500WAPktStatEntry 8 }

        cdx6500WAClearReqPktsRcv OBJECT-TYPE
            SYNTAX Counter
            ACCESS read-only
            STATUS mandatory
            DESCRIPTION
                "Specifies the total number of Clear Request Packets  
                 received from the WAN."
        ::= { cdx6500WAPktStatEntry 9 }

        cdx6500WAClearConfPktsTx OBJECT-TYPE
            SYNTAX Counter
            ACCESS read-only
            STATUS mandatory
            DESCRIPTION
                "Specifies the total number of Clear Confirm Packets
                 sent on the WAN."
        ::= { cdx6500WAPktStatEntry 10 }

        cdx6500WAClearConfPktsRcv OBJECT-TYPE
            SYNTAX Counter
            ACCESS read-only
            STATUS mandatory
            DESCRIPTION
                "Specifies the total number of Clear Confirm Packets
                 received from the WAN."
        ::= { cdx6500WAPktStatEntry 11 }

        cdx6500WAResetReqPktsTx OBJECT-TYPE
            SYNTAX Counter
            ACCESS read-only
            STATUS mandatory
            DESCRIPTION
                "Specifies the total number of Reset Request Packets 
                 sent on the WAN."
        ::= { cdx6500WAPktStatEntry 12 }

        cdx6500WAResetReqPktsRcv OBJECT-TYPE
            SYNTAX Counter
            ACCESS read-only
            STATUS mandatory
            DESCRIPTION
                "Specifies the total number of Reset Request Packets 
                 received from the WAN."
        ::= { cdx6500WAPktStatEntry 13 }

        cdx6500WAResetConfPktsTx OBJECT-TYPE
            SYNTAX Counter
            ACCESS read-only
            STATUS mandatory
            DESCRIPTION
                "Specifies the total number of Reset Confirm Packets 
                 sent on the WAN."                                   
        ::= { cdx6500WAPktStatEntry 14 }

        cdx6500WAResetConfPktsRcv OBJECT-TYPE
            SYNTAX Counter
            ACCESS read-only
            STATUS mandatory
            DESCRIPTION
                "Specifies the total number of Reset Confirm Packets 
                 received from the WAN."
        ::= { cdx6500WAPktStatEntry 15 }

        -- The Wan Adaptor control tables for LAN Connection.

        cdx6500ContWANAdaptorTable OBJECT-TYPE                        
            SYNTAX SEQUENCE OF Cdx6500ContWANAdaptorEntry
            ACCESS not-accessible                                    
            STATUS mandatory                                         
            DESCRIPTION                                               
                "Control parameters for the LAN Connection."                 
        ::= { cdx6500ContWANAdaptor 1 }                           
                                                                        
        cdx6500ContWANAdaptorEntry OBJECT-TYPE                        
            SYNTAX Cdx6500ContWANAdaptorEntry
            ACCESS not-accessible                                    
            STATUS mandatory                                         
            DESCRIPTION                                               
                "Each control applies to a single LAN Connection."
            INDEX { cdx6500WAControlLanConnNumber }                 
        ::= { cdx6500ContWANAdaptorTable 1 }                      
                                                                        
        Cdx6500ContWANAdaptorEntry ::=
            SEQUENCE {
                cdx6500WAControlLanConnNumber
                    INTEGER,
                cdx6500WALanConnEnableDisable
                    INTEGER,
                cdx6500WALanConnBoot
                    INTEGER,
                cdx6500WALanConnResetStat
                    INTEGER
                }

        cdx6500WAControlLanConnNumber OBJECT-TYPE
            SYNTAX INTEGER (1..32)
            ACCESS read-only
            STATUS mandatory
            DESCRIPTION
                "This identifies a specific LAN Connection Record."
        ::= { cdx6500ContWANAdaptorEntry 1 }

        cdx6500WALanConnEnableDisable OBJECT-TYPE
            SYNTAX INTEGER {
                    enable       (0),
                    disable      (1),
                    newvalEnable (50)
                    }
            ACCESS read-write
            STATUS mandatory
            DESCRIPTION
                "This command enables or disables a specified LAN connection.
                 newvalEnable : same functionality as 'enable', new enumeration
                 added for RFC1155 compatibility."
        ::= { cdx6500ContWANAdaptorEntry 2 }

        cdx6500WALanConnBoot OBJECT-TYPE
            SYNTAX INTEGER {
                    boot (1)
                    }
            ACCESS write-only
            STATUS mandatory
            DESCRIPTION
                "This command causes the LAN connection record to be booted."
        ::= { cdx6500ContWANAdaptorEntry 3 }

        cdx6500WALanConnResetStat OBJECT-TYPE
            SYNTAX INTEGER {
                    resetStats (1)
                    }
            ACCESS write-only
            STATUS mandatory
            DESCRIPTION
                "When this command is entered the resettable statistics 
                 parameters are reset for the specified LAN Connection Number."
        ::= { cdx6500ContWANAdaptorEntry 4 }

        END
