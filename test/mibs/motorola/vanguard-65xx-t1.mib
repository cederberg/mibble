-- Version 1.5, modified 02/12/98

        T1-OPT-MIB DEFINITIONS ::= BEGIN

        IMPORTS
            Counter, Gauge
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }
    cdx6500PCTT1E1PortTable OBJECT IDENTIFIER ::= { cdx6500PCTPortProtocolGroup 24 }
          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }
    cdx6500PSTT1E1PortTable OBJECT IDENTIFIER ::= { cdx6500PSTPortProtocolGroup 25 }

        -- Textual Conventions

        DisplayString ::= OCTET STRING

        PhysicalPortNumber ::= INTEGER (49..50)

        VirtualPortNumber ::= INTEGER (100..255)

        cdx6500PCTT1PortTable OBJECT IDENTIFIER
            ::= { cdx6500PCTT1E1PortTable 1 }

        -- T1 Physical Port Configuration Table

        cdx6500PPCTT1PortTable OBJECT-TYPE
            SYNTAX SEQUENCE OF Cdx6500PPCTT1PortEntry
            ACCESS not-accessible
            STATUS mandatory
            DESCRIPTION
                "This table contains the T1 (Physical) Port Configuration
                 parameters."
        ::= { cdx6500PCTT1PortTable 1 }

        cdx6500PPCTT1PortEntry OBJECT-TYPE
            SYNTAX SEQUENCE OF Cdx6500PPCTT1PortEntry
            ACCESS not-accessible
            STATUS mandatory
            DESCRIPTION
                "A T1 Port Configuration Table Entry. Each entry
                 contains the configuration parameters for a single
                 T1 port."
            INDEX { cdx6500T1CfgPortNumber }
        ::= { cdx6500PPCTT1PortTable 1 }

        Cdx6500PPCTT1PortEntry ::=
            SEQUENCE {
                cdx6500T1CfgPortNumber
                    INTEGER,
                cdx6500T1CfgPortType
                    INTEGER,
                cdx6500T1CfgFormat
                    INTEGER,
                cdx6500T1CfgLineFramingType
                    INTEGER,
                cdx6500T1CfgLineCoding
                    INTEGER,
                cdx6500T1CfgTransmitClock
                    INTEGER,
                cdx6500T1CfgLineBuildOut
                    INTEGER,
                cdx6500T1CfgFacilityDataLink
                    INTEGER,
                cdx6500T1CfgThresholdValueLES
                    INTEGER,
                cdx6500T1CfgThresholdValueLCV
                    INTEGER,
                cdx6500T1CfgThresholdValuePCV
                    INTEGER,
                cdx6500T1CfgThresholdValueCSS
                    INTEGER,
                cdx6500T1CfgThresholdValueES
                    INTEGER,
                cdx6500T1CfgThresholdValueBES
                    INTEGER,
                cdx6500T1CfgThresholdValueSES
                    INTEGER,
                cdx6500T1CfgThresholdValueSEFS
                    INTEGER,
                cdx6500T1CfgThresholdValueUAS
                    INTEGER,
                cdx6500T1CfgThresholdValueDM
                    INTEGER,
                cdx6500T1CfgSwitchType
                    INTEGER,
                cdx6500T1CfgVariant
                    INTEGER,
                cdx6500T1CfgUserNetworkSide
                    INTEGER,
                cdx6500T1CfgCallingIdMsbState
                    INTEGER
                }

        cdx6500T1CfgPortNumber OBJECT-TYPE
            SYNTAX PhysicalPortNumber
            ACCESS read-only
            STATUS mandatory
            DESCRIPTION
                "Port number of the (physical) T1 port."
        ::= { cdx6500PPCTT1PortEntry 1 }

        cdx6500T1CfgPortType OBJECT-TYPE
            SYNTAX INTEGER {
                    t1 (44)
                    }
            ACCESS read-only
            STATUS mandatory
            DESCRIPTION
                "This is a digital port having interface type T1.
                 t1 : This is a T1 port."
        ::= { cdx6500PPCTT1PortEntry 2 }

        cdx6500T1CfgFormat OBJECT-TYPE
            SYNTAX INTEGER {
                    channelize (1),
                    isdn       (2),
                    nc         (100)
                    } 
            ACCESS read-only
            STATUS mandatory
            DESCRIPTION
                "This parameter is used to select the format of the T1 
                 interface.
                 channelize : DS0 definition fixed, predefined
                              by the telco or the user.
                 isdn       : DS0 definition defined by the
                              ISDN D channel.
                 nc         : Skipped during configuration."
        ::= { cdx6500PPCTT1PortEntry 3 }

        cdx6500T1CfgLineFramingType OBJECT-TYPE
            SYNTAX INTEGER {
                    esf (1),
                    sf  (4),
                    nc  (100)
                    }
            ACCESS read-only
            STATUS mandatory
            DESCRIPTION
                "Indicates the type of framing used by the DS1 circuit.
                 esf : Extended SuperFrame.
                 sf  : SuperFrame.
                 nc  : Skipped during configuration."
        ::= { cdx6500PPCTT1PortEntry 4 }

        cdx6500T1CfgLineCoding OBJECT-TYPE
            SYNTAX INTEGER {
                    b8zs (1),
                    b7zs (2),
                    ami  (3),
                    nc   (100) 
                    }
            ACCESS read-only
            STATUS mandatory
            DESCRIPTION
                "Selects the type of suppression used on the T1 link.
                 b8zs :Bipolar 8 Zero Substitution. 
                 b7zs :Bipolar 7 zero Substitution.
                 ami  :Alternate Mark Inversion.
                 nc   : Skipped during configuration."
        ::= { cdx6500PPCTT1PortEntry 5 }

        cdx6500T1CfgTransmitClock OBJECT-TYPE
            SYNTAX INTEGER {
                    int  (131),
                    rec  (130),
                    node (129),
                    nc   (100)
                    }
            ACCESS read-only
            STATUS mandatory
            DESCRIPTION
                "Selects the source of the transmit clock.
                 int  : Internal Oscillator.
                 rec  : Received Timing.
                 node : Node Timing (timing off another interface).
                 nc   : Skipped during configuration."
        ::= { cdx6500PPCTT1PortEntry 6 }

        cdx6500T1CfgLineBuildOut OBJECT-TYPE
            SYNTAX INTEGER {
                    lbo0 (1),
                    lbo1 (2),
                    lbo2 (3),
                    lbo3 (4),
                    lbo4 (5),
                    nc   (100)
                    }
            ACCESS read-only
            STATUS mandatory
            DESCRIPTION
                 "Select the Line Build Out to match the physical interface.
                  For DSX interfaces, this value is based on cable
                  length as explained below :-
                  lbo0 :  0 ft to 133 ft
                  lbo1 :134 ft to 266 ft
                  lbo2 :267 ft to 399 ft
                  lbo3 :400 ft to 533 ft
                  lbo4 :534 ft to 655 ft
                  For DS1 interfaces, this value is based on the
                  signal level as explained below :-
                  lbo0 :  0   db
                  lbo1 : -7.5 db
                  lbo2 : -15  db
                  lbo3 : -22.5db
                  lbo4 : not valid for DS1 interfaces.
                  nc   : Skipped during configuration."
        ::= { cdx6500PPCTT1PortEntry 7 }   

        cdx6500T1CfgFacilityDataLink OBJECT-TYPE
            SYNTAX INTEGER {
                    none (1),
                    ansi (3),
                    att  (2),
                    nc   (100)
                    }
            ACCESS read-only
            STATUS mandatory
            DESCRIPTION
                "This describes the use of the facilities data link,
                 and may have the following capabilities:
                 none : indicates that the device does  not use
                        the FDL.
                 ansi : refers to the  FDL  exchange recommended 
                        by ANSI (Ansi-T1-403).
                 att  : refers to ESF FDL exchanges (Att-54016).
                 nc   : Skipped during configuration."
        ::= { cdx6500PPCTT1PortEntry 8 }

        cdx6500T1CfgThresholdValueLES OBJECT-TYPE
            SYNTAX INTEGER (1..255)
            ACCESS read-only
            STATUS mandatory
            DESCRIPTION
                "Threshold value of Line Errored Seconds (LESs)
                 to report alarms on CTP when exceeded."
        ::= { cdx6500PPCTT1PortEntry 9 }

        cdx6500T1CfgThresholdValueLCV OBJECT-TYPE
            SYNTAX INTEGER (1..255)
            ACCESS read-only
            STATUS mandatory
            DESCRIPTION
                "Threshold value of Line Code Violations (LCVs)
                 to report alarms on CTP when exceeded."
        ::= { cdx6500PPCTT1PortEntry 10 }

        cdx6500T1CfgThresholdValuePCV OBJECT-TYPE
            SYNTAX INTEGER (1..255)
            ACCESS read-only
            STATUS mandatory
            DESCRIPTION
                "Threshold value of Path Code Violations (PCVs)
                 to report alarms on CTP when exceeded."
        ::= { cdx6500PPCTT1PortEntry 11 }


        cdx6500T1CfgThresholdValueCSS OBJECT-TYPE
            SYNTAX INTEGER (1..255)
            ACCESS read-only
            STATUS mandatory
            DESCRIPTION
                "Threshold value of Controlled Slip Seconds (CSSs)
                 to report alarms on CTP when exceeded."
        ::= { cdx6500PPCTT1PortEntry 12 }

        cdx6500T1CfgThresholdValueES OBJECT-TYPE
            SYNTAX INTEGER (1..255)
            ACCESS read-only
            STATUS mandatory
            DESCRIPTION
                "Threshold value of Errored Seconds (ESs)
                 to report alarms on CTP when exceeded."
        ::= { cdx6500PPCTT1PortEntry 13 }

        cdx6500T1CfgThresholdValueBES OBJECT-TYPE
            SYNTAX INTEGER (1..255)
            ACCESS read-only
            STATUS mandatory
            DESCRIPTION
                "Threshold value of Bursty Errored Seconds (BESs)
                 to report alarms on CTP when exceeded."
        ::= { cdx6500PPCTT1PortEntry 14 }

        cdx6500T1CfgThresholdValueSES OBJECT-TYPE
            SYNTAX INTEGER (1..255)
            ACCESS read-only
            STATUS mandatory
            DESCRIPTION
                "Threshold value of Severely Errored Seconds (SESs)
                 to report alarms on CTP when exceeded."
        ::= { cdx6500PPCTT1PortEntry 15 }

        cdx6500T1CfgThresholdValueSEFS OBJECT-TYPE
            SYNTAX INTEGER (1..255)
            ACCESS read-only
            STATUS mandatory
            DESCRIPTION
                "Threshold value of Severely Errored Framing Seconds (SEFSs)
                 to report alarms on CTP when exceeded."
        ::= { cdx6500PPCTT1PortEntry 16 }

        cdx6500T1CfgThresholdValueUAS OBJECT-TYPE
            SYNTAX INTEGER (1..255)
            ACCESS read-only
            STATUS mandatory
            DESCRIPTION
                "Threshold value of Unavailable Seconds (UASs)
                 to report alarms on CTP when exceeded."
        ::= { cdx6500PPCTT1PortEntry 17 }

        cdx6500T1CfgThresholdValueDM OBJECT-TYPE
            SYNTAX INTEGER (1..255)
            ACCESS read-only
            STATUS mandatory
            DESCRIPTION
                "Threshold value of Degraded Minutes (DMs)
                 to report alarms on CTP when exceeded."
        ::= { cdx6500PPCTT1PortEntry 18 }

        cdx6500T1CfgSwitchType OBJECT-TYPE
            SYNTAX INTEGER {
                    att4ess  (1),
                    att5ess  (2),
                    ntDms100 (3),
                    ntDms250 (4),
                    md110Us  (5),
                    md110    (6),
                    siemens  (7),
                    ntt      (8),
                    unknown  (9),
                    nc       (100)
                    }
            ACCESS read-only
            STATUS mandatory
            DESCRIPTION
                "The ISDN switch type. This specifies the type of 
                 equipment to which this span is connected.
                 The possible choices are:
                 att4ess  : AT&T 4ESS Switch 
                 att5ess  : AT&T 5ESS Switch 
                 ntDms100 : Northern Telecom DMS-100 Switch 
                 ntDms250 : Northern Telecom DMS-250 Switch
                 md110Us  : Ericsson MD-110 (North America)
                 md110    : Ericsson MD-110 (International)
                 siemens  : Siemens EWSD Switch (U.S.)
                 ntt      : Nippon Telephone and Telegraph switch (Japan)
                 unknown  : Unknown Switch Type
                 nc       : Skipped during configuration"
        ::= { cdx6500PPCTT1PortEntry 19 }

        cdx6500T1CfgVariant OBJECT-TYPE
            SYNTAX INTEGER {
                    att    (1),
                    nt     (2),
                    isdn2  (4),
                    jate   (5),
                    net5   (7),
                    oneTr6 (9),
                    vn3    (10),
                    ccitt  (11),
                    ts014  (14),
                    nc     (100)
                    }
            ACCESS read-only
            STATUS mandatory
            DESCRIPTION
                "Select the ISDN Switch variant. This parameter
                 depends upon the switch type configured.
                 The possible choices are: 
                 att    : AT&T Custom
                 nt     : Northern Telecom
                 isdn2  : Bellcore National ISDN-2
                 jate   : JATE-compatible (Japan)
                 net5   : NET-5 standard (Europe)
                 oneTr6 : 1TR6 standard for PRI (Germany)
                 vn3    : VN3 standard (France)
                 ccitt  : General CCITT Q.931 conformance
                 ts014  : AUSTEL TS014 standard (Australia)
                 nc     : Skipped during configuration"
        ::= { cdx6500PPCTT1PortEntry 20 }

        cdx6500T1CfgUserNetworkSide OBJECT-TYPE
            SYNTAX INTEGER {
                    user    (1),
                    network (2),
                    nc      (100)
                    }
                ACCESS read-only
                STATUS mandatory
                DESCRIPTION
                    "This parameter specifies whether the T1/E1 port 
                     is emulating the network or user side of the 
                     ISDN network.
                     user    : The T1 or E1 port is emulating the user, 
                               ex.  the T1 or E1 port is to be connected 
                               to an ISDN network.
                     network : The T1 or E1 port is emulating the network, 
                               ex. the T1 or E1 port is to be connected 
                               to an ISDN PBX.
                     nc      : Skipped during configuration."
        ::= { cdx6500PPCTT1PortEntry 21 }

        cdx6500T1CfgCallingIdMsbState  OBJECT-TYPE
            SYNTAX INTEGER {
                    disabled (1),
                    enabled  (2),
                    nc       (100)
                    }
            ACCESS read-only
            STATUS mandatory
            DESCRIPTION
                "For DMS100/250 switches, this parameter defines if the MSB
                 is set or clear in the Calling ID IE.
                 disabled : The MSB in the calling ID IE is cleared.
                 enabled  : The MSB in the calling ID IE is set.
                 nc       : Skipped during configuration."
        ::= { cdx6500PPCTT1PortEntry 22 }


        -- The T1 Port Statistics Table
        
        cdx6500PPSTT1PortTable OBJECT-TYPE
            SYNTAX SEQUENCE OF Cdx6500PPSTT1PortEntry
            ACCESS not-accessible
            STATUS mandatory
            DESCRIPTION
                "This table holds statistics information for T1 ports."
        ::= { cdx6500PSTT1E1PortTable 1 }
        
        cdx6500PPSTT1PortEntry OBJECT-TYPE
            SYNTAX Cdx6500PPSTT1PortEntry
            ACCESS not-accessible
            STATUS mandatory
            DESCRIPTION
                "Each entry contains statistics information for one T1 port."
            INDEX { cdx6500T1StatPortNumber }            
        ::= { cdx6500PPSTT1PortTable 1 }
        
        Cdx6500PPSTT1PortEntry ::=
            SEQUENCE {
                cdx6500T1StatPortNumber
                    INTEGER,
                cdx6500T1StatPortType
                    INTEGER,
                cdx6500T1StatInterfaceType
                    INTEGER,
                cdx6500T1StatPortState
                    INTEGER,
                cdx6500T1StatAlarmState
                    INTEGER,
                cdx6500T1BoardHWRevAndPartNumber
                    DisplayString
                }

        cdx6500T1StatPortNumber OBJECT-TYPE
            SYNTAX PhysicalPortNumber
            ACCESS read-only
            STATUS mandatory
            DESCRIPTION
                "The port number of the T1 port."
        ::= { cdx6500PPSTT1PortEntry 1 }           

        cdx6500T1StatTimeSinceLastResetType OBJECT-TYPE
            SYNTAX DisplayString
            ACCESS read-only
            STATUS mandatory
            DESCRIPTION
                "Time since last reset has happened for the port."
        ::= { cdx6500PPSTT1PortEntry 2 }

        cdx6500T1StatPortType OBJECT-TYPE
            SYNTAX INTEGER {
                    t1 (44)
                    }
            ACCESS read-only
            STATUS mandatory
            DESCRIPTION
                "The configured value of the Port Type.
                 illegal : Invalid port type.
                 null    : This is a null port.
                 t1      : This is a digital port with interface type T1."
        ::= { cdx6500PPSTT1PortEntry 3 }
        
        cdx6500T1StatInterfaceType OBJECT-TYPE
            SYNTAX INTEGER {
                    dsx1   (1),
                    ds1Csu (2),
                    na     (100)
                    }
            ACCESS read-only
            STATUS mandatory
            DESCRIPTION
                "This parameter indicates the type of interface for this port.
                 dsx1   : This port has a DSX1 interface.
                 ds1Csu : This port has a DS1-CSU interface.
                 na     : Value not available."
        ::= { cdx6500PPSTT1PortEntry 4 }
                    
        cdx6500T1StatPortState OBJECT-TYPE
            SYNTAX INTEGER {
                    disabled (1),
                    enabled  (2),
                    na       (100)
                    }
            ACCESS read-only
            STATUS mandatory
            DESCRIPTION
                "The current port (CTP) state :
                 disabled : The port has been disabled.
                 enabled  : The port has been enabled.
                 na       : Value not available." 
        ::= { cdx6500PPSTT1PortEntry 5 }
        
        cdx6500T1StatAlarmState OBJECT-TYPE
            SYNTAX INTEGER {
                    none   (1),
                    yellow (2),
                    blue   (3),
                    red    (4),
                    na     (100)
                    }
            ACCESS read-only
            STATUS mandatory
            DESCRIPTION
                "The alarm state of the port :
                 none   : No alarm.
                 yellow : Remote alarm indication (yellow alarm).
                 blue   : Alarm indication signal (blue alarm).
                 red    : No frame sync (red alarm).
                 na     : Value not available."
        ::= { cdx6500PPSTT1PortEntry 6 }
        
        cdx6500T1BoardHWRevAndPartNumber OBJECT-TYPE
            SYNTAX DisplayString
            ACCESS read-only
            STATUS mandatory
            DESCRIPTION
                "Hardware Revision and part number of the board."
        ::= { cdx6500PPSTT1PortEntry 7 }
                    
        -- The Daily History Table

        cdx6500T1StatDailyHistoryTable OBJECT-TYPE
            SYNTAX SEQUENCE OF Cdx6500T1StatDailyHistoryEntry
            ACCESS not-accessible
            STATUS mandatory
            DESCRIPTION
                "The T1 Daily History Table contains various statistics
                 collected over the previous 24 hours which are broken
                 into 96 completed 15 minute intervals."
        ::= { cdx6500PSTT1E1PortTable 3 }

        cdx6500T1StatDailyHistoryEntry OBJECT-TYPE
            SYNTAX Cdx6500T1StatDailyHistoryEntry
            ACCESS not-accessible
            STATUS mandatory
            DESCRIPTION
                "An entry in the T1 Daily History Table."
            INDEX { cdx6500T1StatDailyHistoryPortNumber,
                    cdx6500T1StatDailyHistoryInterval }
        ::= { cdx6500T1StatDailyHistoryTable 1 }

        Cdx6500T1StatDailyHistoryEntry ::=
            SEQUENCE {
                cdx6500T1StatDailyHistoryInterval
                    INTEGER,
                cdx6500T1StatDailyHistoryLES
                    Gauge,
                cdx6500T1StatDailyHistoryLCV
                    Gauge,
                cdx6500T1StatDailyHistoryPCV
                    Gauge,
                cdx6500T1StatDailyHistoryCSS
                    Gauge,
                cdx6500T1StatDailyHistoryES
                    Gauge,
                cdx6500T1StatDailyHistoryBES
                    Gauge,
                cdx6500T1StatDailyHistorySES
                    Gauge,
                cdx6500T1StatDailyHistorySEFS
                    Gauge,
                cdx6500T1StatDailyHistoryUAS
                    Gauge,
                cdx6500T1StatDailyHistoryDM
                    Gauge,
                cdx6500T1StatDailyHistoryPortNumber
                    PhysicalPortNumber
                }

        cdx6500T1StatDailyHistoryInterval OBJECT-TYPE
            SYNTAX INTEGER (1..96)
            ACCESS read-only
            STATUS mandatory
            DESCRIPTION
                "This gives the history at 15 minute intervals.Each 
                 block represents a 15 minute interval of the day, 
                 starting from 00:15 and ending at 24:00.Thus there 
                 are 96 such blocks possible.Therefore,
                 1  represents the history at 00:15 .
                 2  represents the history at 00:30 .
                 ..........
                 96 represents the history at 24:00 ."
        ::= { cdx6500T1StatDailyHistoryEntry 1 }

        cdx6500T1StatDailyHistoryLES OBJECT-TYPE
            SYNTAX Gauge
            ACCESS read-only
            STATUS mandatory
            DESCRIPTION
                "The number of Line Errored Seconds (LESs)
                 encountered by the T1 interface in one of 
                 the previous 96, individual 15 minute intervals."
        ::= { cdx6500T1StatDailyHistoryEntry 2 }

        cdx6500T1StatDailyHistoryLCV OBJECT-TYPE
            SYNTAX Gauge
            ACCESS read-only
            STATUS mandatory
            DESCRIPTION
                "The number of Line Code Violations (LCVs)
                 encountered by the T1 interface in one of
                 the previous 96, individual 15 minute intervals."
        ::= { cdx6500T1StatDailyHistoryEntry 3 }

        cdx6500T1StatDailyHistoryPCV OBJECT-TYPE
            SYNTAX Gauge
            ACCESS read-only
            STATUS mandatory
            DESCRIPTION
                "The number of Path Coding Violations (PCVs)
                 encountered by the T1 interface in one of 
                 the previous 96, individual 15 minute intervals."
        ::= { cdx6500T1StatDailyHistoryEntry 4 }

        cdx6500T1StatDailyHistoryCSS OBJECT-TYPE
            SYNTAX Gauge
            ACCESS read-only
            STATUS mandatory
            DESCRIPTION
                "The number of Controlled Slip Seconds (CSSs)
                 encountered by the T1 interface in one of 
                 the previous 96, individual 15 minute intervals."
        ::= { cdx6500T1StatDailyHistoryEntry 5 }

        cdx6500T1StatDailyHistoryES OBJECT-TYPE
            SYNTAX Gauge
            ACCESS read-only
            STATUS mandatory
            DESCRIPTION
                "The number of Errored Seconds (ESs)
                 encountered by the T1 interface in one of 
                 the previous 96, individual 15 minute intervals."
        ::= { cdx6500T1StatDailyHistoryEntry 6 }

        cdx6500T1StatDailyHistoryBES OBJECT-TYPE
            SYNTAX Gauge
            ACCESS read-only
            STATUS mandatory
            DESCRIPTION
                "The number of Bursty Errored Seconds (BESs)
                 encountered by the T1 interface in one of 
                 the previous 96, individual 15 minute intervals."
        ::= { cdx6500T1StatDailyHistoryEntry 7 }

        cdx6500T1StatDailyHistorySES OBJECT-TYPE
            SYNTAX Gauge
            ACCESS read-only
            STATUS mandatory
            DESCRIPTION
                "The number of Severely Errored Seconds (SESs)
                 encountered by the T1 interface in one of 
                 the previous 96, individual 15 minute intervals."
        ::= { cdx6500T1StatDailyHistoryEntry 8 }

        cdx6500T1StatDailyHistorySEFS OBJECT-TYPE
            SYNTAX Gauge
            ACCESS read-only
            STATUS mandatory
            DESCRIPTION
                "The number of Severely Errored Framing Seconds 
                 (SEFSs) encountered by the T1 interface in one of 
                 the previous 96, individual 15 minute intervals."
        ::= { cdx6500T1StatDailyHistoryEntry 9 }

        cdx6500T1StatDailyHistoryUAS OBJECT-TYPE
            SYNTAX Gauge
            ACCESS read-only
            STATUS mandatory
            DESCRIPTION
                "The number of Unavailable Seconds (UASs)
                 encountered by the T1 interface in one of 
                 the previous 96, individual 15 minute intervals."
        ::= { cdx6500T1StatDailyHistoryEntry 10 }

        cdx6500T1StatDailyHistoryDM OBJECT-TYPE
            SYNTAX Gauge
            ACCESS read-only
            STATUS mandatory
            DESCRIPTION
                "The number of Degraded Minutes (DMs)
                 encountered by the T1 interface in one of 
                 the previous 96, individual 15 minute intervals."
        ::= { cdx6500T1StatDailyHistoryEntry 11 }

        cdx6500T1StatDailyHistoryPortNumber OBJECT-TYPE
            SYNTAX PhysicalPortNumber
            ACCESS read-only
            STATUS mandatory
            DESCRIPTION
                "The port number of the T1 port."
        ::= { cdx6500T1StatDailyHistoryEntry 12 }

        -- ABCD State Table

        cdx6500T1StatABCDStateTable OBJECT-TYPE
            SYNTAX SEQUENCE OF Cdx6500T1StatABCDStateEntry
            ACCESS not-accessible
            STATUS mandatory
            DESCRIPTION
                "The ABCD State Table contains the current
                 TX / RX ABCD state of the Configured DS0 Channels."
        ::= { cdx6500PSTT1E1PortTable 5 } 

        cdx6500T1StatABCDStateEntry OBJECT-TYPE
            SYNTAX Cdx6500T1StatABCDStateEntry
            ACCESS not-accessible
            STATUS mandatory
            DESCRIPTION
                "An entry in the ABCD State Table."
            INDEX { cdx6500T1StatABCDStatePortNumber,
                    cdx6500T1StatABCDStateDS0ChannelNumber }
        ::= { cdx6500T1StatABCDStateTable 1 }

        Cdx6500T1StatABCDStateEntry ::=
            SEQUENCE {
                cdx6500T1StatABCDStateDS0ChannelNumber
                    INTEGER,
                cdx6500T1StatABCDStateCurrentTxState
                    DisplayString,
                cdx6500T1StatABCDStateCurrentRxState
                    DisplayString,
                cdx6500T1StatABCDStatePortNumber
                    PhysicalPortNumber
                }

        cdx6500T1StatABCDStateDS0ChannelNumber OBJECT-TYPE
            SYNTAX INTEGER (1..24)
            ACCESS read-only
            STATUS mandatory
            DESCRIPTION
                "Channel number of the configured DS0 channel."
        ::= {cdx6500T1StatABCDStateEntry 1 }

        cdx6500T1StatABCDStateCurrentTxState OBJECT-TYPE
            SYNTAX DisplayString
            ACCESS read-only
            STATUS deprecated
            DESCRIPTION
                "Current TX ABCD state of the configured DS0 channels. This
                 object is no longer supported."
        ::= { cdx6500T1StatABCDStateEntry 2 }

        cdx6500T1StatABCDStateCurrentRxState OBJECT-TYPE
            SYNTAX DisplayString
            ACCESS read-only
            STATUS mandatory
            DESCRIPTION
                "Current RX ABCD state of the configured DS0 channels."
        ::= { cdx6500T1StatABCDStateEntry 3 }

        cdx6500T1StatABCDStatePortNumber OBJECT-TYPE
            SYNTAX PhysicalPortNumber
            ACCESS read-only
            STATUS mandatory
            DESCRIPTION
                "Port number of the T1 port."
        ::= {cdx6500T1StatABCDStateEntry 4 }


        -- ISDN Call Status

        cdx6500T1ISDNStatusTable OBJECT-TYPE
            SYNTAX SEQUENCE OF Cdx6500T1ISDNStatusEntry
            ACCESS not-accessible
            STATUS mandatory
            DESCRIPTION
                "This table holds ISDN statistics information for T1 ports."
        ::= { cdx6500PSTT1E1PortTable 7 }
        
        cdx6500T1StatISDNStatusEntry OBJECT-TYPE
            SYNTAX Cdx6500T1ISDNStatusEntry
            ACCESS not-accessible
            STATUS mandatory
            DESCRIPTION
                "Each entry contains statistics information for one T1 port."
            INDEX { cdx6500T1StatISDNStatusPortNumber }
        ::= { cdx6500T1ISDNStatusTable 1 }
        
        Cdx6500T1ISDNStatusEntry ::=
            SEQUENCE {
                cdx6500T1StatISDNStatusPortNumber
                    PhysicalPortNumber,
                cdx6500T1StatNumRxCallsSinceLastReset
                    INTEGER,
                cdx6500T1StatNumRxCallsRejected
                    INTEGER,
                cdx6500T1StatRxLastCallFailureCause
                    INTEGER,
                cdx6500T1StatRxLastCalledNumber
                    DisplayString,
                cdx6500T1StatRxLastCallingNumber
                    DisplayString,
                cdx6500T1StatRxMinCallDuration
                    DisplayString,
                cdx6500T1StatRxMaxCallDuration
                    DisplayString,
                cdx6500T1StatRxAvgCallDuration
                    DisplayString,
                cdx6500T1StatNumTxCallsSinceLastReset
                    INTEGER,
                cdx6500T1StatNumTxCallsRejected
                    INTEGER,
                cdx6500T1StatTxLastCallFailureCause
                    INTEGER,                
                cdx6500T1StatTxLastCalledNumber
                    DisplayString,
                cdx6500T1StatTxLastCallingNumber
                    DisplayString,
                cdx6500T1StatTxMinCallDuration
                    DisplayString,
                cdx6500T1StatTxMaxCallDuration
                    DisplayString,
                cdx6500T1StatTxAvgCallDuration
                    DisplayString,
                cdx6500T1StatDchannelState
                    INTEGER
                }

        cdx6500T1StatISDNStatusPortNumber OBJECT-TYPE
            SYNTAX PhysicalPortNumber
            ACCESS read-only
            STATUS mandatory
            DESCRIPTION
                "The port number of the T1 port."
        ::= { cdx6500T1StatISDNStatusEntry 1 }

        cdx6500T1StatNumRxCallsSinceLastReset OBJECT-TYPE
            SYNTAX INTEGER
            ACCESS read-only
            STATUS mandatory
            DESCRIPTION
                "The number of inbound calls that were attempted
                 since the last statistics reset."
        ::= { cdx6500T1StatISDNStatusEntry 2 }

        cdx6500T1StatNumRxCallsRejected OBJECT-TYPE
            SYNTAX INTEGER
            ACCESS read-only
            STATUS mandatory
            DESCRIPTION
                "The number of inbound calls that were rejected
                 since the last statistics reset."
        ::= { cdx6500T1StatISDNStatusEntry 3 }

        cdx6500T1StatRxLastCallFailureCause OBJECT-TYPE
            SYNTAX INTEGER {
                    noFailureReported          (193),
                    noAvailableVirtualPort     (194),
                    securityViolation          (195),
                    noResourcesAvailable       (196),
                    callRejected               (197),
                    invalidPhoneNumber         (198),
                    outgoingCallRequestTimeout (199),
                    callCollision              (200),
                    virtualPortNotAvailable    (201),
                    invalidConfiguration       (202),
                    na                         (255)
                    }
            ACCESS read-only
            STATUS mandatory
            DESCRIPTION
                "The reason the last inbound call was rejected,
                 since the last statistics reset.
                 The posssible values are:
                 noFailureReported          : No call failure
                 noAvailableVirtualPort     : No Virtual Port available
                 securityViolation          : Password/Calling ID security
                                              failed
                 noResourcesAvailable       : No resources available
                 callRejected               : Call failed by Xircom card
                 invalidPhoneNumber         : Incorrect phone number
                 outgoingCallRequestTimeout : Outgoing call request timed out
                 callCollision              : A call collision occurred
                 virtualPortNotAvailable    : Virtual port not available
                 invalidConfiguration       : Invalid configuration
                 na                         : Value not available"
        ::= { cdx6500T1StatISDNStatusEntry 4 }

        cdx6500T1StatRxLastCalledNumber OBJECT-TYPE
            SYNTAX DisplayString (SIZE (0..15))
            ACCESS read-only
            STATUS mandatory
            DESCRIPTION
                "The phone number of the virtual port of the last ISDN
                 call made into this node."
        ::= { cdx6500T1StatISDNStatusEntry 5 }

        cdx6500T1StatRxLastCallingNumber OBJECT-TYPE
            SYNTAX DisplayString (SIZE (0..15))
            ACCESS read-only
            STATUS mandatory
            DESCRIPTION
                "The phone number of last party to make an ISDN
                 call into this node."
        ::= { cdx6500T1StatISDNStatusEntry 6 }

        cdx6500T1StatRxMinCallDuration OBJECT-TYPE
            SYNTAX DisplayString
            ACCESS read-only
            STATUS mandatory
            DESCRIPTION
                "The minimum call duration of all inbound ISDN calls made
                 into this node, since the last statistics reset."
        ::= { cdx6500T1StatISDNStatusEntry 7 }

        cdx6500T1StatRxMaxCallDuration OBJECT-TYPE
            SYNTAX DisplayString
            ACCESS read-only
            STATUS mandatory
            DESCRIPTION
                "The maximum call duration of all inbound ISDN calls made
                 into this node, since the last statistics reset."
        ::= { cdx6500T1StatISDNStatusEntry 8 }

        cdx6500T1StatRxAvgCallDuration OBJECT-TYPE
            SYNTAX DisplayString
            ACCESS read-only
            STATUS mandatory
            DESCRIPTION
                "The average call duration of all inbound ISDN calls made
                 into this node, since the last statistics reset."
        ::= { cdx6500T1StatISDNStatusEntry 9 }

        cdx6500T1StatNumTxCallsSinceLastReset OBJECT-TYPE
            SYNTAX INTEGER
            ACCESS read-only
            STATUS mandatory
            DESCRIPTION
                "The number of outbound calls that were attempted
                 since the last statistics reset."
        ::= { cdx6500T1StatISDNStatusEntry 10 }

        cdx6500T1StatNumTxCallsRejected OBJECT-TYPE
            SYNTAX INTEGER
            ACCESS read-only
            STATUS mandatory
            DESCRIPTION
                "The number of outbound calls that were rejected
                 since the last statistics reset."
        ::= { cdx6500T1StatISDNStatusEntry 11 }

        cdx6500T1StatTxLastCallFailureCause OBJECT-TYPE
            SYNTAX INTEGER {
                    noFailureReported          (193),
                    noAvailableVirtualPort     (194),
                    securityViolation          (195),
                    noResourcesAvailable       (196),
                    callRejected               (197),
                    invalidPhoneNumber         (198),
                    outgoingCallRequestTimeout (199),
                    callCollision              (200),
                    virtualPortNotAvailable    (201),
                    invalidConfiguration       (202),
                    na                         (255)
                    }
            ACCESS read-only
            STATUS mandatory
            DESCRIPTION
                "The reason the last outbound call was rejected,
                 since the last statistics reset.
                 The posssible values are:
                 noFailureReported          : No call failure
                 noAvailableVirtualPort     : No Virtual Port available
                 securityViolation          : Password/Calling ID security
                                              failed
                 noResourcesAvailable       : No resources available
                 callRejected               : Call failed by Xircom card
                 invalidPhoneNumber         : Incorrect phone number
                 outgoingCallRequestTimeout : Outgoing call request timed out
                 callCollision              : A call collision occurred
                 virtualPortNotAvailable    : Virtual port not available
                 invalidConfiguration       : Invalid configuration
                 na                         : Value not available"
        ::= { cdx6500T1StatISDNStatusEntry 12 }

        cdx6500T1StatTxLastCalledNumber OBJECT-TYPE
            SYNTAX DisplayString (SIZE (0..15))
            ACCESS read-only
            STATUS mandatory
            DESCRIPTION
                "The phone number of the last ISDN call made by a virtual 
                 port from this node."
        ::= { cdx6500T1StatISDNStatusEntry 13 }

        cdx6500T1StatTxLastCallingNumber OBJECT-TYPE
            SYNTAX DisplayString (SIZE (0..15))
            ACCESS read-only
            STATUS mandatory
            DESCRIPTION
                "The phone number of the virtual port that made the last 
                 ISDN call from this node."
        ::= { cdx6500T1StatISDNStatusEntry 14 }

        cdx6500T1StatTxMinCallDuration OBJECT-TYPE
            SYNTAX DisplayString
            ACCESS read-only
            STATUS mandatory
            DESCRIPTION
                "The minimum call duration of all outbound ISDN calls made
                 from this node, since the last statistics reset."
        ::= { cdx6500T1StatISDNStatusEntry 15 }

        cdx6500T1StatTxMaxCallDuration OBJECT-TYPE
            SYNTAX DisplayString
            ACCESS read-only
            STATUS mandatory
            DESCRIPTION
                "The maximum call duration of all outbound ISDN calls made
                 from this node, since the last statistics reset."
        ::= { cdx6500T1StatISDNStatusEntry 16 }

        cdx6500T1StatTxAvgCallDuration OBJECT-TYPE
            SYNTAX DisplayString
            ACCESS read-only
            STATUS mandatory
            DESCRIPTION
                "The average call duration of all outbound ISDN calls made
                 from this node, since the last statistics reset."
        ::= { cdx6500T1StatISDNStatusEntry 17 }

        cdx6500T1StatDchannelState OBJECT-TYPE
            SYNTAX INTEGER {
                    up   (1),
                    down (2),
                    na   (100)
                    }
            ACCESS read-only
            STATUS mandatory
            DESCRIPTION
                "Specifies the status of the D Channel.
                 up   : The D Channel is up.
                 down : The D Channel is down.
                 na   : Value not available."
        ::= { cdx6500T1StatISDNStatusEntry 18 }

        cdx6500T1ISDNCallSummaryTable OBJECT-TYPE
            SYNTAX SEQUENCE OF Cdx6500T1StatISDNCallSummaryEntry
            ACCESS not-accessible
            STATUS mandatory
            DESCRIPTION
                "This table holds ISDN call summary information for T1 ports."
        ::= { cdx6500PSTT1E1PortTable 9 }

        cdx6500T1StatISDNCallSummaryEntry OBJECT-TYPE
            SYNTAX Cdx6500T1StatISDNCallSummaryEntry
            ACCESS not-accessible
            STATUS mandatory
            DESCRIPTION
                "An entry in the ISDN call summary table."
            INDEX { cdx6500T1StatISDNPortNumber,
                    cdx6500T1StatISDNBChannelNumber }
        ::= { cdx6500T1ISDNCallSummaryTable 1 }

        Cdx6500T1StatISDNCallSummaryEntry ::=
            SEQUENCE {
                cdx6500T1StatISDNBChannelNumber
                    INTEGER,
                cdx6500T1StatISDNBChannelStatus
                    INTEGER,
                cdx6500T1StatISDNCallDirection
                    INTEGER,
                cdx6500T1StatISDNCallingNumber
                    DisplayString,
                cdx6500T1StatISDNCalledNumber
                    DisplayString,
                cdx6500T1StatISDNDS0Rate
                    INTEGER,
                cdx6500T1StatISDNVirtualPortNumber
                    INTEGER,
                cdx6500T1StatISDNTimeCallStarted
                    DisplayString,
                cdx6500T1StatISDNPortNumber
                    PhysicalPortNumber
                }

        cdx6500T1StatISDNBChannelNumber OBJECT-TYPE
            SYNTAX INTEGER (1..23)
            ACCESS read-only
            STATUS mandatory
            DESCRIPTION
                "B-Channel number of the ISDN Channel."
        ::= { cdx6500T1StatISDNCallSummaryEntry 1 }

        cdx6500T1StatISDNBChannelStatus OBJECT-TYPE
            SYNTAX INTEGER {
                    idle         (1),
                    ringing      (2),
                    connected    (3),
                    outOfService (4),
                    na           (100)
                    }
            ACCESS read-only
            STATUS mandatory
            DESCRIPTION
                "Status of the ISDN B-Channel.
                 The posssible values are:
                 idle          : The B-Channel is in the idle state.
                 ringing       : The B-Channel is in the ringing state.
                 connected     : The B-Channel is in the connected state.
                 outOfService  : The B-Channel is out of service.
                 na            : Value not available."
        ::= { cdx6500T1StatISDNCallSummaryEntry 2 }
     
        cdx6500T1StatISDNCallDirection OBJECT-TYPE
            SYNTAX INTEGER {
                    inbound  (1),
                    outbound (2),
                    invalid  (3),
                    na       (100)
                    }
            ACCESS read-only
            STATUS mandatory
            DESCRIPTION
                "Direction of the ISDN call on the B-Channel.
                 The posssible values are:
                 inbound  : The current call is in the inbound direction.
                 outbound : The current call is in the outbound direction.
                 invalid  : There is no call present.
                 na       : Value not available."
        ::= { cdx6500T1StatISDNCallSummaryEntry 3 }

        cdx6500T1StatISDNCallingNumber OBJECT-TYPE
            SYNTAX DisplayString (SIZE (0..15))
            ACCESS read-only
            STATUS mandatory
            DESCRIPTION
                "This is the phone number of the party originating the 
                 ISDN call."
        ::= { cdx6500T1StatISDNCallSummaryEntry 4 }

        cdx6500T1StatISDNCalledNumber OBJECT-TYPE
            SYNTAX DisplayString (SIZE (0..15))
            ACCESS read-only
            STATUS mandatory
            DESCRIPTION
                "This is the phone number of the party at the destination 
                 end of the ISDN call."
        ::= { cdx6500T1StatISDNCallSummaryEntry 5 }

        cdx6500T1StatISDNDS0Rate OBJECT-TYPE
            SYNTAX INTEGER {
                    ds056k (1),
                    ds064k (2),
                    na     (100)
                    }
            ACCESS read-only
            STATUS mandatory
            DESCRIPTION
                "DS0 Rate of the ISDN B-Channel.
                 The posssible values are:
                 ds056k : The DS0 Rate is 56K.
                 ds064k : The DS0 Rate is 64K.
                 na     : Value not available."
        ::= { cdx6500T1StatISDNCallSummaryEntry 6 }

        cdx6500T1StatISDNVirtualPortNumber OBJECT-TYPE
            SYNTAX INTEGER
            ACCESS read-only
            STATUS mandatory
            DESCRIPTION
                "Virtual Port Number of the port using this B-Channel.
                 A value of 0 implies that no virtual port is
                 currently using the B-Channel."
        ::= { cdx6500T1StatISDNCallSummaryEntry 7 }

        cdx6500T1StatISDNTimeCallStarted OBJECT-TYPE
            SYNTAX DisplayString
            ACCESS read-only
            STATUS mandatory
            DESCRIPTION
                "This is the duration that the current call on this 
                 B-Channel has been connected."
        ::= { cdx6500T1StatISDNCallSummaryEntry 8 }

        cdx6500T1StatISDNPortNumber OBJECT-TYPE
            SYNTAX PhysicalPortNumber
            ACCESS read-only
            STATUS mandatory
            DESCRIPTION
                "Port number of the T1 port."
        ::= {cdx6500T1StatISDNCallSummaryEntry 9 }

        -- The last 24 hour Error Statistics Table

        cdx6500T1StatLast24HoursReportTable OBJECT-TYPE
            SYNTAX SEQUENCE OF Cdx6500T1StatLast24HoursReportEntry
            ACCESS not-accessible
            STATUS mandatory
            DESCRIPTION
                "This table holds a report of the cumulative sum
                 of the statistics for the previous 24 hour interval."
        ::= { cdx6500PSTT1E1PortTable 11 }
        
        cdx6500T1StatLast24HoursReportEntry OBJECT-TYPE
            SYNTAX Cdx6500T1StatLast24HoursReportEntry
            ACCESS not-accessible
            STATUS mandatory
            DESCRIPTION
                "Each entry contains statistics information for one T1 port."
            INDEX  { cdx6500T1StatLast24HoursReportPortNumber }
        ::= { cdx6500T1StatLast24HoursReportTable 1 }

        Cdx6500T1StatLast24HoursReportEntry ::=
            SEQUENCE {
                cdx6500T1StatLast24HoursReportPortNumber
                    PhysicalPortNumber,
                cdx6500T1StatLast24HoursReportLES
                    Gauge,
                cdx6500T1StatLast24HoursReportLCV
                    Gauge,
                cdx6500T1StatLast24HoursReportPCV
                    Gauge,
                cdx6500T1StatLast24HoursReportCSS
                    Gauge,
                cdx6500T1StatLast24HoursReportES
                    Gauge,
                cdx6500T1StatLast24HoursReportBES
                    Gauge,
                cdx6500T1StatLast24HoursReportSES
                    Gauge,
                cdx6500T1StatLast24HoursReportSEFS
                    Gauge,
                cdx6500T1StatLast24HoursReportUAS
                    Gauge
                }

        cdx6500T1StatLast24HoursReportPortNumber OBJECT-TYPE
            SYNTAX PhysicalPortNumber
            ACCESS read-only
            STATUS mandatory
            DESCRIPTION
                "Port number of the T1 port."
        ::= { cdx6500T1StatLast24HoursReportEntry 1 }
     
        cdx6500T1StatLast24HoursReportLES OBJECT-TYPE
            SYNTAX Gauge
            ACCESS read-only
            STATUS mandatory
            DESCRIPTION
                "The number of Line Errored Seconds (LESs)
                 encountered by the T1 interface in the 
                 previous 24 hour interval. "
        ::= { cdx6500T1StatLast24HoursReportEntry 2 }

        cdx6500T1StatLast24HoursReportLCV OBJECT-TYPE
            SYNTAX Gauge
            ACCESS read-only
            STATUS mandatory
            DESCRIPTION
                "The number of Line Code Violations (LCVs)
                 encountered by the T1 interface in the 
                 previous 24 hour interval."
        ::= { cdx6500T1StatLast24HoursReportEntry 3 }

        cdx6500T1StatLast24HoursReportPCV OBJECT-TYPE
            SYNTAX Gauge
            ACCESS read-only
            STATUS mandatory
            DESCRIPTION
                "The number of Path Coding  Violations (PCVs)
                 encountered by the T1 interface in the 
                 previous 24 hour interval."
        ::= { cdx6500T1StatLast24HoursReportEntry 4 }

        cdx6500T1StatLast24HoursReportCSS OBJECT-TYPE
            SYNTAX Gauge
            ACCESS read-only
            STATUS mandatory
            DESCRIPTION
                "The number of Controlled Slip Seconds (CSSs)
                 encountered by the T1 interface in the 
                 previous 24 hour interval."
        ::= { cdx6500T1StatLast24HoursReportEntry 5 }

        cdx6500T1StatLast24HoursReportES OBJECT-TYPE
            SYNTAX Gauge
            ACCESS read-only
            STATUS mandatory
            DESCRIPTION
                "The number of Errored Seconds (ESs) 
                 encountered by the T1 interface in the 
                 previous 24 hour interval."
        ::= { cdx6500T1StatLast24HoursReportEntry 6 }

        cdx6500T1StatLast24HoursReportBES OBJECT-TYPE
            SYNTAX Gauge
            ACCESS read-only
            STATUS mandatory
            DESCRIPTION
                "The number of Bursty Errored Seconds (BESs)
                 encountered by the T1 interface in the 
                 previous 24 hour interval."
        ::= { cdx6500T1StatLast24HoursReportEntry 7 }

        cdx6500T1StatLast24HoursReportSES OBJECT-TYPE
            SYNTAX Gauge
            ACCESS read-only
            STATUS mandatory
            DESCRIPTION
                "The number of Severely Errored Seconds (SESs)
                 encountered by the T1 interface in the
                 previous 24 hour interval."
        ::= { cdx6500T1StatLast24HoursReportEntry 8 }

        cdx6500T1StatLast24HoursReportSEFS OBJECT-TYPE
            SYNTAX Gauge
            ACCESS read-only
            STATUS mandatory
            DESCRIPTION
                "The number of Severely Errored Framing Seconds (SEFSs)
                 encountered by the T1 interface in the previous
                 24 hour interval."
        ::= { cdx6500T1StatLast24HoursReportEntry 9 }

        cdx6500T1StatLast24HoursReportUAS OBJECT-TYPE
            SYNTAX Gauge
            ACCESS read-only
            STATUS mandatory
            DESCRIPTION
                "The number of Unavailable Seconds (UASs)
                 encountered by the T1 interface in the 
                 previous 24 hour interval."
        ::= { cdx6500T1StatLast24HoursReportEntry 10 }

        -- The current 15 minute interval Error Statistics Table

        cdx6500T1StatCurrent15MinutesReportTable OBJECT-TYPE
            SYNTAX SEQUENCE OF Cdx6500T1StatCurrent15MinutesReportEntry
            ACCESS not-accessible
            STATUS mandatory
            DESCRIPTION
                "This table holds a report of the statistics for the 
                 current 15 minutes interval."
        ::= { cdx6500PSTT1E1PortTable 13 }

        cdx6500T1StatCurrent15MinutesReportEntry OBJECT-TYPE
            SYNTAX Cdx6500T1StatCurrent15MinutesReportEntry
            ACCESS not-accessible
            STATUS mandatory
            DESCRIPTION
                "Each entry contains statistics information for one T1 port."
            INDEX  { cdx6500T1StatCurrent15MinutesReportPortNumber }
        ::= { cdx6500T1StatCurrent15MinutesReportTable 1 }

        Cdx6500T1StatCurrent15MinutesReportEntry ::=
            SEQUENCE {
                cdx6500T1StatCurrent15MinutesReportPortNumber
                    PhysicalPortNumber,
                cdx6500T1StatCurrent15MinutesReportTimeElapsed
                    DisplayString,
                cdx6500T1StatCurrent15MinutesReportLES
                    Gauge,
                cdx6500T1StatCurrent15MinutesReportLCV
                    Gauge,
                cdx6500T1StatCurrent15MinutesReportPCV
                    Gauge,
                cdx6500T1StatCurrent15MinutesReportCSS
                    Gauge,
                cdx6500T1StatCurrent15MinutesReportES
                    Gauge,
                cdx6500T1StatCurrent15MinutesReportBES
                    Gauge,
                cdx6500T1StatCurrent15MinutesReportSES
                    Gauge,
                cdx6500T1StatCurrent15MinutesReportSEFS
                    Gauge,
                cdx6500T1StatCurrent15MinutesReportUAS
                    Gauge
                }                                               

        cdx6500T1StatCurrent15MinutesReportPortNumber OBJECT-TYPE
            SYNTAX PhysicalPortNumber
            ACCESS read-only
            STATUS mandatory
            DESCRIPTION
                "Port number of the T1 port."
        ::= { cdx6500T1StatCurrent15MinutesReportEntry 1 }

        cdx6500T1StatCurrent15MinutesReportTimeElapsed OBJECT-TYPE
            SYNTAX DisplayString
            ACCESS read-only
            STATUS mandatory
            DESCRIPTION
                "The time that has elapsed since the beginning 
                 of the current 15 minutes interval."
        ::= { cdx6500T1StatCurrent15MinutesReportEntry 2 }
                    
        cdx6500T1StatCurrent15MinutesReportLES OBJECT-TYPE
            SYNTAX Gauge
            ACCESS read-only
            STATUS mandatory
            DESCRIPTION
                "The number of Line Errored Seconds (LESs)
                 encountered by the T1 interface in the 
                 current 15 minute interval."
        ::= { cdx6500T1StatCurrent15MinutesReportEntry 3 }

        cdx6500T1StatCurrent15MinutesReportLCV OBJECT-TYPE
            SYNTAX Gauge
            ACCESS read-only
            STATUS mandatory
            DESCRIPTION
                "The number of Line Code Violations (LCVs)
                 encountered by the T1 interface in the 
                 current 15 minute interval."
        ::= { cdx6500T1StatCurrent15MinutesReportEntry 4 }

        cdx6500T1StatCurrent15MinutesReportPCV OBJECT-TYPE
            SYNTAX Gauge
            ACCESS read-only
            STATUS mandatory
            DESCRIPTION
                "The number of Path Coding  Violations (PCVs)
                 encountered by the T1 interface in the 
                 current 15 minute interval."
        ::= { cdx6500T1StatCurrent15MinutesReportEntry 5 }

        cdx6500T1StatCurrent15MinutesReportCSS OBJECT-TYPE
            SYNTAX Gauge
            ACCESS read-only
            STATUS mandatory
            DESCRIPTION
                "The number of Controlled Slip Seconds (CSSs)
                 encountered by the T1 interface in the 
                 current 15 minute interval."
        ::= { cdx6500T1StatCurrent15MinutesReportEntry 6 }

        cdx6500T1StatCurrent15MinutesReportES OBJECT-TYPE
            SYNTAX Gauge
            ACCESS read-only
            STATUS mandatory
            DESCRIPTION
                "The number of Errored Seconds (ESs) 
                 encountered by the T1 interface in the 
                 current 15 minute interval."
        ::= { cdx6500T1StatCurrent15MinutesReportEntry 7 }

        cdx6500T1StatCurrent15MinutesReportBES OBJECT-TYPE
            SYNTAX Gauge
            ACCESS read-only
            STATUS mandatory
            DESCRIPTION
                "The number of Bursty Errored Seconds (BESs)
                 encountered by the T1 interface in the 
                 current 15 minute interval."
        ::= { cdx6500T1StatCurrent15MinutesReportEntry 8 }

        cdx6500T1StatCurrent15MinutesReportSES OBJECT-TYPE
            SYNTAX Gauge
            ACCESS read-only
            STATUS mandatory
            DESCRIPTION
                "The number of Severely Errored Seconds (SESs)
                 encountered by the T1 interface in the
                 current 15 minute interval."
        ::= { cdx6500T1StatCurrent15MinutesReportEntry 9 }

        cdx6500T1StatCurrent15MinutesReportSEFS OBJECT-TYPE
            SYNTAX Gauge
            ACCESS read-only
            STATUS mandatory
            DESCRIPTION
                "The number of Severely Errored Framing Seconds (SEFSs)
                 encountered by the T1 interface in the current
                 15 minute interval."
        ::= { cdx6500T1StatCurrent15MinutesReportEntry 10 }

        cdx6500T1StatCurrent15MinutesReportUAS OBJECT-TYPE
            SYNTAX Gauge
            ACCESS read-only
            STATUS mandatory
            DESCRIPTION
                "The number of Unavailable Seconds (UASs)
                 encountered by the T1 interface in the 
                 current 15 minute interval."
        ::= { cdx6500T1StatCurrent15MinutesReportEntry 11 }

        END
