-- Version 1.5, modified 02/12/98

        BCST-OPT-MIB DEFINITIONS ::= BEGIN

        IMPORTS
           OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

        -- Textual conventions

        DisplayString ::= OCTET STRING

        -- The 6500 SVC Broadcast Output (SBCO) Configuration Table
        -- This table contains the configuration parameters for  BCST SBCO

        cdx6500GCTSVCBroadcastTable OBJECT-TYPE
            SYNTAX SEQUENCE OF Cdx6500bcstSBCOcfgEntry
            ACCESS not-accessible
            STATUS mandatory
            DESCRIPTION
                "A list of Broadcast SBCO configuration entries."
        ::= { cdx6500CfgGeneralGroup 10 }

        cdx6500bcstSBCOcfgEntry OBJECT-TYPE
            SYNTAX Cdx6500bcstSBCOcfgEntry
            ACCESS not-accessible
            STATUS mandatory
            DESCRIPTION
                 "The entries for the Broadcast SBCO table."
            INDEX { cdx6500bcstSBCOnum }
        ::= { cdx6500GCTSVCBroadcastTable 1 }

        Cdx6500bcstSBCOcfgEntry ::=
            SEQUENCE {
                cdx6500bcstSBCOnum
                    INTEGER,
                cdx6500bcstSBCOnet
                    INTEGER,
                cdx6500bcstSBCOcalledAddr 
                    DisplayString,
                cdx6500bcstSBCOcallingAddr
                    DisplayString,
                cdx6500bcstSBCOfacilities 
                    DisplayString,
                cdx6500bcstSBCOuserData 
                    DisplayString,
                cdx6500bcstSBCOdirection 
                    INTEGER, 
                cdx6500bcstSBCOdestination
                    INTEGER 
                }

        cdx6500bcstSBCOnum OBJECT-TYPE
            SYNTAX INTEGER (0..255)
            ACCESS read-only
            STATUS mandatory
            DESCRIPTION
                "Index for the Broadcast SBCO configuration table."
        ::= { cdx6500bcstSBCOcfgEntry 1 }

        cdx6500bcstSBCOnet OBJECT-TYPE
            SYNTAX INTEGER (0..255)
            ACCESS read-only
            STATUS mandatory
            DESCRIPTION
                "The main channel subaddress of the Broadcast, BCST."
        ::= { cdx6500bcstSBCOcfgEntry 2}

        cdx6500bcstSBCOcalledAddr OBJECT-TYPE
            SYNTAX DisplayString
            ACCESS read-only
            STATUS mandatory
            DESCRIPTION
                "Call packets containing this called address will enable
                 broadcast traffic for this net."
        ::= { cdx6500bcstSBCOcfgEntry 3 }

        cdx6500bcstSBCOcallingAddr OBJECT-TYPE
            SYNTAX DisplayString
            ACCESS read-only
            STATUS mandatory
            DESCRIPTION
                "Call packets containing this calling address will enable
                 broadcast traffic for this net."
        ::= { cdx6500bcstSBCOcfgEntry 4 }

        cdx6500bcstSBCOfacilities OBJECT-TYPE
            SYNTAX DisplayString
            ACCESS read-only
            STATUS mandatory
            DESCRIPTION
                "Call packets containing the facility bytes shown will enable
                 broadcast traffic for this net."
        ::= { cdx6500bcstSBCOcfgEntry 5 }

        cdx6500bcstSBCOuserData OBJECT-TYPE
            SYNTAX DisplayString
            ACCESS read-only
            STATUS mandatory
            DESCRIPTION
                "Call packets containing the user data bytes shown will enable
                 broadcast traffic for this net."
        ::= { cdx6500bcstSBCOcfgEntry 6 }

        cdx6500bcstSBCOdirection OBJECT-TYPE
            SYNTAX INTEGER {
                    none    (1),
                    called  (2),
                    calling (3)
                    }
            ACCESS read-only
            STATUS mandatory
            DESCRIPTION
                "This specifies the direction in which broadcast traffic will
                 be sent. Select options on this broadcast net as follows:
                 none    - no option specified
                 called  - send traffic towards the called address
                 calling - send traffic towards the calling address
                 Any combination of above specified by summing 
                 (e.g. called + calling)."
        ::= { cdx6500bcstSBCOcfgEntry 7 }

        cdx6500bcstSBCOdestination OBJECT-TYPE
              SYNTAX INTEGER {
                      user (1),
                      bctp (2)
                      }
              ACCESS read-only
              STATUS mandatory
              DESCRIPTION
                  "This specifies who the destination is and what will happen
                   to the broadcast message. Select options on this broadcast
                   net as follows:
                   user - end user to receive broadcast; implies stripping of
                          the net identification byte.
                   bctp - broadcast input port on adjacent node; net 
                          identification byte is not stripped."
        ::= { cdx6500bcstSBCOcfgEntry 8 }   

        -- The 6500 PVC Broadcast Output (PBCO) Configuration Table
        -- This table contains the configuration parameters for  BCST PBCO

        cdx6500GCTPVCBroadcastOutTable OBJECT-TYPE
            SYNTAX SEQUENCE OF Cdx6500bcstPBCOcfgEntry
            ACCESS not-accessible
            STATUS mandatory
            DESCRIPTION
                "A list of BCST PBCO configuration entries."
        ::= { cdx6500CfgGeneralGroup 11 }

        cdx6500bcstPBCOcfgEntry OBJECT-TYPE
            SYNTAX Cdx6500bcstPBCOcfgEntry
            ACCESS not-accessible
            STATUS mandatory
            DESCRIPTION
                "The entries of cdx6500GCTPVCBroadcastOutTable"
            INDEX { cdx6500bcstPBCOnum }
        ::= { cdx6500GCTPVCBroadcastOutTable 1 }

        Cdx6500bcstPBCOcfgEntry ::=
            SEQUENCE {
                cdx6500bcstPBCOnum
                    INTEGER,
                cdx6500bcstPBCOnet
                    INTEGER,
                cdx6500bcstPBCOconnection
                    DisplayString,
                cdx6500bcstPBCOdestination
                    INTEGER
                }

        cdx6500bcstPBCOnum OBJECT-TYPE
            SYNTAX INTEGER (0..255)
            ACCESS read-only
            STATUS mandatory
            DESCRIPTION
                "Index for the BCST PBCO table."
        ::= { cdx6500bcstPBCOcfgEntry 1 }

        cdx6500bcstPBCOnet OBJECT-TYPE
            SYNTAX INTEGER (0..255)
            ACCESS read-only
            STATUS mandatory
            DESCRIPTION
                "The configuration which follows will trigger broadcast
                 traffic for this broadcast net."
        ::= { cdx6500bcstPBCOcfgEntry 2}

        cdx6500bcstPBCOconnection OBJECT-TYPE
            SYNTAX DisplayString
            ACCESS read-only
            STATUS mandatory
            DESCRIPTION
                "Watch for connections destined to this channel.  
                 For example, a connection to port 1, channel 13 is P1(13), 
                 or a connection to port 2, station 4, channel 5 is P2S4(5)."
        ::= { cdx6500bcstPBCOcfgEntry 3 }

        cdx6500bcstPBCOdestination OBJECT-TYPE
            SYNTAX INTEGER 
            ACCESS read-only
            STATUS mandatory
            DESCRIPTION
                "Watch for connections destined to this channel.  
                 For example, a connection to port 1, channel 13 is P1(13), 
                 or a connection to port 2, station 4, channel 5 is P2S4(5)."
        ::= { cdx6500bcstPBCOcfgEntry 4 }

        END
