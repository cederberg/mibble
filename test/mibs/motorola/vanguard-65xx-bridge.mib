-- Version 1.4, modified 02/12/98

        BRIDGE-OPT-MIB DEFINITIONS ::= BEGIN

        IMPORTS 
            Counter
                FROM RFC1155-SMI          
        
           OBJECT-TYPE 
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
      cdx6500PCTBridgeGroup OBJECT IDENTIFIER ::= { cdx6500CfgProtocolGroup 6 }

          cdx6500Statistics OBJECT IDENTIFIER ::= { cdx6500 3 }
   cdx6500StatProtocolGroup OBJECT IDENTIFIER ::= { cdx6500Statistics 1 }
      cdx6500PSTBridgeGroup OBJECT IDENTIFIER ::= { cdx6500StatProtocolGroup 5 }

        -- Textual conventions

        MacAddress ::= OCTET STRING (SIZE (6)) 
 
        DisplayString ::= OCTET STRING

        -- The Bridge-Identifier as used in the Spanning Tree
        -- Protocol to uniquely identify a bridge.  Its first two octets
        -- (in network byte order) contain a priority value and its last
        -- 6 octets contain the MAC address used to refer to a bridge in a
        -- unique fashion (typically, the numerically smallest MAC address
        -- of all ports on the bridge).
        BridgeId ::= OCTET STRING (SIZE (8))   


        --
        -- The Static (Destination-Address Filtering) Database
        -- Address Filter Configurables - Table
    
        cdx6500PCTPortStaticAddrTable OBJECT-TYPE
            SYNTAX SEQUENCE OF Cdx6500PCTPortStaticAddrEntry
            ACCESS not-accessible
            STATUS mandatory
            DESCRIPTION
                "This table contains MAC Address filtering 
                 configuration information."
        ::= { cdx6500PCTBridgeGroup 1 }
    
        cdx6500PCTPortStaticAddrEntry OBJECT-TYPE
            SYNTAX Cdx6500PCTPortStaticAddrEntry
            ACCESS not-accessible
            STATUS mandatory
            DESCRIPTION
                "A list of Source and Destination Address
                 Actions and Bridge Link Lists for each entry."
            INDEX   { cdx6500LfcmStaticAddrEntryNumber }
        ::= { cdx6500PCTPortStaticAddrTable 1 }
    
        Cdx6500PCTPortStaticAddrEntry ::=
            SEQUENCE {
                cdx6500LfcmStaticAddrEntryNumber
                    INTEGER,
                cdx6500LfcmStaticMacAddr
                    MacAddress,
                cdx6500LfcmStaticIncSrcLinkAct
                    DisplayString,
                cdx6500LfcmStaticOutSrcLinkAct
                    DisplayString,
                cdx6500LfcmStaticIncDestLinkAct
                    DisplayString,
                cdx6500LfcmStaticOutDestLinkAct
                    DisplayString,
                cdx6500LfcmStaticIncSrcList
                    DisplayString,
                cdx6500LfcmStaticOutSrcList
                    DisplayString,
                cdx6500LfcmStaticIncDestList
                    DisplayString,
                cdx6500LfcmStaticOutDestList
                    DisplayString,
                cdx6500LfcmStaticMacMask
                    MacAddress
                }
    
        cdx6500LfcmStaticAddrEntryNumber OBJECT-TYPE
            SYNTAX INTEGER
            ACCESS read-only
            STATUS mandatory
            DESCRIPTION
                "The number of the table entry corresponding to
                 the MAC address that is subject to Filtering
                 Action.  The Entry Number ranger is 1 - 300"
        ::= { cdx6500PCTPortStaticAddrEntry 1 }
    
        cdx6500LfcmStaticMacAddr OBJECT-TYPE
            SYNTAX MacAddress
            ACCESS read-only
            STATUS mandatory
            DESCRIPTION
                "MAC Address subject to Filtering action"
        ::= { cdx6500PCTPortStaticAddrEntry 2 }
    
        cdx6500LfcmStaticIncSrcLinkAct OBJECT-TYPE
            SYNTAX DisplayString (SIZE(4..9))
            ACCESS read-only
            STATUS mandatory
            DESCRIPTION
                "PASS      = Pass incoming frames with this MAC Address
                             value on all links. (See User's Manual).
                 BLOCK     = Block incoming frames with this MAC Address
                             value on all links. (See User's Manual).
                 PASSLIST  = Pass List.  Links in this list will pass the
                             frame. Links not in this list will block the
                             frame. (See User's Manual).
                 BLOCKLIST = Block List. Links in this list will block 
                             the frame. Links not in this list will
                             pass the frame. (See User's Manual)."
        ::= { cdx6500PCTPortStaticAddrEntry 3 }
    
        cdx6500LfcmStaticOutSrcLinkAct OBJECT-TYPE
            SYNTAX DisplayString (SIZE(4..9))
            ACCESS read-only
            STATUS mandatory
            DESCRIPTION
                "PASS      = Pass outgoing frames with this MAC Address
                             value on all links. (See User's Manual).
                 BLOCK     = Block outgoing frames with this MAC Address
                             value on all links. (See User's Manual).
                 PASSLIST  = Pass List.  Links in this list will pass the
                             frame. Links not in this list will block the
                             frame. (See User's Manual).
                 BLOCKLIST = Block List. Links in this list will block the
                             frame. Links not in this list will pass the frame.
                             (See User's Manual)."
        ::= { cdx6500PCTPortStaticAddrEntry 4 }
    
        cdx6500LfcmStaticIncDestLinkAct OBJECT-TYPE
            SYNTAX DisplayString (SIZE(4..9))
            ACCESS read-only
            STATUS mandatory
            DESCRIPTION
                "PASS      = Pass incoming frames with this MAC Address
                             value on all links. (See User's Manual).
                 BLOCK     = Block incoming frames with this MAC Address
                             value on all links. (See User's Manual).
                 PASSLIST  = Pass List.
                             Links in this list will pass the frame. 
                             Links not in this list will block the frame.
                             (See User's Manual).
                 BLOCKLIST = Block List.
                             Links in this list will block the frame.
                             Links not in this list will pass the frame.
                             (See User's Manual)."
        ::= { cdx6500PCTPortStaticAddrEntry 5 }
    
        cdx6500LfcmStaticOutDestLinkAct OBJECT-TYPE
            SYNTAX DisplayString (SIZE(4..9))
            ACCESS read-only
            STATUS mandatory
            DESCRIPTION
                "PASS      = Pass outgoing frames with this MAC Address
                             value on all links. (See User's Manual).
                 BLOCK     = Block outgoing frames with this MAC Address
                             value on all links. (See User's Manual).
                 PASSLIST  = Pass List.
                             Links in this list will pass the frame.
                             Links not in this list will block the frame.
                             (See User's Manual).
                 BLOCKLIST = Block List.
                             Links in this list will block the frame.
                             Links not in this list will pass the frame.
                             (See User's Manual)."
        ::= { cdx6500PCTPortStaticAddrEntry 6 }

        cdx6500LfcmStaticIncSrcList OBJECT-TYPE
            SYNTAX DisplayString
            ACCESS read-only
            STATUS mandatory
            DESCRIPTION
                "The individual numbers correspond to the Links
                 which will be filtered according to the preceding
                 parameter:
                 PASSLIST  = the listed links will pass the
                             frame and unlisted links will block the frame.
                 BLOCKLIST = the listed links will block the
                             frame and unlisted links will pass the frame.
                 A range of link numbers can be entered, for
                 example: 1,6,8-12 indicates 1,6,8,9,10,11,12"
        ::= { cdx6500PCTPortStaticAddrEntry 7 }

        cdx6500LfcmStaticOutSrcList OBJECT-TYPE
            SYNTAX DisplayString
            ACCESS read-only
            STATUS mandatory
            DESCRIPTION
                "The individual numbers correspond to the Links
                 which will be filtered according to the preceding parameter:
                 PASSLIST  = the listed links will pass the frame
                             and unlisted links will block the frame
                 BLOCKLIST = the listed links will block the frame
                             and unlisted links will pass the frame
                 A range of link numbers can be entered, for
                 example: 1,6,8-12 indicates 1,6,8,9,10,11,12"
        ::= { cdx6500PCTPortStaticAddrEntry 8 }

        cdx6500LfcmStaticIncDestList OBJECT-TYPE
            SYNTAX DisplayString
            ACCESS read-only
            STATUS mandatory
            DESCRIPTION
                "The individual numbers correspond to the Links
                 which will be filtered according to the preceding
                 parameter:
                 PASSLIST  = the listed links will pass the frame 
                             and unlisted links will block the frame.
                 BLOCKLIST = the listed links will block the
                             frame and unlisted links pass the frame
                 A range of link numbers can be entered, for
                 example: 1,6,8-12 indicates 1,6,8,9,10,11,12"
        ::= { cdx6500PCTPortStaticAddrEntry 9 }

        cdx6500LfcmStaticOutDestList OBJECT-TYPE
            SYNTAX DisplayString
            ACCESS read-only
            STATUS mandatory
            DESCRIPTION
                "The individual numbers correspond to the Links
                 which will be filtered according to the preceding
                 parameter:
                 PASSLIST  = the listed links will pass the frame
                             and unlisted links will block the frame.
                 BLOCKLIST = the listed links will block the frame
                             and unlisted links will pass the frame
                 A range of link numbers can be entered, for 
                 example: 1,6,8-12 indicates 1,6,8,9,10,11,12"
        ::= { cdx6500PCTPortStaticAddrEntry 10 }

        cdx6500LfcmStaticMacMask OBJECT-TYPE
            SYNTAX MacAddress
            ACCESS read-only
            STATUS mandatory
            DESCRIPTION
                "This object contains a six-byte mask to indicate 
                 which nibbles in cdx6500LfcmStaticMacAddr object 
                 contain a wild card. A mask nibble with value 'F' shows 
                 no wild card in corresponding nibble in MacAddress, while
                 a mask nibble with value '0' shows a wild card. 
                 Any (0) nibbles in the mask corresponds to 'don't care' 
                 location in the Mac Address. 
                 Only the significant nibble positions are checked when 
                 comparing a frame's source or destination Mac Address 
                 to the cdx6500LfcmStaticMacAddr field."
        ::= { cdx6500PCTPortStaticAddrEntry 11 }
    
        -- The Protocol Filtering Database - Port
        --
        -- Protocol Filter Configurables - Table
        --
    
        cdx6500PCTPortStaticProtTable OBJECT-TYPE
            SYNTAX SEQUENCE OF Cdx6500PCTPortStaticProtEntry
            ACCESS not-accessible
            STATUS mandatory
            DESCRIPTION
                "This table contains Protocol Filtering
                 Configuration Information."
        ::= { cdx6500PCTBridgeGroup 2 }
    
        cdx6500PCTPortStaticProtEntry OBJECT-TYPE
            SYNTAX Cdx6500PCTPortStaticProtEntry
            ACCESS not-accessible
            STATUS mandatory
            DESCRIPTION
                "This is a list of configurable information
                 for each Protocol Filtering Table entry.
                 The parameters include Protocol Type, 
                 Protocol Value, link actions and Bridge
                 Link lists."
            INDEX { cdx6500LfcmStaticProtEntryNumber }
        ::= { cdx6500PCTPortStaticProtTable 1 }
    
        Cdx6500PCTPortStaticProtEntry ::=
            SEQUENCE {
                cdx6500LfcmStaticProtEntryNumber
                    INTEGER,
                cdx6500LfcmStaticType
                    INTEGER,
                cdx6500LfcmStaticValue
                    INTEGER,
                cdx6500LfcmStaticIncProtLinkAct
                    DisplayString,
                cdx6500LfcmStaticOutProtLinkAct
                    DisplayString,
                cdx6500LfcmStaticIncProtList
                    DisplayString,
                cdx6500LfcmStaticOutProtList
                    DisplayString,
                cdx6500LfcmStaticValue1
                    INTEGER,
                cdx6500LfcmStaticValue2
                    INTEGER
                }
    
        cdx6500LfcmStaticProtEntryNumber OBJECT-TYPE
            SYNTAX INTEGER
            ACCESS read-only
            STATUS mandatory
            DESCRIPTION
                "The number of the table entry corresponding to
                 the Protocol Type that is subject to Filtering
                 Action.  The Entry Number ranger is 1 - 100"
        ::= { cdx6500PCTPortStaticProtEntry 1 }
    
        cdx6500LfcmStaticType OBJECT-TYPE
            SYNTAX INTEGER {
                    dsap  (0),
                    snap  (1),
                    eType (2),
                    newvalDsap (50)
                    }
            ACCESS read-only
            STATUS mandatory
            DESCRIPTION
                "Protocol Type indicates  what type of protocol is
                 involved in the frame.
                 dsap:   The Protocol Value to be filtered/forwarded
                         is the Destination SAP of the 802.2 LLC Protocol.
                 snap:   The Protocol Value to be filtered/forwarded
                         is the SNAP header which identifies the OUI
                         and Protocol type.
                 eType:  The Protocol Value to be filtered/forwarded
                         is defined as the protocol ID of Ethernet
                         type frame.
                 newvalDsap : same functionality as 'dsap', new enumeration
                         introduced for RFC1155 compatibility."
        ::= { cdx6500PCTPortStaticProtEntry 2 }
    
        cdx6500LfcmStaticValue OBJECT-TYPE
            SYNTAX INTEGER
            ACCESS read-only
            STATUS mandatory
            DESCRIPTION
                "The protocol value indicates the value of the
                 protocol that will be filtered or forwarded."
        ::= { cdx6500PCTPortStaticProtEntry 3 }
    
        cdx6500LfcmStaticIncProtLinkAct OBJECT-TYPE
            SYNTAX DisplayString (SIZE(4..9))
            ACCESS read-only
            STATUS mandatory
            DESCRIPTION
                "PASS      = Pass all. If this value is used,
                             incoming frames with the specified
                             protocol value will be passed on all
                             links. All other protocols will be
                             blocked on incoming links. (See User's Manual).
                 BLOCK     = Block all.  If this value is used,
                             incoming frames with the specified
                             protocol value will be blocked on all
                             links. All other protocols will be
                             passed on incoming links. (See User's Manual).
                 PASSLIST  = Pass List.
                             Links in the list will pass the frame.
                             Links not in this list will block
                             the frame. An empty list means all
                             links will block. (See User's Manual).
                 BLOCKLIST = Block List.
                             Links in the list will block the frame.
                             Links not in this list will pass
                             the frame. An empty list will mean
                             all links will pass. (See User's Manual)."
        ::= { cdx6500PCTPortStaticProtEntry 4 }
    
        cdx6500LfcmStaticOutProtLinkAct OBJECT-TYPE
            SYNTAX DisplayString (SIZE(4..9))
            ACCESS read-only
            STATUS mandatory
            DESCRIPTION
                "PASS      = Pass all.  If this value is used, outgoing
                             frames with the specified protocol value
                             will be passed on all links. All other 
                             protocols will be blocked on outgoing links. 
                             (See User's Manual).
                 BLOCK     = Block all.  If this value is used, outgoing
                             frames with the specified protocol value will
                             be blocked on all links. All other protocols
                             will be passed on outgoing links.
                             (See User's Manual).
                 PASSLIST  = Pass List.
                             Links in this list will pass the frame. Links
                             not in this list will block the frame. An empty
                             list means all links will block.
                             (See User's Manual).
                 BLOCKLIST = Block List.
                             Links in this list will block the frame. Links
                             not in this list will pass the frame. An empty
                             list will mean all links will pass.
                             (See User's Manual)."
        ::= { cdx6500PCTPortStaticProtEntry 5 }

        cdx6500LfcmStaticIncProtList OBJECT-TYPE
            SYNTAX DisplayString
            ACCESS read-only
            STATUS mandatory
            DESCRIPTION
                "The individual numbers correspond to the Links which will 
                 be filtered according to the preceding parameter:
                 PASSLIST  = the listed links will pass the frame and
                             unlisted links will block the frame. An
                             empty list means all links will block.
                 BLOCKLIST = the listed links will block the frame
                             and unlisted links will pass the frame. 
                             An empty list will mean all links will pass.
                 A range of link numbers can be entered, for example: 
                 1,6,8-12 indicates 1,6,8,9,10,11,12"
        ::= { cdx6500PCTPortStaticProtEntry 6 }

        cdx6500LfcmStaticOutProtList OBJECT-TYPE
            SYNTAX DisplayString
            ACCESS read-only
            STATUS mandatory
            DESCRIPTION
                "The individual numbers correspond to the Links which will
                 be filtered according to the preceding parameter:
                 PASSLIST  = the listed links will pass the frame and
                             unlisted links will block the frame. An
                             empty list means all links will block.
                 BLOCKLIST = the listed links will block the frame
                             and unlisted links will pass the frame. 
                             An empty list will mean all links will pass.
                 A range of link numbers can be entered, for example:
                 1,6,8-12 indicates 1,6,8,9,10,11,12"
        ::= { cdx6500PCTPortStaticProtEntry 7 }

        cdx6500LfcmStaticValue1 OBJECT-TYPE
            SYNTAX INTEGER
            ACCESS read-only
            STATUS mandatory
            DESCRIPTION
                "The protocol value indicates the value of the
                 protocol that will be filtered or forwarded."
        ::= { cdx6500PCTPortStaticProtEntry 8 }
    
        cdx6500LfcmStaticValue2 OBJECT-TYPE
            SYNTAX INTEGER
            ACCESS read-only
            STATUS mandatory
            DESCRIPTION
                "The protocol value indicates the value of the
                 protocol that will be filtered or forwarded."
        ::= { cdx6500PCTPortStaticProtEntry 9 }


        --
        -- The cdx6500 dot1dSr Link group
        --
        -- Configurables - Table
        --
    
        cdx6500PCTSrLinkTable OBJECT-TYPE
            SYNTAX SEQUENCE OF Cdx6500PCTSrLinkEntry
            ACCESS not-accessible
            STATUS mandatory
            DESCRIPTION
                "A table that contains configuration information about every
                 WAN Bridge Link that is associated with this source route
                 bridge."
        ::= { cdx6500PCTBridgeGroup 3 }
    
        cdx6500PCTSrLinkEntry OBJECT-TYPE
            SYNTAX Cdx6500PCTSrLinkEntry
            ACCESS not-accessible
            STATUS mandatory
            DESCRIPTION
                "A list of information for each WAN Bridge Link of a source
                 route bridge."
            INDEX { cdx6500LfcmSrLink } 
        ::= { cdx6500PCTSrLinkTable 1 }
    
        Cdx6500PCTSrLinkEntry ::=
            SEQUENCE {
                cdx6500LfcmSrLink
                    INTEGER,
                cdx6500LfcmSrLinkHopCount
                    INTEGER,
                cdx6500LfcmSrLinkBridgeNum
                    INTEGER,
                cdx6500LfcmSrLinkTargetSegment                
                    INTEGER,
                cdx6500LfcmSrLinkLargestFrame
                    INTEGER
                }
    
        cdx6500LfcmSrLink OBJECT-TYPE
            SYNTAX INTEGER
            ACCESS read-only
            STATUS mandatory
            DESCRIPTION
                "The link number of the WAN Bridge Linkfor which
                 this entry contains Source Route management information."
        ::= { cdx6500PCTSrLinkEntry 1 }
    
        cdx6500LfcmSrLinkHopCount OBJECT-TYPE
            SYNTAX INTEGER
            ACCESS read-only
            STATUS mandatory
            DESCRIPTION
                "The maximum number of routing descriptors allowed
                 in an All Paths or Spanning Tree Explorer frames."
        ::= { cdx6500PCTSrLinkEntry 2 }
    
        cdx6500LfcmSrLinkBridgeNum OBJECT-TYPE
            SYNTAX INTEGER
            ACCESS read-only
            STATUS mandatory
            DESCRIPTION
                "A bridge number uniquely identifies a bridge when
                 more than one bridge is used to span the same two
                 segments.  Current source routing protocols limit
                 this value to the range: 0 through 15. A value of
                 65535 signifies that no bridge number is assigned
                 to this bridge."
        ::= { cdx6500PCTSrLinkEntry 3 }
    
        cdx6500LfcmSrLinkTargetSegment OBJECT-TYPE
            SYNTAX INTEGER
            ACCESS read-only
            STATUS mandatory
            DESCRIPTION
                "The segment number that corresponds to the target
                 segment this port is considered to be connected to
                 by the bridge.  Current source routing protocols
                 limit this value to the range: 0 through 4095. A
                 value of 65535 signifies that no target segment is
                 assigned to this port."
        ::= { cdx6500PCTSrLinkEntry 4 }
    
        cdx6500LfcmSrLinkLargestFrame OBJECT-TYPE
            SYNTAX INTEGER
            ACCESS read-only
            STATUS mandatory
            DESCRIPTION
                "The maximum size of the INFO field (LLC and
                 above) that this port can send/receive.  It does
                 not include any MAC level (framing) octets.  The
                 value of this object is used by this bridge to
                 determine whether a modification of the
                 LargestFrame field of the Routing Control field
                 of the Routing Information Field is necessary.
                 Valid values as defined by the 802.5 source routing
                 bridging specification are 516, 1500, 2052, 4472, 
                 8144, 11407, 17800, and 65535 octets.  Behavior of
                 the WAN Bridge LINK when an illegal value is written
                 is implementation specific.  It is recommended that
                 a reasonable legal value be chosen."
        ::= { cdx6500PCTSrLinkEntry 5 }

        --
        -- The cdx6500 dot1dStatic Link group
        -- The Link Static (Destination-Address Filtering) Database
        --
        -- dot1dStatic Link Configurables - Table
        --
    
        cdx6500PCTStaticLinkTable OBJECT-TYPE
            SYNTAX SEQUENCE OF Cdx6500PCTStaticLinkEntry
            ACCESS not-accessible
            STATUS mandatory
            DESCRIPTION
                "A table containing filtering information
                 configured into the bridge by (local or network)
                 management specifying the set of WAN Bridge Links to which
                 frames received from specific links and containing
                 specific destination addresses are allowed to be
                 forwarded. The value of zero in this table as the
                 WAN Bridge Link from which frames with a specific
                 destination address are received, is used to
                 specify all links for which there is no specific
                 entry in this table for that particular
                 destination address.  Entries are valid for
                 unicast and for group/broadcast addresses."
            REFERENCE
                 "P802.1d/D9, July 14, 1989: Section 6.7.2"
        ::= { cdx6500PCTBridgeGroup 4 }
    
        cdx6500PCTStaticLinkEntry OBJECT-TYPE
            SYNTAX Cdx6500PCTStaticLinkEntry
            ACCESS not-accessible
            STATUS mandatory
            DESCRIPTION
                "Filtering information configured into the bridge
                 by (local or network) management specifying the
                 set of WAN Bridge Links to which frames received from a
                 specific bridge link and containing a specific
                 destination address are allowed to be forwarded."
            REFERENCE
                   "P802.1d/D9, July 14,1989: Section 6.7.2"
            INDEX   { cdx6500LfcmLinkStaticAddress,
                      cdx6500LfcmLinkStaticReceivePort }
        ::= { cdx6500PCTStaticLinkTable 1 }
    
        Cdx6500PCTStaticLinkEntry ::=
            SEQUENCE {
                cdx6500LfcmLinkStaticAddress
                    MacAddress,
                cdx6500LfcmLinkStaticReceivePort
                    INTEGER,
                cdx6500LfcmLinkStaticAllowToGoTo
                    OCTET STRING,
                cdx6500LfcmLinkStaticStatus
                    INTEGER
                }
     
        cdx6500LfcmLinkStaticAddress OBJECT-TYPE
            SYNTAX MacAddress
            ACCESS read-only
            STATUS mandatory
            DESCRIPTION
                "The destination MAC address in a frame to which
                 this entry's filtering information applies.  This
                 object can take the value of a unicast address, a
                 group address or the broadcast address."
            REFERENCE
                 "P802.1d/D9, July 14, 1989: Section 3.9.1, 3.9.2"
        ::= { cdx6500PCTStaticLinkEntry 1 }
    
        cdx6500LfcmLinkStaticReceivePort OBJECT-TYPE
            SYNTAX INTEGER
            ACCESS read-only
            STATUS mandatory
            DESCRIPTION
                "Either the value '0', or the WAN Bridge Link of the
                 link from which a frame must be received in order
                 for this entry's filtering information to apply.
                 A value of zero indicates that this entry applies
                 on all bridge links of the bridge for which there is no
                 other applicable entry."
        ::= { cdx6500PCTStaticLinkEntry 2 }
    
        cdx6500LfcmLinkStaticAllowToGoTo OBJECT-TYPE
            SYNTAX OCTET STRING
            ACCESS read-only
            STATUS mandatory
            DESCRIPTION
                "The set of WAN Bridge Links to which frames received from a
                 specific port and destined for a specific MAC
                 address, are allowed to be forwarded.  Each octet
                 within the value of this object specifies a set of
                 eight bridge links, with the first octet specifying links
                 1 through 8, the second octet specifying links 9
                 through 16, etc.  Within each octet, the most
                 significant bit represents the lowest numbered
                 link, and the least significant bit represents the
                 highest numbered link.  Thus, each link of the
                 bridge is represented by a single bit within the
                 value of this object.  If that bit has a value of
                 '1' then that link is included in the set of
                 links; the link is not included if its bit has a
                 value of '0'.  (Note that the setting of the bit
                 corresponding to the link from which a frame is
                 received is irrelevant.)"
        ::= { cdx6500PCTStaticLinkEntry 3 }
    
        cdx6500LfcmLinkStaticStatus OBJECT-TYPE
            SYNTAX INTEGER {
                    other           (1),
                    invalid         (2),
                    permanent       (3),
                    deleteOnReset   (4),
                    deleteOnTimeout (5)
                    }
            ACCESS read-only
            STATUS mandatory
            DESCRIPTION
                "This object indicates the status of this entry.
                 other           - this entry is currently in use but
                                   the conditions under which it will
                                   remain so are different from each of the
                                   following values.
                 invalid         - writing this value to the object
                                   removes the corresponding entry.
                 permanent       - this entry is currently in use
                                   and will remain so after the next reset
                                   of the bridge.
                 deleteOnReset   - this entry is currently in
                                   use and will remain so until the next
                                   reset of the bridge.
                 deleteOnTimeout - this entry is currently
                                   in use and will remain so until it is
                                   aged out."
        ::= { cdx6500PCTStaticLinkEntry 4 }

        --
        -- Local Termination(LTRM)
        --
        -- Station Table - Configurables - Table
        --
    
        cdx6500PCTLtrmStnTable OBJECT-TYPE
            SYNTAX SEQUENCE OF Cdx6500PCTLtrmStnEntry
            ACCESS not-accessible
            STATUS mandatory
            DESCRIPTION
                "This table contains configuration for Local
                 Termination Station Table."
        ::= { cdx6500PCTBridgeGroup 5 }

        cdx6500PCTLtrmStnEntry OBJECT-TYPE
            SYNTAX Cdx6500PCTLtrmStnEntry
            ACCESS not-accessible
            STATUS mandatory
            DESCRIPTION
                "A list of parameters for the Station Table."
            INDEX { cdx6500LfcmLtrmStnEntryNumber }
        ::= { cdx6500PCTLtrmStnTable 1 }
    
        Cdx6500PCTLtrmStnEntry ::= 
            SEQUENCE {
                cdx6500LfcmLtrmStnEntryNumber
                    INTEGER,
                cdx6500LfcmLtrmMacAddress
                    MacAddress,
                cdx6500LfcmLtrmSap
                    INTEGER,
                cdx6500LfcmLtrmProfileName
                    INTEGER
                }
    
        cdx6500LfcmLtrmStnEntryNumber OBJECT-TYPE
            SYNTAX INTEGER
            ACCESS read-only
            STATUS mandatory
            DESCRIPTION
                "The Station Number (1 - 64) that is to be configured."
        ::= { cdx6500PCTLtrmStnEntry 1 }
    
        cdx6500LfcmLtrmMacAddress OBJECT-TYPE
            SYNTAX MacAddress
            ACCESS read-only
            STATUS mandatory
            DESCRIPTION
                "This MAC address must match the Source MAC
                 address of the frame received from the LAN
                 port or destination MAC address of a frame
                 received from WAN for the session to be
                 spoofed."
        ::= { cdx6500PCTLtrmStnEntry 2 }

        cdx6500LfcmLtrmSap OBJECT-TYPE
            SYNTAX INTEGER
            ACCESS read-only
            STATUS mandatory
            DESCRIPTION
                "This SAP must match the Source SAP of the
                 frame received from the LAN port or
                 destination SAP of a frame received from
                 WAN for the session to be spoofed."
        ::= { cdx6500PCTLtrmStnEntry 3 }
    
        cdx6500LfcmLtrmProfileName OBJECT-TYPE
            SYNTAX INTEGER
            ACCESS read-only
            STATUS mandatory
            DESCRIPTION
                "Local Term Station Table reference this
                 parameter for the T1, T2, Ti, N2, N3
                 and TW values."
        ::= { cdx6500PCTLtrmStnEntry 4 }

        --
        -- Profile Table Configurables - Table
        --
    
        cdx6500PCTLtrmProfTable OBJECT-TYPE
            SYNTAX SEQUENCE OF Cdx6500PCTLtrmProfEntry
            ACCESS not-accessible
            STATUS mandatory
            DESCRIPTION
                "This table contains configuration for Local
                 Termination Profile Table."
        ::= { cdx6500PCTBridgeGroup 6 }
    
        cdx6500PCTLtrmProfEntry OBJECT-TYPE
            SYNTAX Cdx6500PCTLtrmProfEntry
            ACCESS not-accessible
            STATUS mandatory
            DESCRIPTION
                "A list of parameters for the Profile Table."
            INDEX { cdx6500LfcmLtrmProfEntryNumber }
        ::= { cdx6500PCTLtrmProfTable 1 }
    
        Cdx6500PCTLtrmProfEntry ::= 
            SEQUENCE {
                cdx6500LfcmLtrmProfEntryNumber
                    INTEGER,
                cdx6500LfcmLtrmProfLlcName
                    DisplayString,
                cdx6500LfcmLtrmProfTimeout1
                    INTEGER,
                cdx6500LfcmLtrmProfTimeout2
                    INTEGER,
                cdx6500LfcmLtrmProfTimeout3
                    INTEGER,
                cdx6500LfcmLtrmProfN2
                    INTEGER,
                cdx6500LfcmLtrmProfN3
                    INTEGER,
                cdx6500LfcmLtrmProfTxWindowsize
                    INTEGER
                }
    
        cdx6500LfcmLtrmProfEntryNumber OBJECT-TYPE
            SYNTAX INTEGER
            ACCESS read-only
            STATUS mandatory
            DESCRIPTION
                "The Profile Number (1 - 8) that is to be configured."
        ::= { cdx6500PCTLtrmProfEntry 1 }
    
        cdx6500LfcmLtrmProfLlcName OBJECT-TYPE
            SYNTAX DisplayString
            ACCESS read-only
            STATUS mandatory
            DESCRIPTION
                "Local Term Station Table reference this
                 parameter for the T1, T2, Ti, N2, N3
                 and TW values."
        ::= { cdx6500PCTLtrmProfEntry 2 }
    
        cdx6500LfcmLtrmProfTimeout1 OBJECT-TYPE
            SYNTAX INTEGER
            ACCESS read-only
            STATUS mandatory
            DESCRIPTION
                "This Ack Timer is used by a station to detect
                 a failure of the remote station to acknowledge
                 an outstanding I frame or supervisory frame with
                 poll bit set to 1. Time is in seconds."
        ::= { cdx6500PCTLtrmProfEntry 3 }
    
        cdx6500LfcmLtrmProfTimeout2 OBJECT-TYPE
            SYNTAX INTEGER
            ACCESS read-only
            STATUS mandatory
            DESCRIPTION
                "The Receive Ack Timer is used by a station to
                 determine how long it will withhold acknowledgment
                 of a frame(s) from the remote station that require
                 acknowledgment. This is a method of reducing the
                 amount of acknowledgments generated by a link
                 station.  When this timer expires, the link station
                 should immediately send an acknowledgment for all
                 received frames not yet acknowledged. Time is in
                 tenths of seconds."
        ::= { cdx6500PCTLtrmProfEntry 4 }
    
        cdx6500LfcmLtrmProfTimeout3 OBJECT-TYPE
            SYNTAX INTEGER
            ACCESS read-only
            STATUS mandatory
            DESCRIPTION
                "The Idle Timer is used by a station to detect an
                 inoperative condition of the Logical Link. This
                 timer is started when the link becomes idle (no
                 data to pass and no outstanding acknowledgments)
                 and if it expires, the station sends a supervisory
                 frame with the poll bit set to 1. Time is in
                 seconds."
        ::= { cdx6500PCTLtrmProfEntry 5 }
    
        cdx6500LfcmLtrmProfN2 OBJECT-TYPE
            SYNTAX INTEGER
            ACCESS read-only
            STATUS mandatory
            DESCRIPTION
                "This count defines the number of times an I frame
                 or supervisory frame with poll bit set to 1, will
                 be transmitted, due to T1 acknowledgment time-out,
                 before the Logical Link will be declared down
                 (inoperative)."
        ::= { cdx6500PCTLtrmProfEntry 6 }
    
        cdx6500LfcmLtrmProfN3 OBJECT-TYPE
            SYNTAX INTEGER
            ACCESS read-only
            STATUS mandatory
            DESCRIPTION
                "The receive count is used in conjunction with T2
                 to reduce the amount of acknowledgments a station
                 generates. The receive count is used by a station
                 to determine how many frames it will receive from
                 the remote station while withholding acknowledgment
                 of these frames. This is a method of reducing the
                 amount of acknowledgments generated by a link
                 station. When this count expires, the link station
                 should immediately send an acknowledgment for all
                 received frames not yet acknowledged."
        ::= { cdx6500PCTLtrmProfEntry 7 }

        cdx6500LfcmLtrmProfTxWindowsize OBJECT-TYPE
            SYNTAX INTEGER
            ACCESS read-only
            STATUS mandatory
            DESCRIPTION
                "Transmit Window Size is the maximum number of I
                 frames a station may transmit without acknowledgment."
        ::= { cdx6500PCTLtrmProfEntry 8 }


        -- LFCM Single Objects - Configs

        cdx6500dot1dBridgeCfgGroup OBJECT IDENTIFIER 
            ::= { cdx6500PCTBridgeGroup 7 }

        cdx6500dot1dBasePortCfg OBJECT IDENTIFIER 
            ::= { cdx6500dot1dBridgeCfgGroup 1 }

        --
        -- Configuration
        --
        -- Base LAN Port
        --

        cdx6500LfcmBridgeLfMode OBJECT-TYPE
            SYNTAX INTEGER
            ACCESS read-write
            STATUS deprecated
            DESCRIPTION
                "The maximum size of the INFO field that this Bridge Link
                 can send and receive. The minimum value of this parameter or 
                 of adjacent Bridge Link or values of Largest Frame Size of
                 bridge wide parameter is used to determine whether
                 a modification of the Routing Control field of RIF is 
                 necessary.
                 Deprecated object without replacement"
        ::= { cdx6500dot1dBasePortCfg 1 }

        cdx6500LfcmWanDataPri OBJECT-TYPE
            SYNTAX INTEGER {
                    low       (0),
                    med       (2),
                    high      (4),
                    newvalLow (50)
                    }
            ACCESS read-write
            STATUS mandatory
            DESCRIPTION
                "This parameter specifies the transmission
                 priority of the bridged data over WAN.
                 newvalLow : same functionality as 'low', new enumeration
                 added for RFC1155 compatibility."
        ::= { cdx6500dot1dBasePortCfg 2 }
    
        cdx6500LfcmLearnOnlyPeriod OBJECT-TYPE
            SYNTAX INTEGER
            ACCESS read-write
            STATUS mandatory
            DESCRIPTION
                "This is the time in seconds that a bridge will be prevented 
                 from forwarding frames after the Forwarding is cleared due 
                 to node boot."
        ::= { cdx6500dot1dBasePortCfg 3 }

        cdx6500LfcmLssRingNumber OBJECT-TYPE
            SYNTAX INTEGER
            ACCESS read-write
            STATUS mandatory
            DESCRIPTION
                "This is a virtual ring number that is used by the 6500 
                 whenever a virtual ring definition is required: to support 
                 the LSS in its path trace function and in IP tunnelling for
                 token ring networks."
        ::= { cdx6500dot1dBasePortCfg 4 }

        cdx6500LfcmBridgedProtocols OBJECT-TYPE
            SYNTAX INTEGER {
                    none       (0),
                    ip         (1),
                    ipx        (2),
                    ipIpx      (3),
                    newvalNone (50)
                    }
            ACCESS read-write
            STATUS mandatory
            DESCRIPTION
                "This parameter specifies the routable protocols
                 that are allowed to be bridged.
                 newvalNone : same functionality as 'none', new enumeration
                 added for RFC1155 compatibillity."
        ::= { cdx6500dot1dBasePortCfg 5 }

        cdx6500LfcmMaxBridgeLinks OBJECT-TYPE
            SYNTAX INTEGER (1..65535)
            ACCESS read-only
            STATUS mandatory
            DESCRIPTION
                "This parameter specifies the maximum number of
                 bridge links that can be configured."
        ::= { cdx6500dot1dBasePortCfg 6 }

        cdx6500dot1dStpPortCfg OBJECT IDENTIFIER 
            ::= { cdx6500dot1dBridgeCfgGroup 2 }

        --
        -- The cdx6500 dot1dStp Port group
        --
        -- STP Port Configurables

        cdx6500LfcmStpControl OBJECT-TYPE
            SYNTAX INTEGER {
                    auto       (0),
                    man        (1),
                    newvalAuto (50)
                    }
            ACCESS read-only
            STATUS mandatory
            DESCRIPTION
                "auto: This bridge participates in STP and
                       automatically calculates the STE 
                       (Single Route Broadcast) frame path.
                 man : The spanning tree is manually configured
                       Configure Bridge Link parameter.
                 newvalAuto : same functionality as 'auto', new enumeration
                       added for RFC1155 compatibility."
        ::= { cdx6500dot1dStpPortCfg 1 }

        cdx6500LfcmStpBadHelloThreshold OBJECT-TYPE
            SYNTAX INTEGER
            ACCESS read-only
            STATUS mandatory
            DESCRIPTION
                "A Bad Hello counter is incremented when HELLO PDU is 
                 received while the STPE Control parameter is configured to 
                 MAN. An event (report) is generated when the counter exceeds
                 the value of this parameter. The event will be generated
                 only once during the Bad Hello Time."
        ::= { cdx6500dot1dStpPortCfg 2 }

        cdx6500LfcmStpBadHelloTimeout OBJECT-TYPE
            SYNTAX INTEGER
            ACCESS read-only
            STATUS mandatory
            DESCRIPTION
                "This is a timeout value in minute. On 
                 timeout the Bad Hello counter is reset."
        ::= { cdx6500dot1dStpPortCfg 3 }

        cdx6500LtrmCfg OBJECT IDENTIFIER ::= { cdx6500dot1dBridgeCfgGroup 3 }
    
        --
        --  WAN Parameters Configurables
        --
    
        cdx6500LfcmLtrmWanTimeout1 OBJECT-TYPE
            SYNTAX INTEGER
            ACCESS read-only
            STATUS mandatory
            DESCRIPTION
                "This Ack Timer is used by a station to detect
                 a failure of the remote station to acknowledge
                 an outstanding I frame or supervisory frame with
                 poll bit set to 1. Time is in seconds."
        ::= { cdx6500LtrmCfg 1 }
    
        cdx6500LfcmLtrmWanTimeout2 OBJECT-TYPE
            SYNTAX INTEGER
            ACCESS read-only
            STATUS mandatory
            DESCRIPTION
                "The Receive Ack Timer is used by a station to
                 determine how long it will withhold acknowledgment
                 of a frame(s) from the remote station that require
                 acknowledgment. This is a method of reducing the
                 amount of acknowledgments generated by a link
                 station.  When this timer expires, the link station
                 should immediately send an acknowledgment for all
                 received frames not yet acknowledged. Time is in
                 tenths of seconds."
        ::= { cdx6500LtrmCfg 2 }
    
        cdx6500LfcmLtrmWanTimeout3 OBJECT-TYPE
            SYNTAX INTEGER
            ACCESS read-only
            STATUS mandatory
            DESCRIPTION
                "The Idle Timer is used by a station to detect an
                 inoperative condition of the Logical Link. This
                 timer is started when the link becomes idle (no
                 data to pass and no outstanding acknowledgments)
                 and if it expires, the station sends a supervisory
                 frame with the poll bit set to 1. Time is in
                 seconds."
        ::= { cdx6500LtrmCfg 3 }
    
        cdx6500LfcmLtrmWanN2 OBJECT-TYPE
            SYNTAX INTEGER
            ACCESS read-only
            STATUS mandatory
            DESCRIPTION
                "This count defines the number of times an I frame
                 or supervisory frame with poll bit set to 1, will
                 be transmitted, due to T1 acknowledgment time-out,
                 before the Logical Link will be declared down
                 (inoperative)."
        ::= { cdx6500LtrmCfg 4 }
    
        cdx6500LfcmLtrmWanN3 OBJECT-TYPE
            SYNTAX INTEGER
            ACCESS read-only
            STATUS mandatory
            DESCRIPTION
                "The receive count is used in conjunction with T2
                 to reduce the amount of acknowledgments a station
                 generates. The receive count is used by a station
                 to determine how many frames it will receive from
                 the remote station while withholding acknowledgment
                 of these frames. This is a method of reducing the
                 amount of acknowledgments generated by a link
                 station. When this count expires, the link station
                 should immediately send an acknowledgment for all
                 received frames not yet acknowledged."
        ::= { cdx6500LtrmCfg 5 }
    
        cdx6500LfcmLtrmWanTxWindowSize OBJECT-TYPE
            SYNTAX INTEGER
            ACCESS read-only
            STATUS mandatory
            DESCRIPTION
                "Transmit Window Size is the maximum number of I
                 frames a station may transmit without acknowledgment."
        ::= { cdx6500LtrmCfg 6 }

        cdx6500LfcmBaseLlcLtrmDataPri OBJECT-TYPE
            SYNTAX INTEGER
            ACCESS read-only
            STATUS mandatory
            DESCRIPTION
                "This parameter specifies the transmission priority
                 of the LLC LT data over WAN."
        ::= { cdx6500LtrmCfg 7 }

        cdx6500LssCfg OBJECT IDENTIFIER ::= { cdx6500dot1dBridgeCfgGroup 4 }
    
        --
        --  LSS Configurables
        --
    
        cdx6500LfcmLssVirtualPortMacAddr OBJECT-TYPE
            SYNTAX MacAddress
            ACCESS read-only
            STATUS mandatory
            DESCRIPTION
                "Specifies the MAC address of the virtual LAN port
                 of the virtual ring. The entered value will be
                 replaced by the Burned In Address (BIA) if the LAN
                 hardware is present."
        ::= { cdx6500LssCfg 1 }
    
        cdx6500LfcmLssBridgeId OBJECT-TYPE
            SYNTAX INTEGER
            ACCESS read-only
            STATUS mandatory
            DESCRIPTION
                "This is the bridge ID of a virtual bridge and it
                 uniquely identifies a bridge when more than one
                 bridge is used to span the same two segments."
        ::= { cdx6500LssCfg 2 }
    
        cdx6500LfcmLssNotificationInter OBJECT-TYPE
            SYNTAX INTEGER
            ACCESS read-only
            STATUS mandatory
            DESCRIPTION
                "The Notification Interval Time
                 Deprecated object without replacement."
        ::= { cdx6500LssCfg 3 }
    
        cdx6500LfcmLssCalculationInter OBJECT-TYPE
            SYNTAX INTEGER
            ACCESS read-only
            STATUS deprecated
            DESCRIPTION
                "The Calculation Interval Time.
                 Deprecated object without replacement."
        ::= { cdx6500LssCfg 4 }

        cdx6500LfcmLssPathTraceCtrl OBJECT-TYPE
            SYNTAX INTEGER {
                    disable       (0),
                    enable        (1),
                    newvalDisable (50)
                    }
            ACCESS read-only
            STATUS mandatory
            DESCRIPTION
                "The value of this parameter specifies whether or
                 not the LBS is enabled to send the Path Trace
                 frames to the LAN Manager.
                 newvalDisable : same functionality as 'disable', new
                 enumeration added for RFC1155 compatibility."
        ::= { cdx6500LssCfg 5 }

        --
        -- The cdx6500 dot1dTp Port group
        --
        -- TP Port Configurables - Permanent Address Table
        --

        cdx6500PCTTbPermTable OBJECT-TYPE
            SYNTAX SEQUENCE OF Cdx6500PCTTbPermEntry
            ACCESS not-accessible
            STATUS mandatory
            DESCRIPTION
                "This table contains Permanent MAC Address
                 that are loaded into the Forwarding Table
                 after a table or node boot."
        ::= { cdx6500PCTBridgeGroup 8 }
    
        cdx6500PCTTbPermEntry OBJECT-TYPE
            SYNTAX Cdx6500PCTTbPermEntry
            ACCESS not-accessible
            STATUS mandatory
            DESCRIPTION
                "A list of the individual elements that make
                 the entries of the Permanent MAC Address table"
            INDEX { cdx6500LfcmTbEntry }
        ::= { cdx6500PCTTbPermTable 1 }
    
        Cdx6500PCTTbPermEntry ::= 
            SEQUENCE {
                cdx6500LfcmTbEntry
                    INTEGER,
                cdx6500LfcmTpPortLocalMacAddress
                    MacAddress,
                cdx6500LfcmTpPortBridgeLinkNums
                    INTEGER
                }
    
        cdx6500LfcmTbEntry OBJECT-TYPE
            SYNTAX INTEGER
            ACCESS read-write
            STATUS mandatory
            DESCRIPTION
                "The number of the table entry corresponding to
                 the MAC address used for Forwarding Action.
                 The Entry Number ranger is 1 - 8000"
        ::= { cdx6500PCTTbPermEntry 1 }

        cdx6500LfcmTpPortLocalMacAddress OBJECT-TYPE    
            SYNTAX MacAddress
            ACCESS read-write
            STATUS mandatory
            DESCRIPTION
                "MAC Address which is to be used for forwarding."
        ::= { cdx6500PCTTbPermEntry 2 }

        cdx6500LfcmTpPortBridgeLinkNums OBJECT-TYPE
            SYNTAX INTEGER
            ACCESS read-write
            STATUS mandatory
            DESCRIPTION
                "This is the bridge link to forward a frame
                 with the MAC Address which is the Forwarding Table"
        ::= { cdx6500PCTTbPermEntry 3 }

        --
        -- The cdx6500 dot1dBase Link group
        --
        -- Configuration - Table
        -- 
    
        cdx6500PCTdot1dBaseLinkTable OBJECT-TYPE
            SYNTAX SEQUENCE OF Cdx6500PCTdot1dBaseLinkEntry
            ACCESS not-accessible
            STATUS mandatory
            DESCRIPTION
                "This table contains WAN Bridge Link parameters,
                 one per Bridge Link."
        ::= { cdx6500PCTBridgeGroup 9 }
    
        cdx6500PCTdot1dBaseLinkEntry OBJECT-TYPE
            SYNTAX Cdx6500PCTdot1dBaseLinkEntry
            ACCESS not-accessible
            STATUS mandatory
            DESCRIPTION
                "A list of parameters for each WAN Bridge Link."
            INDEX { cdx6500LfcmBaseLinkIndex }
        ::= { cdx6500PCTdot1dBaseLinkTable 1 }
    
        Cdx6500PCTdot1dBaseLinkEntry ::=
            SEQUENCE {
                cdx6500LfcmBaseLinkIndex
                    INTEGER,
                cdx6500LfcmLinkType
                    DisplayString,
                cdx6500LfcmMacAddrFilterAction
                    INTEGER,
                cdx6500LfcmProtocolFilterAction
                    INTEGER,
                cdx6500LfcmStpLinkManState
                    INTEGER
                }

        cdx6500LfcmBaseLinkIndex OBJECT-TYPE
            SYNTAX INTEGER
            ACCESS read-only
            STATUS mandatory
            DESCRIPTION
                "This is the WAN Bridge Link number (5 - 36) 
                 that identifies the particular Bridge Link."
        ::= { cdx6500PCTdot1dBaseLinkEntry 1 }

        cdx6500LfcmLinkType OBJECT-TYPE
            SYNTAX DisplayString
            ACCESS read-only
            STATUS mandatory
            DESCRIPTION
                "This is the bridge type for links which connect to
                 WANs and defines the kind of bridging that will be
                 employed on the link: applies only to WAN Bridge,
                 Links number 5 to 36."
        ::= { cdx6500PCTdot1dBaseLinkEntry 2 }

        cdx6500LfcmMacAddrFilterAction OBJECT-TYPE
            SYNTAX INTEGER {
                    pass       (0),
                    block      (1),
                    none       (2),
                    newvalPass (50)
                    }
            ACCESS read-only
            STATUS mandatory
            DESCRIPTION
                "pass  = Pass all frames with MAC address not listed
                         in MAC Address Filter Table
                 block = Block all frames with MAC address not listed
                         in MAC Address Filter Table
                 none  = No MAC address filtering to be performed for
                         this link.
                 newvalPass = same action as 'pass', new enumeration
                 added for RFc1155 compatibility."
        ::= { cdx6500PCTdot1dBaseLinkEntry 3 }
    
        cdx6500LfcmProtocolFilterAction OBJECT-TYPE
            SYNTAX INTEGER {
                    pass       (0),
                    block      (1),
                    none       (2),
                    newvalPass (50)
                    }
            ACCESS read-only
            STATUS mandatory
            DESCRIPTION
                "pass  = Pass all frames with Protocol value not listed
                         in Protocol Filter Table
                 block = Block all frames with Protocol value not listed
                         in Protocol Filter Table
                 none  = No Protocol filtering to be performed for this
                         link.
                 newvalPass = same action as 'pass', new enumeration
                 added for RFc1155 compatibility."
        ::= { cdx6500PCTdot1dBaseLinkEntry 4 }

        cdx6500LfcmStpLinkManState OBJECT-TYPE
            SYNTAX INTEGER {
                    forward       (0),
                    block         (9),
                    newvalForward (50)
                    }
            ACCESS read-only
            STATUS mandatory
            DESCRIPTION
                "Value of this parameters specifies whether to forward or
                 block a STE (or Single Route Broadcast ) frame while the
                 STPE Control parameter is configured to MAN.
                 newvalForward : same functionality as 'forward', new
                 enumeration added for RFC1155 compatibility."
        ::= { cdx6500PCTdot1dBaseLinkEntry 5 }

        --
        -- The cdx6500 Base Port group
        --
        -- Base Port Configurables
        --

        cdx6500PCTBasePortTable OBJECT-TYPE
            SYNTAX SEQUENCE OF Cdx6500PCTBasePortEntry
            ACCESS not-accessible
            STATUS mandatory
            DESCRIPTION
                "This table contains Configurables for the Base Port."
        ::= { cdx6500PCTBridgeGroup 10 }
    
        cdx6500PCTBasePortEntry OBJECT-TYPE
            SYNTAX Cdx6500PCTBasePortEntry
            ACCESS not-accessible
            STATUS mandatory
            DESCRIPTION
                "A list of the individual elements that make
                 the Base Port Configurables."
            INDEX { cdx6500LfcmBasePortIndex }
        ::= { cdx6500PCTBasePortTable 1 }
    
        Cdx6500PCTBasePortEntry ::= 
            SEQUENCE {
                cdx6500LfcmBasePortIndex
                    INTEGER,
                cdx6500LfcmPortAddrFiltAction
                    INTEGER,
                cdx6500LfcmPortProtFiltAction
                    INTEGER,
                cdx6500LfcmPortStptManState
                    INTEGER
                }
    
        cdx6500LfcmBasePortIndex OBJECT-TYPE
            SYNTAX INTEGER
            ACCESS read-write
            STATUS mandatory
            DESCRIPTION
                "The port number of the port for which this entry
                 contains bridge management information."
        ::= { cdx6500PCTBasePortEntry 1 }

        cdx6500LfcmPortAddrFiltAction OBJECT-TYPE
            SYNTAX INTEGER {
                    pass       (0),
                    block      (1),
                    none       (2),
                    newvalPass (50)
                    }
            ACCESS read-write
            STATUS mandatory
            DESCRIPTION
                "pass  = Pass all frames with MAC address not listed
                         in MAC Address Filter Table
                 block = Block all frames with MAC address not listed
                         in MAC Address Filter Table
                 none  = No MAC address filtering to be performed for
                         this link.
                 newvalPass = same functionality as 'pass', new enumeration
                 added for RFC1155 compatibility."
        ::= { cdx6500PCTBasePortEntry 2 }

        cdx6500LfcmPortProtFiltAction OBJECT-TYPE
            SYNTAX INTEGER {
                    pass       (0),
                    block      (1),
                    none       (2),
                    newvalPass (50)
                    }
            ACCESS read-write
            STATUS mandatory
            DESCRIPTION
                "pass  = Pass all frames with Protocol value not listed
                         in Protocol Filter Table
                 block = Block all frames with Protocol value not listed
                         in Protocol Filter Table
                 none  = No Protocol filtering to be performed for this
                         link.
                 newvalPass = same functionality as 'pass', new enumeration
                 added for RFC1155 compatibility."
        ::= { cdx6500PCTBasePortEntry 3 }

        cdx6500LfcmPortStptManState OBJECT-TYPE
            SYNTAX INTEGER {
                    forward       (0),
                    block         (9),
                    newvalForward (50)
                    }
            ACCESS  read-write
            STATUS  mandatory
            DESCRIPTION
                "Value of this parameters specifies whether to forward or
                 block a STE (or Single Route Broadcast ) frame while the
                 STPE Control parameter is configured to MAN.
                 newvalForward : same functionality as 'newvalForward', new
                 enumeration added for RFC1155 compatibility."
        ::= { cdx6500PCTBasePortEntry 4 }

        --
        -- The cdx6500 dot1dSr Port group
        --
        -- Statistics for SR Port - Table
        --

        cdx6500PSTSrPortTable OBJECT-TYPE
            SYNTAX SEQUENCE OF Cdx6500PSTSrPortEntry
            ACCESS not-accessible
            STATUS mandatory
            DESCRIPTION
                "A table that contains information about every
                 port that is associated with this source route bridge."
        ::= { cdx6500PSTBridgeGroup 1 }

        cdx6500PSTSrPortEntry OBJECT-TYPE
            SYNTAX Cdx6500PSTSrPortEntry
            ACCESS not-accessible
            STATUS mandatory
            DESCRIPTION
                "A list of information for each port of a source
                 route bridge."
            INDEX { cdx6500LfcmSrPortIfIndex  }
        ::= { cdx6500PSTSrPortTable 1 }

        Cdx6500PSTSrPortEntry ::=
            SEQUENCE {
                cdx6500LfcmSrPortIfIndex
                    INTEGER,
                cdx6500LfcmSrPortFramesRx
                    Counter,
                cdx6500LfcmSrPortFramesTx
                    Counter,
                cdx6500LfcmSrPortRingNumber
                    INTEGER
                }

        cdx6500LfcmSrPortIfIndex OBJECT-TYPE
            SYNTAX INTEGER 
            ACCESS read-only
            STATUS mandatory
            DESCRIPTION
                "The port number of the port for which this entry
                 contains Source Route management information."
        ::= { cdx6500PSTSrPortEntry 1 }

        cdx6500LfcmSrPortFramesRx OBJECT-TYPE
            SYNTAX Counter 
            ACCESS read-only
            STATUS mandatory
            DESCRIPTION
                "The sum of ARE, STE and SRF frames received 
                 on this LAN link."
        ::= { cdx6500PSTSrPortEntry 2 }

        cdx6500LfcmSrPortFramesTx OBJECT-TYPE
            SYNTAX Counter 
            ACCESS read-only
            STATUS mandatory
            DESCRIPTION
                "The sum of ARE, STE and SRF frames transmitted
                 on this LAN link."
        ::= { cdx6500PSTSrPortEntry 3 }

        cdx6500LfcmSrPortRingNumber OBJECT-TYPE
            SYNTAX INTEGER 
            ACCESS read-only
            STATUS deprecated
            DESCRIPTION
                "The Next Ring number of the LAN link to which the bridge
                 route is bridging. This is the ring number to which the Codex
                 remote bridge half is attached.
                 Deprecated object without replacement"
        ::= { cdx6500PSTSrPortEntry 4 }

        --
        -- The cdx6500 dot1dTp Port group
        --
        -- TP Port Statistics - Table
        --

        cdx6500PSTTpPortTable OBJECT-TYPE
            SYNTAX SEQUENCE OF Cdx6500PSTTpPortEntry
            ACCESS not-accessible
            STATUS mandatory
            DESCRIPTION
                "A table that contains information about every
                 port that is associated with this transparent bridge."
        ::= { cdx6500PSTBridgeGroup 2 }

        cdx6500PSTTpPortEntry OBJECT-TYPE
            SYNTAX Cdx6500PSTTpPortEntry
            ACCESS not-accessible
            STATUS mandatory
            DESCRIPTION
                "A list of information for each port of a transparent bridge."
            INDEX { cdx6500LfcmTpPortIfIndex }
        ::= { cdx6500PSTTpPortTable 1 }

        Cdx6500PSTTpPortEntry ::=
            SEQUENCE {
                cdx6500LfcmTpPortIfIndex
                    INTEGER,
                cdx6500LfcmTpPortUnicastRx
                    Counter,
                cdx6500LfcmTpPortUnicastTx
                    Counter,
                cdx6500LfcmTpPortMulticastRx
                    Counter,
                cdx6500LfcmTpPortMulticastTx
                    Counter,
                cdx6500LfcmTpPortBroadcastRx
                    Counter,
                cdx6500LfcmTpPortBroadcastTx
                    Counter,
                cdx6500LfcmTpPortInboundDisc
                    Counter,
                cdx6500LfcmTpPortOutboundDisc
                    Counter,
                cdx6500LfcmTpPortULPInBoundDisc
                    Counter,
                cdx6500LfcmTpPortULPOutBoundDisc
                    Counter,
                cdx6500LfcmTpPortMLPInBoundDisc
                    Counter,
                cdx6500LfcmTpPortMLPOutBoundDisc
                    Counter
                }

        cdx6500LfcmTpPortIfIndex OBJECT-TYPE
            SYNTAX INTEGER
            ACCESS read-only
            STATUS mandatory
            DESCRIPTION
                "The port number of the port for which this entry
                 contains Transparent bridging management
                 information."
        ::= { cdx6500PSTTpPortEntry 1 }

        cdx6500LfcmTpPortUnicastRx OBJECT-TYPE
            SYNTAX Counter
            ACCESS read-only
            STATUS mandatory
            DESCRIPTION
                "The number of Unicast Frames received on
                 this LAN link."
        ::= { cdx6500PSTTpPortEntry 2 }

        cdx6500LfcmTpPortUnicastTx OBJECT-TYPE
            SYNTAX Counter
            ACCESS read-only
            STATUS mandatory
            DESCRIPTION
                "The number of Unicast Frames transmitted on
                 this LAN link."
        ::= { cdx6500PSTTpPortEntry 3 }

        cdx6500LfcmTpPortMulticastRx OBJECT-TYPE
            SYNTAX Counter
            ACCESS read-only
            STATUS mandatory
            DESCRIPTION
                "The number of Multicast Frames received on
                 this LAN link."
        ::= { cdx6500PSTTpPortEntry 4 }

        cdx6500LfcmTpPortMulticastTx OBJECT-TYPE
            SYNTAX Counter
            ACCESS read-only
            STATUS mandatory
            DESCRIPTION
                "The number of Multicast Frames transmitted on
                 this LAN link."
        ::= { cdx6500PSTTpPortEntry 5 }

        cdx6500LfcmTpPortBroadcastRx OBJECT-TYPE
            SYNTAX Counter
            ACCESS read-only
            STATUS mandatory
            DESCRIPTION
                "The number of Broadicast Frames received on
                 this LAN link."
        ::= { cdx6500PSTTpPortEntry 6 }

        cdx6500LfcmTpPortBroadcastTx OBJECT-TYPE
            SYNTAX Counter
            ACCESS read-only
            STATUS mandatory
            DESCRIPTION
                "The number of Broadicast Frames transmitted on
                 this LAN link."
        ::= { cdx6500PSTTpPortEntry 7 }

        cdx6500LfcmTpPortInboundDisc OBJECT-TYPE
            SYNTAX Counter
            ACCESS read-only
            STATUS mandatory
            DESCRIPTION
                "The number of frames discarded due to 
                 receive link state not in forwarding state ."
        ::= { cdx6500PSTTpPortEntry 8 }

        cdx6500LfcmTpPortOutboundDisc OBJECT-TYPE
            SYNTAX Counter
            ACCESS read-only
            STATUS mandatory
            DESCRIPTION
                "The number of frames discarded due to 
                 transmit link state not in forwarding state ."
        ::= { cdx6500PSTTpPortEntry 9 }

        cdx6500LfcmTpPortULPInBoundDisc OBJECT-TYPE
            SYNTAX Counter
            ACCESS read-only
            STATUS mandatory
            DESCRIPTION
                "The number of frames discarded due to 
                 Unicast Link Protect being set on the incoming link."
        ::= { cdx6500PSTTpPortEntry 10 }

        cdx6500LfcmTpPortULPOutBoundDisc OBJECT-TYPE
            SYNTAX Counter
            ACCESS read-only
            STATUS mandatory
            DESCRIPTION
                "The number of frames discarded due to 
                 Unicast Link Protect being set on the outgoing link."
        ::= { cdx6500PSTTpPortEntry 11 }

        cdx6500LfcmTpPortMLPInBoundDisc OBJECT-TYPE
            SYNTAX Counter
            ACCESS read-only
            STATUS mandatory
            DESCRIPTION
                "The number of frames discarded due to 
                 Multicast Link Protect being set on the incoming link."
        ::= { cdx6500PSTTpPortEntry 12 }

        cdx6500LfcmTpPortMLPOutBoundDisc OBJECT-TYPE
            SYNTAX Counter
            ACCESS read-only
            STATUS mandatory
            DESCRIPTION
                "The number of frames discarded due to 
                 Multicast Link Protect being set on the outgoing link."
        ::= { cdx6500PSTTpPortEntry 13 }

        --
        -- The Static (Destination-Address Filtering) Database - Port
        --
        -- Port Static Address and Protocol Filters Statistics - Table
        --

        cdx6500PSTPortFilterTable OBJECT-TYPE
            SYNTAX SEQUENCE OF Cdx6500PSTPortFilterEntry
            ACCESS not-accessible
            STATUS mandatory
            DESCRIPTION
                "This table contains MAC Address and
                 Protocol Filtering information."
        ::= { cdx6500PSTBridgeGroup 3 }

        cdx6500PSTPortFilterEntry OBJECT-TYPE
            SYNTAX Cdx6500PSTPortFilterEntry
            ACCESS not-accessible
            STATUS mandatory
            DESCRIPTION
                "A list of filtering statistcs for MAC
                 Address and Protocol filtering."
            INDEX { cdx6500LfcmPortFilterIfIndex }
        ::= { cdx6500PSTPortFilterTable 1 }

       Cdx6500PSTPortFilterEntry ::= 
           SEQUENCE {
               cdx6500LfcmPortFilterIfIndex
                   INTEGER,
               cdx6500LfcmPortFilSrcAddrInDisc
                   Counter,
               cdx6500LfcmPortFilSrcAddrOutDisc
                   Counter,
               cdx6500LfcmPortFilDestAddrInDisc
                   Counter,
               cdx6500LfcmPortFilDestAddrOutDisc
                   Counter,
               cdx6500LfcmPortFilProtInDisc
                   Counter,
               cdx6500LfcmPortFilProtOutDisc
                   Counter,
               cdx6500LfcmPortFilTotalInDisc
                   Counter,
               cdx6500LfcmPortFilTotalOutDisc
                   Counter
               }

        cdx6500LfcmPortFilterIfIndex OBJECT-TYPE
            SYNTAX INTEGER
            ACCESS read-only
            STATUS mandatory
            DESCRIPTION
                "The port number of the port for which this entry
                 contains filter information."
        ::= { cdx6500PSTPortFilterEntry 1 }

        cdx6500LfcmPortFilSrcAddrInDisc OBJECT-TYPE
            SYNTAX Counter
            ACCESS read-only
            STATUS mandatory
            DESCRIPTION
                "The number of inbound frames on this port that were 
                 not forwarded because of Source MAC Address filtering."
        ::= { cdx6500PSTPortFilterEntry 2 }

        cdx6500LfcmPortFilSrcAddrOutDisc OBJECT-TYPE
            SYNTAX Counter
            ACCESS read-only
            STATUS mandatory
            DESCRIPTION
                "The number of outbound frames on this port that were 
                 not forwarded because of Source MAC Address filtering."
        ::= { cdx6500PSTPortFilterEntry 3 }

        cdx6500LfcmPortFilDestAddrInDisc OBJECT-TYPE
            SYNTAX Counter
            ACCESS read-only
            STATUS mandatory
            DESCRIPTION
                "The number of inbound frames on this port that were 
                 not forwarded because of Destination MAC Address filtering."
        ::= { cdx6500PSTPortFilterEntry 4 }

        cdx6500LfcmPortFilDestAddrOutDisc OBJECT-TYPE
            SYNTAX Counter
            ACCESS read-only
            STATUS mandatory
            DESCRIPTION
                "The number of outbound frames on this port that were 
                 not forwarded because of Destination MAC Address filtering."
        ::= { cdx6500PSTPortFilterEntry 5 }

        cdx6500LfcmPortFilProtInDisc OBJECT-TYPE
            SYNTAX Counter
            ACCESS read-only
            STATUS mandatory
            DESCRIPTION
                "The number of inbound frames on this port that were not
                 forwarded because of Protocol filtering."
        ::= { cdx6500PSTPortFilterEntry 6 }

        cdx6500LfcmPortFilProtOutDisc OBJECT-TYPE
            SYNTAX Counter
            ACCESS read-only
            STATUS mandatory
            DESCRIPTION
                "The number of outbound frames on this port that were not 
                 forwarded because of Protocol filtering."
        ::= { cdx6500PSTPortFilterEntry 7 }

        cdx6500LfcmPortFilTotalInDisc OBJECT-TYPE
            SYNTAX Counter
            ACCESS read-only
            STATUS mandatory
            DESCRIPTION
                "The sum of Source MAC Address, Destination MAC Address, and
                 Protocol inbound frames on this port not forwarded because of
                 filtering."
        ::= { cdx6500PSTPortFilterEntry 8 }

        cdx6500LfcmPortFilTotalOutDisc OBJECT-TYPE
            SYNTAX Counter
            ACCESS read-only
            STATUS mandatory
            DESCRIPTION
                "The sum of Source MAC Address, Destination MAC Address, and
                 Protocol outbound frames on this port not forwarded because of
                 filtering."
        ::= { cdx6500PSTPortFilterEntry 9 }

        --
        -- dot1dBase Link Statistics - Table
        --

        cdx6500PSTBaseLinkTable OBJECT-TYPE
            SYNTAX SEQUENCE OF Cdx6500PSTBaseLinkEntry
            ACCESS not-accessible
            STATUS mandatory
            DESCRIPTION
                "This table contains statistics for the WAN Bridge Links."
        ::= { cdx6500PSTBridgeGroup 4 }

        cdx6500PSTBaseLinkEntry OBJECT-TYPE
            SYNTAX Cdx6500PSTBaseLinkEntry
            ACCESS not-accessible
            STATUS mandatory
            DESCRIPTION
                "A list of controls and statistics for each WAN Bridge Links."
            INDEX { cdx6500LfcmBaseLink }
        ::= { cdx6500PSTBaseLinkTable 1 }

       Cdx6500PSTBaseLinkEntry ::= 
           SEQUENCE {
               cdx6500LfcmBaseLink
                   INTEGER,
               cdx6500LfcmBaseLinkIfIndex
                   INTEGER,
               cdx6500LfcmBaseLinkCircuit
                   INTEGER,
               cdx6500LfcmBaseLinkBlStatus
                   INTEGER,
               cdx6500LfcmBaseLinkClearStats
                   INTEGER,
               cdx6500LfcmBaseLinkLastStatReset
                   DisplayString,
               cdx6500LfcmLinkBridgeLinkBoot
                   INTEGER,
               cdx6500LfcmLinkBlEnable
                   INTEGER,
               cdx6500LfcmLinkBlDisable
                   INTEGER,
               cdx6500LfcmCtrlsLinkSetLinkProt
                   INTEGER,
               cdx6500LfcmCtrlsLinkClrLinkProt
                   INTEGER,
               cdx6500LfcmCtrlsLinkSetMultProt
                   INTEGER,
               cdx6500LfcmCtrlsLinkClrMultProt
                   INTEGER
               }

        cdx6500LfcmBaseLink OBJECT-TYPE
            SYNTAX INTEGER
            ACCESS read-only
            STATUS mandatory
            DESCRIPTION
                "This object is the WAN Bridge Link number for 
                 control and statistics."
        ::= { cdx6500PSTBaseLinkEntry 1 }

        cdx6500LfcmBaseLinkIfIndex OBJECT-TYPE
            SYNTAX INTEGER
            ACCESS read-only
            STATUS mandatory
            DESCRIPTION
                "The value of the instance of the ifIndex object,
                 for the interface corresponding to this WAN Bridge Link.
                 Not Supported, will return zero"
        ::= { cdx6500PSTBaseLinkEntry 2 }

        cdx6500LfcmBaseLinkCircuit OBJECT-TYPE
            SYNTAX OBJECT IDENTIFIER
            ACCESS read-only
            STATUS mandatory
            DESCRIPTION
                "For a WAN Bridge Link which (potentially) has
                 the same value of dot1dBasePortIfIndex as another
                 WAN Bridge Link on the same bridge, this object
                 contains the name of an object instance unique
                 to this WAN Bridge Link.  For example, in the
                 case where multiple ports correspond one-to-one
                 with multiple X.25 virtual circuits, this value
                 might identify an (e.g., the first) object
                 instance associated with the X.25 virtual circuit
                 corresponding to this port.
                 For a WAN Bridge Link which has a unique value of
                 dot1dBasePortIfIndex, this object can have the
                 value { 0 0 }.
                 Not Supported, will return zero"
        ::= { cdx6500PSTBaseLinkEntry 3 }

        cdx6500LfcmBaseLinkBlStatus OBJECT-TYPE
            SYNTAX INTEGER {
                    configErr       (0),
                    swDisabled      (1),
                    userDisabled    (3),
                    congested       (4),
                    inactive        (5),
                    active          (6),
                    unconfig        (7),
                    newvalConfigErr (50)
                    }
            ACCESS read-only
            STATUS mandatory
            DESCRIPTION
                "The status of the WAN Brdige Link:
                 configErr    = Configuration error on link
                 swDisabled   = Physical errors on link
                 userDisabled = User shut down link
                 congested    = WAN congested condition
                 inactive     = Configured link - ready for use but not active
                 active       = Configured and active link
                 unconfig     = Not configured.
                 newvalConfigErr = same functionality as 'configErr', new
                 enumeration added for RFC1155 compatibility."
        ::= { cdx6500PSTBaseLinkEntry 4 }

        cdx6500LfcmBaseLinkClearStats OBJECT-TYPE
            SYNTAX INTEGER {
                    reset (1)
                    }
            ACCESS write-only
            STATUS mandatory
            DESCRIPTION
                "This is the command to reset the LAN port bridge statistics."
        ::= { cdx6500PSTBaseLinkEntry 5 }

        cdx6500LfcmBaseLinkLastStatReset OBJECT-TYPE
            SYNTAX DisplayString
            ACCESS read-only
            STATUS mandatory
            DESCRIPTION
                "The time of the last LAN port statistics reset."
        ::= { cdx6500PSTBaseLinkEntry 6 }

        cdx6500LfcmLinkBridgeLinkBoot OBJECT-TYPE
            SYNTAX INTEGER {
                    boot (1)
                    }
            ACCESS write-only
            STATUS mandatory
            DESCRIPTION
                "This is the command to boot the WAN Bridge Link parameters."
        ::= { cdx6500PSTBaseLinkEntry 7 }

        cdx6500LfcmLinkBlEnable OBJECT-TYPE
            SYNTAX INTEGER {
                    enable (1)
                    }
            ACCESS write-only
            STATUS mandatory
            DESCRIPTION
                "This is the command to Enable the WAN Bridge Link."
        ::= { cdx6500PSTBaseLinkEntry 8 }

        cdx6500LfcmLinkBlDisable OBJECT-TYPE
            SYNTAX INTEGER {
                    disable (1)
                    }
            ACCESS write-only
            STATUS mandatory
            DESCRIPTION
                "This is the command to Disable the WAN Bridge Link."
        ::= { cdx6500PSTBaseLinkEntry 9 }

        cdx6500LfcmCtrlsLinkSetLinkProt OBJECT-TYPE
            SYNTAX INTEGER {
                    setUcastProtection (1)
                    }
            ACCESS write-only
            STATUS mandatory
            DESCRIPTION
                "This is a command to set Unicast Protection
                 for the WAN Bridge Link."
        ::= { cdx6500PSTBaseLinkEntry 10 }
    
        cdx6500LfcmCtrlsLinkClrLinkProt OBJECT-TYPE
            SYNTAX INTEGER {
                    clearUcastProtection (1)
                    }
            ACCESS write-only
            STATUS mandatory
            DESCRIPTION
                "This is a command to clear Unicast Protection
                 for the WAN Bridge Link."
        ::= { cdx6500PSTBaseLinkEntry 11 }
    
        cdx6500LfcmCtrlsLinkSetMultProt OBJECT-TYPE
            SYNTAX INTEGER {
                    setMcastProtection (1)
                    }
            ACCESS write-only
            STATUS mandatory
            DESCRIPTION
                "This is a command to set Multicast Protection
                 for the WAN Bridge Link."
        ::= { cdx6500PSTBaseLinkEntry 12 }
    
        cdx6500LfcmCtrlsLinkClrMultProt OBJECT-TYPE
            SYNTAX INTEGER {
                    clearMcastProtection (1)
                    }
            ACCESS write-only
            STATUS mandatory
            DESCRIPTION
                "This is a command to clear Multicast Protection
                 for the WAN Bridge Link."
        ::= { cdx6500PSTBaseLinkEntry 13 }

        --
        -- dot1dSr Link group
        --
        -- Statistics - Table
        --

        cdx6500PSTSrLinkTable OBJECT-TYPE
            SYNTAX SEQUENCE OF Cdx6500PSTSrLinkEntry
            ACCESS not-accessible
            STATUS mandatory
            DESCRIPTION
                "A table that contains information about every
                 WAN Bridge Link that is associated with this
                 source route bridge."
        ::= { cdx6500PSTBridgeGroup 5 }

        cdx6500PSTSrLinkEntry OBJECT-TYPE
            SYNTAX Cdx6500PSTSrLinkEntry
            ACCESS not-accessible
            STATUS mandatory
            DESCRIPTION
                "A list of information for each WAN Bridge Link
                 of a source route bridge."
            INDEX { cdx6500LfcmSrLinkIfIndex  }
        ::= { cdx6500PSTSrLinkTable 1 }

        Cdx6500PSTSrLinkEntry ::=
            SEQUENCE {
                cdx6500LfcmSrLinkIfIndex
                    INTEGER,
                cdx6500LfcmSrLinkSteSpanMode
                    INTEGER,
                cdx6500LfcmSrLinkSpecInFrames
                    Counter,
                cdx6500LfcmSrLinkSpecOutFrames
                    Counter,
                cdx6500LfcmSrLinkApeInFrames
                    Counter,
                cdx6500LfcmSrLinkApeOutFrames
                    Counter,
                cdx6500LfcmSrLinkSteOutFrames
                    Counter,
                cdx6500LfcmSrLinkSteinFrames
                    Counter,
                cdx6500LfcmSrLinkSegMisDisc
                    Counter,
                cdx6500LfcmSrLinkDupSegDisc
                    Counter,
                cdx6500LfcmSrLinkHopCountExcDisc
                    Counter,
                cdx6500LfcmSrLinkTotalFramesRx
                    Counter,
                cdx6500LfcmSrLinkTotalFramesTx
                    Counter,
                cdx6500LfcmSrLinkNextRingNumber
                    INTEGER
                }

        cdx6500LfcmSrLinkIfIndex OBJECT-TYPE
            SYNTAX INTEGER
            ACCESS read-only
            STATUS mandatory
            DESCRIPTION
                "The bridge link number of the WAN Bridge Link
                 for which this entry contains Source Route
                 management information."
        ::= { cdx6500PSTSrLinkEntry 1 }

        cdx6500LfcmSrLinkSteSpanMode OBJECT-TYPE
            SYNTAX INTEGER {
                    deprecatedObj (1)
                    }
            ACCESS read-only
            STATUS mandatory
            DESCRIPTION
                "This object is no longer supported."
        ::= { cdx6500PSTSrLinkEntry 2 }

        cdx6500LfcmSrLinkSpecInFrames OBJECT-TYPE
            SYNTAX Counter
            ACCESS read-only
            STATUS mandatory
            DESCRIPTION
                "The number of specifically routed frames that
                 have been received from this bridge link's segment."
        ::= { cdx6500PSTSrLinkEntry 3 }

        cdx6500LfcmSrLinkSpecOutFrames OBJECT-TYPE
            SYNTAX Counter
            ACCESS read-only
            STATUS mandatory
            DESCRIPTION
                "The number of specifically routed frames that
                 this bridge link has transmitted on its segment."
        ::= { cdx6500PSTSrLinkEntry 4 }

        cdx6500LfcmSrLinkApeInFrames OBJECT-TYPE
            SYNTAX Counter
            ACCESS read-only
            STATUS mandatory
            DESCRIPTION
                "The number of all paths explorer frames that have
                 been received by this bridge link from its segment."
        ::= { cdx6500PSTSrLinkEntry 5 }

        cdx6500LfcmSrLinkApeOutFrames OBJECT-TYPE
            SYNTAX Counter
            ACCESS read-only
            STATUS mandatory
            DESCRIPTION
                "The number of all paths explorer frames that have
                 been transmitted by this bridge link on its segment."
        ::= { cdx6500PSTSrLinkEntry 6 }

        cdx6500LfcmSrLinkSteOutFrames OBJECT-TYPE
            SYNTAX Counter
            ACCESS read-only
            STATUS mandatory
            DESCRIPTION
                "The number of spanning tree explorer frames that
                 have been transmitted by this bridge link on its
                 segment."
        ::= { cdx6500PSTSrLinkEntry 7 }

        cdx6500LfcmSrLinkSteinFrames OBJECT-TYPE
            SYNTAX Counter
            ACCESS read-only
            STATUS mandatory
            DESCRIPTION
                "The number of spanning tree explorer frames that
                 have been received by this bridge Link from its segment."
        ::= { cdx6500PSTSrLinkEntry 8 }

        cdx6500LfcmSrLinkSegMisDisc OBJECT-TYPE
            SYNTAX Counter
            ACCESS read-only
            STATUS mandatory
            DESCRIPTION
                "The number of explorer frames that have been
                 discarded by this bridge link because the routing
                 descriptor field contained an invalid adjacent
                 segment value."
        ::= { cdx6500PSTSrLinkEntry 9 }

        cdx6500LfcmSrLinkDupSegDisc OBJECT-TYPE
            SYNTAX Counter
            ACCESS read-only
            STATUS mandatory
            DESCRIPTION
                "The number of frames that have been discarded by
                 this bridge link because the routing descriptor
                 field contained a duplicate segment identifier."
        ::= { cdx6500PSTSrLinkEntry 10 }

        cdx6500LfcmSrLinkHopCountExcDisc OBJECT-TYPE
            SYNTAX Counter
            ACCESS read-only
            STATUS mandatory
            DESCRIPTION
                "The number of explorer frames that have been
                 discarded by this bridge link because the Routing
                 Information Field has exceeded the maximum route
                 descriptor length."
        ::= { cdx6500PSTSrLinkEntry 11 }

        cdx6500LfcmSrLinkTotalFramesRx OBJECT-TYPE
            SYNTAX Counter
            ACCESS read-only
            STATUS mandatory
            DESCRIPTION
                "The sum of ARE, STE and SRF frames
                 received on this bridge link." 
        ::= { cdx6500PSTSrLinkEntry 12 }

        cdx6500LfcmSrLinkTotalFramesTx OBJECT-TYPE
            SYNTAX Counter
            ACCESS read-only
            STATUS mandatory
            DESCRIPTION
                "The sum of ARE, STE and SRF frames
                 transmitted on this bridge link." 
        ::= { cdx6500PSTSrLinkEntry 13 }

        cdx6500LfcmSrLinkNextRingNumber OBJECT-TYPE
            SYNTAX INTEGER
            ACCESS read-only
            STATUS mandatory
            DESCRIPTION
                "The Next Ring number of the WAN bridge link
                 to which the bridge route is bridging.  This
                 is the ring number to which the Codex
                 remote bridge halfis attached."
        ::= { cdx6500PSTSrLinkEntry 14 }

        --
        -- The cdx6500 dot1dTp Link group
        --
        -- dot1dTp Link group Statistics - Table
        --

        cdx6500PSTTpLinkTable OBJECT-TYPE
            SYNTAX SEQUENCE OF Cdx6500PSTTpLinkEntry
            ACCESS not-accessible
            STATUS mandatory
            DESCRIPTION
                "A table that contains information about every
                 bridge link that is associated with this transparent
                 bridge."
        ::= { cdx6500PSTBridgeGroup 6 }

        cdx6500PSTTpLinkEntry OBJECT-TYPE
            SYNTAX Cdx6500PSTTpLinkEntry
            ACCESS not-accessible
            STATUS mandatory
            DESCRIPTION
                "A list of information for each bridge link of a
                 transparent bridge."
            INDEX { cdx6500LfcmTpLink  }
        ::= { cdx6500PSTTpLinkTable 1 }

        Cdx6500PSTTpLinkEntry ::= 
            SEQUENCE {
                cdx6500LfcmTpLink
                    INTEGER,
                cdx6500LfcmTpLinkMaxInfo
                    INTEGER,
                cdx6500LfcmTpLinkInFrames
                    Counter,
                cdx6500LfcmTpLinkOutFrames
                    Counter,
                cdx6500LfcmTpLinkInDiscards
                    Counter,
                cdx6500LfcmTpLinkUnicastRx
                    Counter,
                cdx6500LfcmTpLinkUnicastTx
                    Counter,
                cdx6500LfcmTpLinkMulticastRx
                    Counter,
                cdx6500LfcmTpLinkMulticastTx
                    Counter,
                cdx6500LfcmTpLinkBroadcastRx
                    Counter,
                cdx6500LfcmTpLinkBroadcastTx
                    Counter,
                cdx6500LfcmTpLinkInBoundDisc
                    Counter,
                cdx6500LfcmTpLinkOutBoundDisc
                    Counter,
                cdx6500LfcmTpLinkULPInBoundDisc
                    Counter,
                cdx6500LfcmTpLinkULPOutBoundDisc
                    Counter,
                cdx6500LfcmTpLinkMLPInBoundDisc
                    Counter,
                cdx6500LfcmTpLinkMLPOutBoundDisc
                    Counter
                }

        cdx6500LfcmTpLink OBJECT-TYPE
            SYNTAX INTEGER
            ACCESS read-only
            STATUS mandatory
            DESCRIPTION
                "The bridge link number of the port for which this entry 
                 contains Transparent bridging management information."
        ::= { cdx6500PSTTpLinkEntry 1 }

        cdx6500LfcmTpLinkMaxInfo OBJECT-TYPE
            SYNTAX INTEGER
            ACCESS read-only
            STATUS mandatory
            DESCRIPTION
                "The maximum size of the INFO (non-MAC) field that
                 this port will receive or transmit."
        ::= { cdx6500PSTTpLinkEntry 2 }

        cdx6500LfcmTpLinkInFrames OBJECT-TYPE
            SYNTAX Counter
            ACCESS read-only
            STATUS mandatory
            DESCRIPTION
                "The number of frames that have been received by
                 this bridge link from its segment. Note that a
                 frame received on the interface corresponding
                 to this bridge link is only counted by this
                 object if and only if it is for a protocol
                 being processed by the local bridging function."
        ::= { cdx6500PSTTpLinkEntry 3 }

        cdx6500LfcmTpLinkOutFrames OBJECT-TYPE
            SYNTAX Counter
            ACCESS read-only
            STATUS mandatory
            DESCRIPTION
                "The number of frames that have been transmitted
                 by this bridge link to its segment.  Note that
                 a frame transmitted on the interface corresponding
                 to this bridge link is only counted by this object
                 if and only if it is for a protocol being processed
                 by the local bridging function."
        ::= { cdx6500PSTTpLinkEntry 4 }

        cdx6500LfcmTpLinkInDiscards OBJECT-TYPE
            SYNTAX Counter
            ACCESS read-only
            STATUS mandatory
            DESCRIPTION
                "Count of valid frames received which were
                 discarded (i.e., filtered) by the Forwarding Process."
        ::= { cdx6500PSTTpLinkEntry 5 }

        cdx6500LfcmTpLinkUnicastRx OBJECT-TYPE
            SYNTAX Counter
            ACCESS read-only
            STATUS mandatory
            DESCRIPTION
                "The number of Unicast Frames received on this WAN 
                 Bridge Link."
        ::= { cdx6500PSTTpLinkEntry 6 }

        cdx6500LfcmTpLinkUnicastTx OBJECT-TYPE
            SYNTAX Counter
            ACCESS read-only
            STATUS mandatory
            DESCRIPTION
                "The number of Unicast Frames transmitted on this WAN 
                 Bridge Link."
        ::= { cdx6500PSTTpLinkEntry 7 }

        cdx6500LfcmTpLinkMulticastRx OBJECT-TYPE
            SYNTAX Counter
            ACCESS read-only
            STATUS mandatory
            DESCRIPTION
                "The number of Multicast Frames received on this WAN 
                 Bridge Link."
        ::= { cdx6500PSTTpLinkEntry 8 }

        cdx6500LfcmTpLinkMulticastTx OBJECT-TYPE
            SYNTAX Counter
            ACCESS read-only
            STATUS mandatory
            DESCRIPTION
                "The number of Multicast Frames transmitted on
                 this WAN Bridge Link."
        ::= { cdx6500PSTTpLinkEntry 9 }

        cdx6500LfcmTpLinkBroadcastRx OBJECT-TYPE
            SYNTAX Counter
            ACCESS read-only
            STATUS mandatory
            DESCRIPTION
                "The number of Broadcast Frames received on this WAN 
                 Bridge Link."
        ::= { cdx6500PSTTpLinkEntry 10 }

        cdx6500LfcmTpLinkBroadcastTx OBJECT-TYPE
            SYNTAX Counter
            ACCESS read-only
            STATUS mandatory
            DESCRIPTION
                "The number of Broadcast Frames transmitted on this WAN
                 Bridge Link."
        ::= { cdx6500PSTTpLinkEntry 11 }

        cdx6500LfcmTpLinkInBoundDisc OBJECT-TYPE
            SYNTAX Counter
            ACCESS read-only
            STATUS mandatory
            DESCRIPTION
                "The number of frames discarded due to receive link state
                 not in forwarding state ."
        ::= { cdx6500PSTTpLinkEntry 12 }

        cdx6500LfcmTpLinkOutBoundDisc OBJECT-TYPE
            SYNTAX Counter
            ACCESS read-only
            STATUS mandatory
            DESCRIPTION
                "The number of frames discarded due to 
                 transmit link state not in forwarding state."
        ::= { cdx6500PSTTpLinkEntry 13 }

        cdx6500LfcmTpLinkULPInBoundDisc OBJECT-TYPE
            SYNTAX Counter
            ACCESS read-only
            STATUS mandatory
            DESCRIPTION
                "The number of frames discarded due to Unicast Link Protect
                 being set on the incoming link."
        ::= { cdx6500PSTTpLinkEntry 14 }

        cdx6500LfcmTpLinkULPOutBoundDisc OBJECT-TYPE
            SYNTAX Counter
            ACCESS read-only
            STATUS mandatory
            DESCRIPTION
                "The number of frames discarded due to Unicast Link Protect
                 being set on the outgoing link."
        ::= { cdx6500PSTTpLinkEntry 15 }

        cdx6500LfcmTpLinkMLPInBoundDisc OBJECT-TYPE
            SYNTAX Counter
            ACCESS read-only
            STATUS mandatory
            DESCRIPTION
                "The number of frames discarded due to Multicast Link Protect
                 being set on the incoming link."
        ::= { cdx6500PSTTpLinkEntry 16 }

        cdx6500LfcmTpLinkMLPOutBoundDisc OBJECT-TYPE
            SYNTAX Counter
            ACCESS read-only
            STATUS mandatory
            DESCRIPTION
                "The number of frames discarded due to Multicast Link Protect
                 being set on the outgoing link."
        ::= { cdx6500PSTTpLinkEntry 17 }

        --
        -- The cdx6500 dot1dStp Link group
        --
        -- dot1dStp Link Statistics - Table
        --

        cdx6500PSTStpLinkTable OBJECT-TYPE
            SYNTAX SEQUENCE OF Cdx6500PSTStpLinkEntry
            ACCESS not-accessible
            STATUS mandatory
            DESCRIPTION
                "A table that contains bridge-Link-specific
                 information for the Spanning Tree Protocol."
        ::= { cdx6500PSTBridgeGroup 7 }

        cdx6500PSTStpLinkEntry OBJECT-TYPE
            SYNTAX Cdx6500PSTStpLinkEntry
            ACCESS not-accessible
            STATUS mandatory
            DESCRIPTION
                "A list of information maintained by every bridge
                 link about the Spanning Tree Protocol state for
                 that bridge link."
            INDEX { cdx6500LfcmStpLink  }
        ::= { cdx6500PSTStpLinkTable 1 }

       Cdx6500PSTStpLinkEntry ::= 
           SEQUENCE {
               cdx6500LfcmStpLink
                   INTEGER,
               cdx6500LfcmStpPriority
                   INTEGER,
               cdx6500LfcmStpState
                   INTEGER,
               cdx6500LfcmStpEnable
                   INTEGER,
               cdx6500LfcmStpPathCost
                   INTEGER,
               cdx6500LfcmStpDesignatedRoot
                   BridgeId,
               cdx6500LfcmStpDesignatedCost
                   INTEGER,
               cdx6500LfcmStpDesignatedBridge
                   BridgeId,
               cdx6500LfcmStpDesignatedPort
                   OCTET STRING,
               cdx6500LfcmStpForwardTransitions
                   Counter
               }

        cdx6500LfcmStpLink OBJECT-TYPE
            SYNTAX INTEGER
            ACCESS read-only
            STATUS mandatory
            DESCRIPTION
                "The bridge link number for which this entry
                 contains Spanning Tree Protocol management information."
        ::= { cdx6500PSTStpLinkEntry 1 }

        cdx6500LfcmStpPriority OBJECT-TYPE
            SYNTAX INTEGER
            ACCESS read-only
            STATUS mandatory
            DESCRIPTION
                "The value of the priority field which is
                 contained in the first (in network byte order)
                 octet of the (2 octet long) Port ID.  The other
                 octet of the Port ID is given by the value of
                 cdx6500LfcmStpLink."
        ::= { cdx6500PSTStpLinkEntry 2 }

        cdx6500LfcmStpState OBJECT-TYPE
            SYNTAX INTEGER {
                    disabled   (1),
                    blocking   (2),
                    listening  (3),
                    learning   (4),
                    forwarding (5),
                    broken     (6)
                    }
            ACCESS read-only
            STATUS mandatory
            DESCRIPTION
                "The bridge link's current state as defined by
                 application of the Spanning Tree Protocol.  This
                 state controls what action a bridge link takes on
                 reception of a frame. For bridge links which are
                 disabled (see cdx6500LfcmStpEnable), this object
                 will have a value of 'disabled'."
        ::= { cdx6500PSTStpLinkEntry 3 }

        cdx6500LfcmStpEnable OBJECT-TYPE
            SYNTAX INTEGER {
                    enabled  (1),
                    disabled (2)
                    }
            ACCESS read-only
            STATUS mandatory
            DESCRIPTION
                "The enabled/disabled status of the bridge link."
        ::= { cdx6500PSTStpLinkEntry 4 }

        cdx6500LfcmStpPathCost OBJECT-TYPE
            SYNTAX INTEGER
            ACCESS read-only
            STATUS mandatory
            DESCRIPTION
                "The contribution of this bridge link to the path cost
                 of paths towards the spanning tree root which include
                 this bridge link."
        ::= { cdx6500PSTStpLinkEntry 5 }

        cdx6500LfcmStpDesignatedRoot OBJECT-TYPE
            SYNTAX BridgeId
            ACCESS read-only
            STATUS mandatory
            DESCRIPTION
                "The unique Bridge Identifier of the Bridge
                 recorded as the Root in the Configuration BPDUs
                 transmitted by the Designated Bridge for the
                 segment to which the bridge link is attached."
        ::= { cdx6500PSTStpLinkEntry 6 }

        cdx6500LfcmStpDesignatedCost OBJECT-TYPE
            SYNTAX INTEGER
            ACCESS read-only
            STATUS mandatory
            DESCRIPTION
                "The path cost of the Designated Port of the
                 segment connected to this bridge link.  This
                 value is compared to the Root Path Cost field
                 in received bridge PDUs."
        ::= { cdx6500PSTStpLinkEntry 7 }

        cdx6500LfcmStpDesignatedBridge OBJECT-TYPE
            SYNTAX BridgeId
            ACCESS read-only
            STATUS mandatory
            DESCRIPTION
                "The Bridge Identifier of the bridge which this
                 bridge link considers to be the Designated
                 Bridge for this bridge link's segment."
        ::= { cdx6500PSTStpLinkEntry 8 }

        cdx6500LfcmStpDesignatedPort OBJECT-TYPE
            SYNTAX OCTET STRING
            ACCESS read-only
            STATUS mandatory
            DESCRIPTION
                "The Port Identifier of the bridge link on the
                 Designated Bridge for this bridge link's segment."
        ::= { cdx6500PSTStpLinkEntry 9 }

        cdx6500LfcmStpForwardTransitions OBJECT-TYPE
            SYNTAX Counter
            ACCESS read-only
            STATUS mandatory
            DESCRIPTION
                "The number of times this port has transitioned
                 from the Learning state to the Forwarding state.
                 Not supported, will return zero."
        ::= { cdx6500PSTStpLinkEntry 10 }

        --
        -- The cdx6500 dot1dStatic Link group
        --
        -- dot1dStatic Link Statistics - Table
        --

        cdx6500PSTStaticStatsLinkTable OBJECT-TYPE
            SYNTAX SEQUENCE OF Cdx6500PSTStaticStatsLinkEntry
            ACCESS not-accessible
            STATUS mandatory
            DESCRIPTION
                "This table contains MAC Address and
                 Protocol Filtering information."
        ::= { cdx6500PSTBridgeGroup 8 }

        cdx6500PSTStaticsStatsLinkEntry OBJECT-TYPE
            SYNTAX Cdx6500PSTStaticStatsLinkEntry
            ACCESS not-accessible
            STATUS mandatory
            DESCRIPTION
                "A list of filtering statistcs for MAC
                 Address and Protocol filtering."
            INDEX { cdx6500LfcmLinkFilterIndex }
        ::= { cdx6500PSTStaticStatsLinkTable 1 }

        Cdx6500PSTStaticStatsLinkEntry ::=
            SEQUENCE {
                cdx6500LfcmLinkFilterIndex
                    INTEGER,
                cdx6500LfcmLinkFilSrcAddrInDisc
                    Counter,
                cdx6500LfcmLinkFilSrcAddrOutDisc
                    Counter,
                cdx6500LfcmLinkFilDestAddrInDisc
                    Counter,
                cdx6500LfcmLinkFilDestAddrOutDisc
                    Counter,
                dx6500LfcmLinkFilProtInDisc
                    Counter,
                cdx6500LfcmLinkFilProtOutDisc
                    Counter,
                cdx6500LfcmLinkFilTotalInDisc
                    Counter,
                cdx6500LfcmLinkFilTotalOutDisc
                    Counter
                }

        cdx6500LfcmLinkFilterIndex OBJECT-TYPE
            SYNTAX INTEGER
            ACCESS read-only
            STATUS mandatory
            DESCRIPTION
                "The bridge link for which this entry contains filter
                 information."
        ::= { cdx6500PSTStaticsStatsLinkEntry 1 }

        cdx6500LfcmLinkFilSrcAddrInDisc OBJECT-TYPE
            SYNTAX Counter
            ACCESS read-only
            STATUS mandatory
            DESCRIPTION
                "The number of inbound frames on this bridge link that 
                 were not forwarded becauseof Source MAC Address filtering."
        ::= { cdx6500PSTStaticsStatsLinkEntry 2 }

        cdx6500LfcmLinkFilSrcAddrOutDisc OBJECT-TYPE
            SYNTAX Counter
            ACCESS read-only
            STATUS mandatory
            DESCRIPTION
                "The number of outbound frames on this bridge link that
                 were not forwarded becauseof Source MAC Address filtering."
        ::= { cdx6500PSTStaticsStatsLinkEntry 3 }

        cdx6500LfcmLinkFilDestAddrInDisc OBJECT-TYPE
            SYNTAX Counter
            ACCESS read-only
            STATUS mandatory
            DESCRIPTION
                "The number of inbound frames on this bridge link that 
                 were not forwarded because of Destination MAC Address
                 filtering."
        ::= { cdx6500PSTStaticsStatsLinkEntry 4 }

        cdx6500LfcmLinkFilDestAddrOutDisc OBJECT-TYPE
            SYNTAX Counter
            ACCESS read-only
            STATUS mandatory
            DESCRIPTION
                "The number of outbound frames on this bridge link that 
                 were not forwarded because of Destination MAC Address
                 filtering."
        ::= { cdx6500PSTStaticsStatsLinkEntry 5 }

        cdx6500LfcmLinkFilProtInDisc OBJECT-TYPE
            SYNTAX Counter
            ACCESS read-only
            STATUS mandatory
            DESCRIPTION
                "The number of inbound frames on this bridge link that 
                 were not forwarded because of Protocol filtering."
        ::= { cdx6500PSTStaticsStatsLinkEntry 6 }

        cdx6500LfcmLinkFilProtOutDisc OBJECT-TYPE
            SYNTAX Counter
            ACCESS read-only
            STATUS mandatory
            DESCRIPTION
                "The number of outbound frames on this bridge link that 
                 were not forwarded because of Protocol filtering."
        ::= { cdx6500PSTStaticsStatsLinkEntry 7 }

        cdx6500LfcmLinkFilTotalInDisc OBJECT-TYPE
            SYNTAX Counter
            ACCESS read-only
            STATUS mandatory
            DESCRIPTION
                "The sum of Source MAC Address, Destination MAC Address, and
                 Protocol inbound frames on this bridge link not forwarded 
                 because of filtering."
        ::= { cdx6500PSTStaticsStatsLinkEntry 8 }

        cdx6500LfcmLinkFilTotalOutDisc OBJECT-TYPE
            SYNTAX Counter
            ACCESS read-only
            STATUS mandatory
            DESCRIPTION
                "The sum of Source MAC Address, Destination MAC Address, and
                 Protocol outbound frames on this bridge link  not forwarded 
                 because of filtering."
        ::= { cdx6500PSTStaticsStatsLinkEntry 9 }

        --
        -- Local Termination(LTRM)
        --
        -- Statistics - Table
        --
    
        cdx6500PSTLtrmStatsTable OBJECT-TYPE
            SYNTAX SEQUENCE OF Cdx6500PSTLtrmStatsEntry
            ACCESS not-accessible
            STATUS mandatory
            DESCRIPTION
                "This table contains Local Termination session statistics."
        ::= { cdx6500PSTBridgeGroup 9 }
    
        cdx6500PSTLtrmStatsEntry OBJECT-TYPE
            SYNTAX Cdx6500PSTLtrmStatsEntry
            ACCESS not-accessible
            STATUS mandatory
            DESCRIPTION
                "A list of statistics and boot control per
                 Local Termination session."
            INDEX { cdx6500LfcmLtrmStatsIndex }
        ::= { cdx6500PSTLtrmStatsTable 1 }
    
        Cdx6500PSTLtrmStatsEntry ::= 
            SEQUENCE {
                cdx6500LfcmLtrmStatsIndex
                    INTEGER,
                cdx6500LfcmLtrmStatsDataCharIn
                    Counter,
                cdx6500LfcmLtrmStatsDataCharOut
                    Counter,
                cdx6500LfcmLtrmStatsDataFrIn
                    Counter,
                cdx6500LfcmLtrmStatsDataFrOut
                    Counter,
                cdx6500LfcmLtrmStatsCtFrRrIn 
                    Counter,
                cdx6500LfcmLtrmStatsCtFrRrOut
                    Counter,
                cdx6500LfcmLtrmStatsCtFrRnrIn
                    Counter,
                cdx6500LfcmLtrmStatsCtFrRnrOut
                    Counter,
                cdx6500LfcmLtrmStatsCtFrXidIn
                    Counter,
                cdx6500LfcmLtrmStatsCtFrXidOut
                    Counter,
                cdx6500LfcmLtrmStatsCtFrRejIn
                    Counter,
                cdx6500LfcmLtrmStatsCtFrRejOut
                    Counter,
                cdx6500LfcmLtrmStatsCtFrSabmeIn
                    Counter,
                cdx6500LfcmLtrmStatsCtFrSabmeOut
                    Counter,
                cdx6500LfcmLtrmStatsTotFrInData
                    Counter,
                cdx6500LfcmLtrmStatsTotFrOutData
                    Counter,
                cdx6500LfcmLtrmStatsBoot
                    INTEGER
                }
    
        cdx6500LfcmLtrmStatsIndex OBJECT-TYPE
            SYNTAX INTEGER (1..64)
            ACCESS read-only
            STATUS mandatory
            DESCRIPTION
                "This is the Session number for which there is statistics."
        ::= { cdx6500PSTLtrmStatsEntry 1 }
    
        cdx6500LfcmLtrmStatsDataCharIn OBJECT-TYPE
            SYNTAX Counter
            ACCESS read-only
            STATUS mandatory
            DESCRIPTION
                "The number of data bytes received."
        ::= { cdx6500PSTLtrmStatsEntry 2 }
    
        cdx6500LfcmLtrmStatsDataCharOut OBJECT-TYPE
            SYNTAX Counter
            ACCESS read-only
            STATUS mandatory
            DESCRIPTION
                "The number of data bytes transmitted."
        ::= { cdx6500PSTLtrmStatsEntry 3 }
    
        cdx6500LfcmLtrmStatsDataFrIn OBJECT-TYPE
            SYNTAX Counter
            ACCESS read-only
            STATUS mandatory
            DESCRIPTION
                "The number of data frames received."
        ::= { cdx6500PSTLtrmStatsEntry 4 }
    
        cdx6500LfcmLtrmStatsDataFrOut OBJECT-TYPE
            SYNTAX Counter
            ACCESS read-only
            STATUS mandatory
            DESCRIPTION
                "The number of data frames transmitted."
        ::= { cdx6500PSTLtrmStatsEntry 5 }
    
        cdx6500LfcmLtrmStatsCtFrRrIn OBJECT-TYPE
            SYNTAX Counter
            ACCESS read-only
            STATUS mandatory
            DESCRIPTION
                "The number of Receiver Ready frames received."
        ::= { cdx6500PSTLtrmStatsEntry 6 }
    
        cdx6500LfcmLtrmStatsCtFrRrOut OBJECT-TYPE
            SYNTAX Counter
            ACCESS read-only
            STATUS mandatory
            DESCRIPTION
                "The number of Receiver Ready frames transmitted."
        ::= { cdx6500PSTLtrmStatsEntry 7 }
    
        cdx6500LfcmLtrmStatsCtFrRnrIn OBJECT-TYPE
            SYNTAX Counter
            ACCESS read-only
            STATUS mandatory
            DESCRIPTION
                "The number of Receiver Not Ready frames received."
        ::= { cdx6500PSTLtrmStatsEntry 8 }
    
        cdx6500LfcmLtrmStatsCtFrRnrOut OBJECT-TYPE
            SYNTAX Counter
            ACCESS read-only
            STATUS mandatory
            DESCRIPTION
                "The number of Receiver Not Ready frames transmitted."
        ::= { cdx6500PSTLtrmStatsEntry 9 }
    
        cdx6500LfcmLtrmStatsCtFrXidIn OBJECT-TYPE
            SYNTAX Counter
            ACCESS read-only
            STATUS mandatory
            DESCRIPTION
                "The number of ID Exchange frames received."
        ::= { cdx6500PSTLtrmStatsEntry 10 }
    
        cdx6500LfcmLtrmStatsCtFrXidOut OBJECT-TYPE
            SYNTAX Counter
            ACCESS read-only
            STATUS mandatory
            DESCRIPTION
                "The number of ID Exchange frames transmitted."
        ::= { cdx6500PSTLtrmStatsEntry 11 }
    
        cdx6500LfcmLtrmStatsCtFrRejIn OBJECT-TYPE
            SYNTAX Counter
            ACCESS read-only
            STATUS mandatory
            DESCRIPTION
                "The number of Reject frames received."
        ::= { cdx6500PSTLtrmStatsEntry 12 }
    
        cdx6500LfcmLtrmStatsCtFrRejOut OBJECT-TYPE
            SYNTAX Counter
            ACCESS read-only
            STATUS mandatory
            DESCRIPTION
                "The number of Reject frames transmitted."
        ::= { cdx6500PSTLtrmStatsEntry 13 }
    
        cdx6500LfcmLtrmStatsCtFrSabmeIn OBJECT-TYPE
            SYNTAX Counter
            ACCESS read-only
            STATUS mandatory
            DESCRIPTION
                "The number of SABME frames received."
        ::= { cdx6500PSTLtrmStatsEntry 14 }
    
        cdx6500LfcmLtrmStatsCtFrSabmeOut OBJECT-TYPE
            SYNTAX Counter
            ACCESS read-only
            STATUS mandatory
            DESCRIPTION
                "The number of SABME frames transmitted."
        ::= { cdx6500PSTLtrmStatsEntry 15 }
    
        cdx6500LfcmLtrmStatsTotFrInData OBJECT-TYPE
            SYNTAX Counter
            ACCESS read-only
            STATUS mandatory
            DESCRIPTION
                "The sum of Data Frames, Receiver Ready, Receiver
                 Not Ready, Reject, SABME and ID Exchange frames received."
        ::= { cdx6500PSTLtrmStatsEntry 16 }
    
        cdx6500LfcmLtrmStatsTotFrOutData OBJECT-TYPE
            SYNTAX Counter
            ACCESS read-only
            STATUS mandatory
            DESCRIPTION
                "The sum of Data Frames, Receiver Ready, Receiver
                 Not Ready, Reject, SABME and ID Exchange frames transmitted."
        ::= { cdx6500PSTLtrmStatsEntry 17 }
    
        cdx6500LfcmLtrmStatsBoot OBJECT-TYPE
            SYNTAX INTEGER {
                    boot (1)
                    }
            ACCESS read-only
            STATUS mandatory
            DESCRIPTION
                "This command is used to boot a Local Termination session 
                 when set to `boot'."
        ::= { cdx6500PSTLtrmStatsEntry 18 }

        -- Bridge Group Statistics

        cdx6500dot1dBridgeStatsGroup OBJECT IDENTIFIER 
            ::= { cdx6500PSTBridgeGroup 10 }

        cdx6500dot1dBasePortStats OBJECT IDENTIFIER 
            ::= { cdx6500dot1dBridgeStatsGroup 1 }

        --
        -- Base LAN Port Statistics - Table
        --

        cdx6500PSTPortBaseTable OBJECT-TYPE
            SYNTAX SEQUENCE OF Cdx6500PSTPortBasePort
            ACCESS not-accessible
            STATUS mandatory
            DESCRIPTION
                 "A table that contains generic information about
                  every port that is associated with this bridge.
                  Transparent, source-route, and srt ports are included."
        ::= { cdx6500PSTBridgeGroup 11 }
    
        cdx6500PSTPortBasePortEntry OBJECT-TYPE
            SYNTAX Cdx6500PSTPortBasePort
            ACCESS not-accessible
            STATUS mandatory
            DESCRIPTION
                "A list of information for each port of the bridge."
            INDEX { cdx6500LfcmBasePort }
        ::= { cdx6500PSTPortBaseTable 1 }
    
        Cdx6500PSTPortBasePort ::= 
            SEQUENCE {
                cdx6500LfcmBasePort
                    INTEGER,
                cdx6500LfcmBridgeLinkStatus
                    INTEGER,
                cdx6500LfcmClearStats
                    INTEGER,
                cdx6500LfcmLastStatsReset
                    INTEGER,
                cdx6500LfcmBridgeBoot
                    INTEGER,
                cdx6500LfcmPortBridgeLinkBoot
                    INTEGER,
                cdx6500LfcmPortBlEnable
                    INTEGER,
                cdx6500LfcmPortBlDisable
                    INTEGER,
                cdx6500LfcmCtrlsPortSetLinkProt
                    INTEGER,
                cdx6500LfcmCtrlsPortClrLinkProt
                    INTEGER,
                cdx6500LfcmCtrlsPortSetMultProt
                    INTEGER,
                cdx6500LfcmCtrlsPortClrMultProt
                    INTEGER
                }
    
        cdx6500LfcmBasePort OBJECT-TYPE
            SYNTAX INTEGER   
            ACCESS read-only
            STATUS mandatory
            DESCRIPTION
                "The port number of the port for which this entry
                 contains bridge management information."
        ::= { cdx6500PSTPortBasePortEntry 1 }

        cdx6500LfcmBridgeLinkStatus OBJECT-TYPE
            SYNTAX INTEGER {
                    configErr       (0),
                    swDisabled      (1),
                    userDisabled    (3),
                    congested       (4),
                    inactive        (5),
                    active          (6),
                    unconfig        (7),
                    newvalConfigErr (50)
                    }
            ACCESS read-only
            STATUS mandatory
            DESCRIPTION
                "The status of the LAN Port link:
                 unconfig     = Not configured
                 configerr    = Configuration error on link
                 swDisabled   = Physical errors on link
                 userDisabled = User shut down link
                 congested    = WAN congested condition
                 inactive     = Configured link - ready for use but not active
                 active       = Configured and active link.
                 newvalConfigErr = same functionality as 'configErr', new
                 enumeration added for RFC1155 compatibility."
        ::= { cdx6500PSTPortBasePortEntry 2 }

        cdx6500LfcmClearStats OBJECT-TYPE
            SYNTAX INTEGER {
                    resetStats (1)
                    }
            ACCESS write-only
            STATUS mandatory
            DESCRIPTION
                "This is the command to reset the LAN port bridge statistics."
        ::= { cdx6500PSTPortBasePortEntry 3 }

        cdx6500LfcmLastStatsReset OBJECT-TYPE
            SYNTAX DisplayString
            ACCESS read-only
            STATUS mandatory
            DESCRIPTION
                "The time of the last LAN port statistics reset."
        ::= { cdx6500PSTPortBasePortEntry 4 }

        cdx6500LfcmBridgeBoot OBJECT-TYPE
            SYNTAX INTEGER {
                    boot (1)
                    }
            ACCESS write-only
            STATUS mandatory
            DESCRIPTION
                "This is the command to boot the LAN port bridge parameters."
        ::= { cdx6500PSTPortBasePortEntry 5 }

        cdx6500LfcmPortBridgeLinkBoot OBJECT-TYPE
            SYNTAX INTEGER {
                    boot (1)
                    }
            ACCESS write-only
            STATUS mandatory
            DESCRIPTION
                "This is the command to boot the LAN port Bridge
                 Link parameters."
        ::= { cdx6500PSTPortBasePortEntry 6 }

        cdx6500LfcmPortBlEnable OBJECT-TYPE
            SYNTAX INTEGER {
                    enable (1)
                    }
            ACCESS write-only
            STATUS mandatory
            DESCRIPTION
                "This is the command to Enable the LAN port Bridge Link."
        ::= { cdx6500PSTPortBasePortEntry 7 }

        cdx6500LfcmPortBlDisable OBJECT-TYPE
            SYNTAX INTEGER {
                    disable (1)
                    }
            ACCESS write-only
            STATUS mandatory
            DESCRIPTION
                "This is the command to Disable the LAN port Bridge Link."
        ::= { cdx6500PSTPortBasePortEntry 8 }

        cdx6500LfcmCtrlsPortSetLinkProt OBJECT-TYPE
            SYNTAX INTEGER {
                    setUcastProtection (1)
                    }
            ACCESS write-only
            STATUS mandatory
            DESCRIPTION
                "This is a command to set Unicast Protection
                 for the LAN Bridge Link."
        ::= { cdx6500PSTPortBasePortEntry 9 }
    
        cdx6500LfcmCtrlsPortClrLinkProt OBJECT-TYPE
            SYNTAX INTEGER {
                    clearUcastProtection (1)
                    }
            ACCESS write-only
            STATUS mandatory
            DESCRIPTION
                "This is a command to clear Unicast Protection
                 for the LAN Bridge Link."
        ::= { cdx6500PSTPortBasePortEntry 10 }
    
        cdx6500LfcmCtrlsPortSetMultProt OBJECT-TYPE
            SYNTAX INTEGER {
                    setMcastProtection (1)
                    }
            ACCESS write-only
            STATUS mandatory
            DESCRIPTION
                "This is a command to set Multicast Protection
                 for the LAN Bridge Link."
        ::= { cdx6500PSTPortBasePortEntry 11 }
    
        cdx6500LfcmCtrlsPortClrMultProt  OBJECT-TYPE
            SYNTAX INTEGER {
                    clearMcastProtection (1)
                    }
            ACCESS write-only
            STATUS mandatory
            DESCRIPTION
                "This is a command to clear Multicast Protection
                 for the LAN Bridge Link."
        ::= { cdx6500PSTPortBasePortEntry 12 }
    
        cdx6500dot1dTpPortStats OBJECT IDENTIFIER 
            ::= { cdx6500dot1dBridgeStatsGroup 2 }

        --
        -- TP Port Statistics
        --

        cdx6500LfcmTpPortLearnedEntries OBJECT-TYPE
            SYNTAX INTEGER
            ACCESS read-only
            STATUS mandatory
            DESCRIPTION
                "The number of end station addresses learned."
        ::= { cdx6500dot1dTpPortStats 1 }

        cdx6500LfcmTpPortAvailEntries OBJECT-TYPE
            SYNTAX INTEGER
            ACCESS read-only
            STATUS mandatory
            DESCRIPTION
                "The number of Available Entries in the Forwarding Table."
        ::= { cdx6500dot1dTpPortStats 2 }

        cdx6500LfcmTpPortMaximumEntries OBJECT-TYPE
            SYNTAX INTEGER
            ACCESS read-only
            STATUS mandatory
            DESCRIPTION
                "The maximum number of entries being used in
                 the Forwarding Table since the last node boot."
        ::= { cdx6500dot1dTpPortStats 3 }

        cdx6500dot1dBaseLinkStats OBJECT IDENTIFIER
            ::= { cdx6500dot1dBridgeStatsGroup 3 }

       --
       -- dot1dBase Link Statistics
       --

        cdx6500LfcmNumLinks OBJECT-TYPE
            SYNTAX INTEGER
            ACCESS read-only
            STATUS mandatory
            DESCRIPTION
                "The number of WAN Bridge Links that have been configured."
        ::= { cdx6500dot1dBaseLinkStats 1 }

        END
