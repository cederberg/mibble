OMNI-gx2Em870-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Em870
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"3" Fev 1, 2003
		   --DESCRIPTION
		   --			Added revision and description comment section


		--    OMNISTAR Laser Module (Forward Path Transmetter)  MIB MODULE

	-- This MIB module defines information for management of HFC networks
		-- 
		-- The MIB module assumes that all generic (static) network element
		-- information is defined in a different module such as the HFC module
		-- The MIB consists of two groups:
		-- the device type descriptor subgroup and 
		-- gx2Em870 Network Elements subgroup.
		-- The device type descriptor subgroup is used to define 
		-- parameters specific to gx2Em870 device type.
		-- These parameters are common across all network elements
		-- from gx2Em870 device type.
		--
		-- The gx2Em870 Network Elements subgroup is
		-- a list of gx2Em870 type elements in the
		-- current network topology with nominal
		-- and current parameter values for the
		-- individual network elements; the individual
		-- network elements are identified by  
		-- index from hfcCommonTable.
		-- That implies what hfcCommonTableIndex and
		-- gx2Em870TableIndex are equal for each individual
		-- network element.
		-- This table is an extension of the hfcCommonTable
		-- for all elements of gx2Em870 type.
		--
		-- Both groups are mandatory for management of gx2Em870 devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Em870 Device Descriptor subgroup.

		-- The device type descriptor subgroup is used to define 
		-- parameters specific to gx2Em870 device type.
		-- These parameters are common across all network elements
		-- from gx2Em870 device type.


		gx2Em870Descriptor OBJECT IDENTIFIER ::= {gx2Em870 1}



--*****************************************************************************
		--              gx2Em870 Table
		
		-- Contains a list of all gx2Em870 type devices in
		-- the network. Each device is characterized with
		-- current network topology information, with nominal
		-- and current parameter values for the
		-- individual network elements;
		--
		-- The individual network elements indentified by  
		-- index from hfcCommonTable.
		-- That implies what hfcCommonTableIndex and
		-- gx2Em870TableIndex are equal for each individual
		-- nettwork element.
		-- This table should be used as an extension of the hfcCommonTable
		-- for all elements of gx2Em870 type.


	       gx2Em870AnalogTable                    OBJECT-TYPE
			 SYNTAX             SEQUENCE OF Gx2Em870AnalogEntry
			 ACCESS             not-accessible
			 STATUS             mandatory
			 DESCRIPTION
			 "This table contains gx2Em870 specific parameters with
			  nominal and current values."
			 ::= { gx2Em870 2 }


	       gx2Em870AnalogEntry               OBJECT-TYPE
			 SYNTAX             Gx2Em870AnalogEntry
			 ACCESS             not-accessible
			 STATUS             mandatory
			 DESCRIPTION
			 "This list contains the analog parameters and descriptions."
			 INDEX { gx2Em870AnalogTableIndex }
			 ::= { gx2Em870AnalogTable  1}

--*************************************************************************
--	NO DIGITAL TABLE FOR THIS MODULE
--*************************************************************************
	       gx2Em870StatusTable                    OBJECT-TYPE
			 SYNTAX             SEQUENCE OF Gx2Em870StatusEntry
			 ACCESS             not-accessible
			 STATUS             mandatory
			 DESCRIPTION
			 "This table contains gx2Em870 specific parameters with
			  nominal and current values."
			 ::= { gx2Em870 4 }

	       gx2Em870StatusEntry               OBJECT-TYPE
			 SYNTAX             Gx2Em870StatusEntry
			 ACCESS             not-accessible
			 STATUS             mandatory
			 DESCRIPTION
			 "This list contains Status parameters and descriptions."
			 INDEX { gx2Em870StatusTableIndex }
			 ::= { gx2Em870StatusTable  2}

--*************************************************************************
	       gx2Em870FactoryTable                    OBJECT-TYPE
			 SYNTAX             SEQUENCE OF Gx2Em870FactoryEntry
			 ACCESS             not-accessible
			 STATUS             mandatory
			 DESCRIPTION
			 "This table contains gx2Em870 specific parameters with
			  nominal and current values."
			 ::= { gx2Em870 5 }

	       gx2Em870FactoryEntry               OBJECT-TYPE
			 SYNTAX             Gx2Em870FactoryEntry
			 ACCESS             not-accessible
			 STATUS             mandatory
			 DESCRIPTION
			 "This list contains Factory parameters and descriptions."
			 INDEX { gx2Em870FactoryTableIndex }
			 ::= { gx2Em870FactoryTable  3}
--*************************************************************************

	      Gx2Em870AnalogEntry    ::= SEQUENCE  
	       {
		gx2Em870AnalogTableIndex         INTEGER,
		
		--           Analog Parameters

		em870labelOpticalPower			DisplayString (SIZE (0..80)),
		em870uomOpticalPower				DisplayString (SIZE (0..80)),
		em870majorHighOpticalPower 		Float, 
		em870majorLowOpticalPower 		Float, 
		em870minorHighOpticalPower 		Float,
		em870minorLowOpticalPower 		Float, 
		em870currentValueOpticalPower 	Float, 
		em870stateFlagOpticalPower 		INTEGER,
		em870minValueOpticalPower 		Float,
		em870maxValueOpticalPower  		Float,
		em870alarmStateOpticalPower 	INTEGER,

		em870labelOmiOffset				DisplayString (SIZE (0..80)),
		em870uomOmiOffset				DisplayString (SIZE (0..80)),
		em870majorHighOmiOffset			Float, 
		em870majorLowOmiOffset			Float, 
		em870minorHighOmiOffset			Float,
		em870minorLowOmiOffset			Float, 
		em870currentValueOmiOffset		Float, 
		em870stateFlagOmiOffset			INTEGER,
		em870minValueOmiOffset			Float,
		em870maxValueOmiOffset 			Float,
		em870alarmStateOmiOffset		INTEGER,

		em870labelDFBPower				DisplayString (SIZE (0..80)),
		em870uomDFBPower				DisplayString (SIZE (0..80)),
		em870majorHighDFBPower			Float, 
		em870majorLowDFBPower			Float, 
		em870minorHighDFBPower			Float,
		em870minorLowDFBPower			Float, 
		em870currentValueDFBPower		Float, 
		em870stateFlagDFBPower			INTEGER,
		em870minValueDFBPower			Float,
		em870maxValueDFBPower 			Float,
		em870alarmStateDFBPower			INTEGER,

		em870labelLaserBias				DisplayString (SIZE (0..80)),
		em870uomLaserBias				DisplayString (SIZE (0..80)),
		em870majorHighLaserBias			Float, 
		em870majorLowLaserBias			Float, 
		em870minorHighLaserBias			Float,
		em870minorLowLaserBias			Float, 
		em870currentValueLaserBias		Float, 
		em870stateFlagLaserBias			INTEGER,
		em870minValueLaserBias			Float,
		em870maxValueLaserBias 			Float,
		em870alarmStateLaserBias		INTEGER,

		em870labelCoolerCurrent			DisplayString (SIZE (0..80)),
		em870uomCoolerCurrent			DisplayString (SIZE (0..80)),
		em870majorHighCoolerCurrent		Float, 
		em870majorLowCoolerCurrent		Float, 
		em870minorHighCoolerCurrent		Float,
		em870minorLowCoolerCurrent		Float, 
		em870currentValueCoolerCurrent	Float, 
		em870stateFlagCoolerCurrent		INTEGER,
		em870minValueCoolerCurrent		Float,
		em870maxValueCoolerCurrent 		Float,
		em870alarmStateCoolerCurrent	INTEGER,

		em870labelLaserTemp				DisplayString (SIZE (0..80)),
		em870uomLaserTemp				DisplayString (SIZE (0..80)),
		em870majorHighLaserTemp			Float, 
		em870majorLowLaserTemp			Float, 
		em870minorHighLaserTemp			Float,
		em870minorLowLaserTemp			Float, 
		em870currentValueLaserTemp		Float, 
		em870stateFlagLaserTemp			INTEGER,
		em870minValueLaserTemp			Float,
		em870maxValueLaserTemp 			Float,
		em870alarmStateLaserTemp		INTEGER,

		em870labelModTemp				DisplayString (SIZE (0..80)),
		em870uomModTemp					DisplayString (SIZE (0..80)),
		em870majorHighModTemp			Float, 
		em870majorLowModTemp			Float, 
		em870minorHighModTemp			Float,
		em870minorLowModTemp			Float, 
		em870currentValueModTemp		Float, 
		em870stateFlagModTemp			INTEGER,
		em870minValueModTemp			Float,
		em870maxValueModTemp			Float,
		em870alarmStateModTemp			INTEGER,

		em870labelFanCurrent			DisplayString (SIZE (0..80)),
		em870uomFanCurrent				DisplayString (SIZE (0..80)),
		em870majorHighFanCurrent		Float, 
		em870majorLowFanCurrent			Float, 
		em870minorHighFanCurrent		Float,
		em870minorLowFanCurrent			Float, 
		em870currentValueFanCurrent		Float, 
		em870stateFlagFanCurrent		INTEGER,
		em870minValueFanCurrent			Float,
		em870maxValueFanCurrent 		Float,
		em870alarmStateFanCurrent		INTEGER,

		em870label12Volt				DisplayString (SIZE (0..80)),
		em870uom12Volt					DisplayString (SIZE (0..80)),
		em870majorHigh12Volt			Float, 
		em870majorLow12Volt				Float, 
		em870minorHigh12Volt			Float,
		em870minorLow12Volt				Float, 
		em870currentValue12Volt			Float, 
		em870stateFlag12Volt			INTEGER,
		em870minValue12Volt				Float,
		em870maxValue12Volt				Float,
		em870alarmState12Volt			INTEGER
		}

		-- ****************  Digital Parameters ***********************

		--NONE

		-- ****************  Status Parameters ************************************
	    Gx2Em870StatusEntry    ::= SEQUENCE  
	    {
		gx2Em870StatusTableIndex		INTEGER,

		em870labelBoot					DisplayString (SIZE (0..80)),
		em870valueBoot					INTEGER,
		em870stateflagBoot				INTEGER,
		
		em870labelFlash					DisplayString (SIZE (0..80)),
		em870valueFlash					INTEGER,
		em870stateflagFlash				INTEGER,

		em870labelFactoryDataCRC 		DisplayString (SIZE (0..80)),
		em870valueFactoryDataCRC		INTEGER,
		em870stateflagFactoryDataCRC	INTEGER,

		em870labelAlarmDataCrc			DisplayString (SIZE (0..80)),
		em870valueAlarmDataCrc			INTEGER,
		em870stateflagAlarmDataCrc		INTEGER

		}


		-- ****************  Factory Parameters *************************************
	    Gx2Em870FactoryEntry    ::= SEQUENCE  
	    {
		gx2Em870FactoryTableIndex		INTEGER,
		em870bootControlByte  			INTEGER,
		em870bootStatusByte   			INTEGER,
		em870bank1CRC    				INTEGER,
		em870bank2CRC    				INTEGER,
		em870prgEEPROMByte    			INTEGER,
		em870factoryCRC    				INTEGER,
		em870calculateCRC    			INTEGER,
		em870hourMeter    				INTEGER,
		em870flashPrgCntA    			INTEGER,
		em870flashPrgCntB    			INTEGER,
		em870flashBankARev    			DisplayString (SIZE (0..80)),
		em870flashBankBRev    			DisplayString (SIZE (0..80))


		}
            -- ************** Analog Parameters ****************************
		gx2Em870AnalogTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2Em870AnalogEntry 1}

-- New Parameter

		em870labelOpticalPower              OBJECT-TYPE
			   SYNTAX           DisplayString (SIZE (0..80))
			   ACCESS           read-only
			   STATUS           optional
			   DESCRIPTION
			   "The value of this object provides the label of the
			    Optical Output Power Analog parameter."
			   ::= { gx2Em870AnalogEntry 2}

		em870uomOpticalPower                OBJECT-TYPE
			   SYNTAX           DisplayString (SIZE (0..80))
			   ACCESS           read-only
			   STATUS           optional
			   DESCRIPTION
			   "The value of this object provides the Unit of Measure of the
			    Optical Output Power Analog parameter."
			   ::= { gx2Em870AnalogEntry 3}

		em870majorHighOpticalPower          OBJECT-TYPE
			   SYNTAX           Float 
			   ACCESS           read-only
			   STATUS           mandatory
			   DESCRIPTION
			   "The value of this object provides the Major High alarm value
			    of the Optical Output Power Analog parameter.
			   This value is a floating point number that is represented as an IEEE 32 bit number."
			   ::= { gx2Em870AnalogEntry 4}


		em870majorLowOpticalPower           OBJECT-TYPE
			   SYNTAX           Float 
			   ACCESS           read-only
			   STATUS           mandatory
			   DESCRIPTION
			   "The value of this object provides the Major Low alarm value
			    of the Optical Output Power Analog parameter.
			   This value is a floating point number that is represented as an IEEE 32 bit number."
			   ::= { gx2Em870AnalogEntry 5}

		em870minorHighOpticalPower          OBJECT-TYPE
			   SYNTAX           Float
			   ACCESS           read-only
			   STATUS           mandatory
			   DESCRIPTION
			   "The value of this object provides the Minor High alarm value
			    of the Optical Output Power Analog parameter.
			   This value is a floating point number that is represented as an IEEE 32 bit number."
			   ::= { gx2Em870AnalogEntry 6}

		em870minorLowOpticalPower           OBJECT-TYPE
			   SYNTAX           Float 
			   ACCESS           read-only
			   STATUS           mandatory
			   DESCRIPTION
			   "The value of this object provides the Minor Low alarm value
			    of the Optical Output Power Analog parameter.
			   This value is a floating point number that is represented as an IEEE 32 bit number."
			   ::= { gx2Em870AnalogEntry 7}

		em870currentValueOpticalPower       OBJECT-TYPE
			   SYNTAX           Float 
			   ACCESS           read-only
			   STATUS           mandatory
			   DESCRIPTION
			   "The value of this object provides the Current value
			    of the Optical Output Power Analog parameter.
			   This value is a floating point number that is represented as an IEEE 32 bit number."
			   ::= { gx2Em870AnalogEntry 8}

		em870stateFlagOpticalPower          OBJECT-TYPE
			   SYNTAX           INTEGER
								{
								hidden(1),
								read-only(2),
								updateable(3)
								}
			   ACCESS           read-only
			   STATUS           mandatory
			   DESCRIPTION
			   "The value of this object provides the state
			    of the Optical Output Power Analog parameter. (0-Hidden	
			          1-Read-Only, 2-Updateable)."
			   ::= { gx2Em870AnalogEntry 9}

		em870minValueOpticalPower           OBJECT-TYPE
			   SYNTAX           Float
			   ACCESS           read-only
			   STATUS           mandatory
			   DESCRIPTION
			   "The value of this object provides the minimum value
			    the Optical Output Power Analog parameter can achive.
			   This value is a floating point number that is represented as an IEEE 32 bit number."
			   ::= { gx2Em870AnalogEntry 10}

		em870maxValueOpticalPower           OBJECT-TYPE
			   SYNTAX           Float
			   ACCESS           read-only
			   STATUS           mandatory
			   DESCRIPTION
			   "The value of this object provides the maximum value
			    the Optical Output Power Analog parameter can achive.
			   This value is a floating point number that is represented as an IEEE 32 bit number."
			   ::= { gx2Em870AnalogEntry 11}

		em870alarmStateOpticalPower         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Output Power Analog parameter."
			   ::= { gx2Em870AnalogEntry 12}
			   
-- New Parameter

		em870labelOmiOffset       OBJECT-TYPE
			   SYNTAX           DisplayString (SIZE (0..80))
			   ACCESS           read-only
			   STATUS           optional
			   DESCRIPTION
			   "The value of this object provides the label of the
			    RF Input Power Analog parameter."
			   ::= { gx2Em870AnalogEntry 13}

		em870uomOmiOffset             OBJECT-TYPE
			   SYNTAX           DisplayString (SIZE (0..80))
			   ACCESS           read-only
			   STATUS           optional
			   DESCRIPTION
			   "The value of this object provides the Unit of Measure of the
			    RF Input Power Analog parameter.."
			   ::= { gx2Em870AnalogEntry 14}

		em870majorHighOmiOffset       OBJECT-TYPE
			   SYNTAX           Float 
			   ACCESS           read-only
			   STATUS           mandatory
			   DESCRIPTION
			   "The value of this object provides the Major High alarm value
			    of the Optical Power  Analog parameter.
			   This value is a floating point number that is represented as an IEEE 32 bit number."
			   ::= { gx2Em870AnalogEntry 15}


		em870majorLowOmiOffset        OBJECT-TYPE
			   SYNTAX           Float 
			   ACCESS           read-only
			   STATUS           mandatory
			   DESCRIPTION
			   "The value of this object provides the Major Low alarm value
			    of the RF Input Power Analog parameter.
			   This value is a floating point number that is represented as an IEEE 32 bit number."
			   ::= { gx2Em870AnalogEntry 16}

		em870minorHighOmiOffset       OBJECT-TYPE
			   SYNTAX           Float
			   ACCESS           read-only
			   STATUS           mandatory
			   DESCRIPTION
			   "The value of this object provides the Minor High alarm value
			    of the RF Input Power Analog parameter.
			   This value is a floating point number that is represented as an IEEE 32 bit number."
			   ::= { gx2Em870AnalogEntry 17}

		em870minorLowOmiOffset        OBJECT-TYPE
			   SYNTAX           Float 
			   ACCESS           read-only
			   STATUS           mandatory
			   DESCRIPTION
			   "The value of this object provides the Minor Low alarm value
			    of the RF Input Power Analog parameter.
			   This value is a floating point number that is represented as an IEEE 32 bit number."
			   ::= { gx2Em870AnalogEntry 18}

		em870currentValueOmiOffset    OBJECT-TYPE
			   SYNTAX           Float 
			   ACCESS           read-only
			   STATUS           mandatory
			   DESCRIPTION
			   "The value of this object provides the Current value
			    of the RF Input Power Analog parameter.
			   This value is a floating point number that is represented as an IEEE 32 bit number.
			   +99 dB or -99 dB will be reported for this value when outside the min/max operating 
			   range."
			   ::= { gx2Em870AnalogEntry 19}

		em870stateFlagOmiOffset       OBJECT-TYPE
			   SYNTAX           INTEGER
								{
								hidden(1),
								read-only(2),
								updateable(3)
								}
			   ACCESS           read-only
			   STATUS           mandatory
			   DESCRIPTION
			   "The value of this object provides the state
			    of the RF Input Power Analog parameter. (0-Hidden	
			          1-Read-Only, 2-Updateable)."
			   ::= { gx2Em870AnalogEntry 20}

		em870minValueOmiOffset        OBJECT-TYPE
			   SYNTAX           Float
			   ACCESS           read-only
			   STATUS           mandatory
			   DESCRIPTION
			   "The value of this object provides the minimum value
			    the RF Input Power Analog parameter can achive.
	   		   This value is a floating point number that is represented as an IEEE 32 bit number."
			   ::= { gx2Em870AnalogEntry 21}

		em870maxValueOmiOffset        OBJECT-TYPE
			   SYNTAX           Float
			   ACCESS           read-only
			   STATUS           mandatory
			   DESCRIPTION
			   "The value of this object provides the maximum value
			    the RF Input Power Analog parameter can achive.
			   This value is a floating point number that is represented as an IEEE 32 bit number."
			   ::= { gx2Em870AnalogEntry 22}

		em870alarmStateOmiOffset      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Input Power Analog parameter."
			   ::= { gx2Em870AnalogEntry 23}
-- New Parameter

		em870labelDFBPower            OBJECT-TYPE
			   SYNTAX           DisplayString (SIZE (0..80))
			   ACCESS           read-only
			   STATUS           optional
			   DESCRIPTION
			   "The value of this object provides the label of the
			    DFB Output Power Current Analog parameter."
			   ::= { gx2Em870AnalogEntry 24}

		em870uomDFBPower              OBJECT-TYPE
			   SYNTAX           DisplayString (SIZE (0..80))
			   ACCESS           read-only
			   STATUS           optional
			   DESCRIPTION
			   "The value of this object provides the Unit of Measure of the
			    DFB Output Power Analog parameter."
			   ::= { gx2Em870AnalogEntry 25}

		em870majorHighDFBPower        OBJECT-TYPE
			   SYNTAX           Float 
			   ACCESS           read-only
			   STATUS           mandatory
			   DESCRIPTION
			   "The value of this object provides the Major High alarm value
			    of the DFB Output Power Analog parameter.
			   This value is a floating point number that is represented as an IEEE 32 bit number."
			   ::= { gx2Em870AnalogEntry 26}


		em870majorLowDFBPower         OBJECT-TYPE
			   SYNTAX           Float 
			   ACCESS           read-only
			   STATUS           mandatory
			   DESCRIPTION
			   "The value of this object provides the Major Low alarm value
			    of the DFB Output Power Analog parameter.
			   This value is a floating point number that is represented as an IEEE 32 bit number."
			   ::= { gx2Em870AnalogEntry 27}

		em870minorHighDFBPower        OBJECT-TYPE
			   SYNTAX           Float
			   ACCESS           read-only
			   STATUS           mandatory
			   DESCRIPTION
			   "The value of this object provides the Minor High alarm value
			    of the DFB Output Power Analog parameter.
			   This value is a floating point number that is represented as an IEEE 32 bit number."
			   ::= { gx2Em870AnalogEntry 28}

		em870minorLowDFBPower         OBJECT-TYPE
			   SYNTAX           Float 
			   ACCESS           read-only
			   STATUS           mandatory
			   DESCRIPTION
			   "The value of this object provides the Minor Low alarm value
			    of the DFB Output Power Analog parameter.
			   This value is a floating point number that is represented as an IEEE 32 bit number."
			   ::= { gx2Em870AnalogEntry 29}

		em870currentValueDFBPower     OBJECT-TYPE
			   SYNTAX           Float 
			   ACCESS           read-only
			   STATUS           mandatory
			   DESCRIPTION
			   "The value of this object provides the Current value
			    of the DFB Output Power Analog parameter.
			   This value is a floating point number that is represented as an IEEE 32 bit number."
			   ::= { gx2Em870AnalogEntry 30}

		em870stateFlagDFBPower        OBJECT-TYPE
			   SYNTAX           INTEGER
								{
								hidden(1),
								read-only(2),
								updateable(3)
								}
			   ACCESS           read-only
			   STATUS           mandatory
			   DESCRIPTION
			   "The value of this object provides the state
			    of the DFB Output Power Analog parameter. (0-Hidden	
			          1-Read-Only, 2-Updateable)."
			   ::= { gx2Em870AnalogEntry 31}

		em870minValueDFBPower         OBJECT-TYPE
			   SYNTAX           Float
			   ACCESS           read-only
			   STATUS           mandatory
			   DESCRIPTION
			   "The value of this object provides the minimum value
			    the DFB Output Power Analog parameter can achive.
			   This value is a floating point number that is represented as an IEEE 32 bit number."
			   ::= { gx2Em870AnalogEntry 32}

		em870maxValueDFBPower         OBJECT-TYPE
			   SYNTAX           Float
			   ACCESS           read-only
			   STATUS           mandatory
			   DESCRIPTION
			   "The value of this object provides the maximum value
			    the DFB Output Power Analog parameter can achive.
   			   This value is a floating point number that is represented as an IEEE 32 bit number."
			   ::= { gx2Em870AnalogEntry 33}

		em870alarmStateDFBPower       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the DFB Output Power Analog parameter."
			   ::= { gx2Em870AnalogEntry 34}


-- New Parameter

		em870labelLaserBias            OBJECT-TYPE
			   SYNTAX           DisplayString (SIZE (0..80))
			   ACCESS           read-only
			   STATUS           optional
			   DESCRIPTION
			   "The value of this object provides the label of the
			    Laser Bias Current Analog parameter."
			   ::= { gx2Em870AnalogEntry 35}

		em870uomLaserBias              OBJECT-TYPE
			   SYNTAX           DisplayString (SIZE (0..80))
			   ACCESS           read-only
			   STATUS           optional
			   DESCRIPTION
			   "The value of this object provides the Unit of Measure of the
			    Laser Bias Analog parameter."
			   ::= { gx2Em870AnalogEntry 36}

		em870majorHighLaserBias        OBJECT-TYPE
			   SYNTAX           Float 
			   ACCESS           read-only
			   STATUS           mandatory
			   DESCRIPTION
			   "The value of this object provides the Major High alarm value
			    of the Laser Bias Analog parameter.
			   This value is a floating point number that is represented as an IEEE 32 bit number."
			   ::= { gx2Em870AnalogEntry 37}


		em870majorLowLaserBias         OBJECT-TYPE
			   SYNTAX           Float 
			   ACCESS           read-only
			   STATUS           mandatory
			   DESCRIPTION
			   "The value of this object provides the Major Low alarm value
			    of the Laser Bias Analog parameter.
			   This value is a floating point number that is represented as an IEEE 32 bit number."
			   ::= { gx2Em870AnalogEntry 38}

		em870minorHighLaserBias        OBJECT-TYPE
			   SYNTAX           Float
			   ACCESS           read-only
			   STATUS           mandatory
			   DESCRIPTION
			   "The value of this object provides the Minor High alarm value
			    of the Laser Bias Analog parameter.
			   This value is a floating point number that is represented as an IEEE 32 bit number."
			   ::= { gx2Em870AnalogEntry 39}

		em870minorLowLaserBias         OBJECT-TYPE
			   SYNTAX           Float 
			   ACCESS           read-only
			   STATUS           mandatory
			   DESCRIPTION
			   "The value of this object provides the Minor Low alarm value
			    of the Laser Bias Analog parameter.
			   This value is a floating point number that is represented as an IEEE 32 bit number."
			   ::= { gx2Em870AnalogEntry 40}

		em870currentValueLaserBias     OBJECT-TYPE
			   SYNTAX           Float 
			   ACCESS           read-only
			   STATUS           mandatory
			   DESCRIPTION
			   "The value of this object provides the Current value
			    of the Laser Bias Analog parameter.
			   This value is a floating point number that is represented as an IEEE 32 bit number."
			   ::= { gx2Em870AnalogEntry 41}

		em870stateFlagLaserBias        OBJECT-TYPE
			   SYNTAX           INTEGER
								{
								hidden(1),
								read-only(2),
								updateable(3)
								}
			   ACCESS           read-only
			   STATUS           mandatory
			   DESCRIPTION
			   "The value of this object provides the state
			    of the Laser Bias Analog parameter. (0-Hidden	
			          1-Read-Only, 2-Updateable)."
			   ::= { gx2Em870AnalogEntry 42}

		em870minValueLaserBias         OBJECT-TYPE
			   SYNTAX           Float
			   ACCESS           read-only
			   STATUS           mandatory
			   DESCRIPTION
			   "The value of this object provides the minimum value
			    the Laser Bias Analog parameter can achive.
			   This value is a floating point number that is represented as an IEEE 32 bit number."
			   ::= { gx2Em870AnalogEntry 43}

		em870maxValueLaserBias         OBJECT-TYPE
			   SYNTAX           Float
			   ACCESS           read-only
			   STATUS           mandatory
			   DESCRIPTION
			   "The value of this object provides the maximum value
			    the Laser Bias Analog parameter can achive.
   			   This value is a floating point number that is represented as an IEEE 32 bit number."
			   ::= { gx2Em870AnalogEntry 44}

		em870alarmStateLaserBias       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Bias Analog parameter."
			   ::= { gx2Em870AnalogEntry 45}

-- New Parameter


		em870labelCoolerCurrent           OBJECT-TYPE
			   SYNTAX           DisplayString (SIZE (0..80))
			   ACCESS           read-only
			   STATUS           optional
			   DESCRIPTION
			   "The value of this object provides the label of the
			    Cooler Current Analog parameter."
			   ::= { gx2Em870AnalogEntry 46}

		em870uomCoolerCurrent             OBJECT-TYPE
			   SYNTAX           DisplayString (SIZE (0..80))
			   ACCESS           read-only
			   STATUS           optional
			   DESCRIPTION
			   "The value of this object provides the Unit of Measure of the
			    Cooler Current Analog parameter.."
			   ::= { gx2Em870AnalogEntry 47}

		em870majorHighCoolerCurrent       OBJECT-TYPE
			   SYNTAX           Float 
			   ACCESS           read-only
			   STATUS           mandatory
			   DESCRIPTION
			   "The value of this object provides the Major High alarm value
			    of the Cooler Current Analog parameter.
			   This value is a floating point number that is represented as an IEEE 32 bit number."
			   ::= { gx2Em870AnalogEntry 48}


		em870majorLowCoolerCurrent        OBJECT-TYPE
			   SYNTAX           Float 
			   ACCESS           read-only
			   STATUS           mandatory
			   DESCRIPTION
			   "The value of this object provides the Major Low alarm value
			    of the Cooler Current Analog parameter.
			   This value is a floating point number that is represented as an IEEE 32 bit number."
			   ::= { gx2Em870AnalogEntry 49}

		em870minorHighCoolerCurrent       OBJECT-TYPE
			   SYNTAX           Float
			   ACCESS           read-only
			   STATUS           mandatory
			   DESCRIPTION
			   "The value of this object provides the Minor High alarm value
			    of the Cooler Current Analog parameter.
			   This value is a floating point number that is represented as an IEEE 32 bit number."
			   ::= { gx2Em870AnalogEntry 50}

		em870minorLowCoolerCurrent        OBJECT-TYPE
			   SYNTAX           Float 
			   ACCESS           read-only
			   STATUS           mandatory
			   DESCRIPTION
			   "The value of this object provides the Minor Low alarm value
			    of the Cooler Current Analog parameter.
			   This value is a floating point number that is represented as an IEEE 32 bit number."
			   ::= { gx2Em870AnalogEntry 51}

		em870currentValueCoolerCurrent    OBJECT-TYPE
			   SYNTAX           Float 
			   ACCESS           read-only
			   STATUS           mandatory
			   DESCRIPTION
			   "The value of this object provides the Current value
			    of the Cooler Current Analog parameter.
			   This value is a floating point number that is represented as an IEEE 32 bit number."
			   ::= { gx2Em870AnalogEntry 52}

		em870stateFlagCoolerCurrent       OBJECT-TYPE
			   SYNTAX           INTEGER
								{
								hidden(1),
								read-only(2),
								updateable(3)
								}
			   ACCESS           read-only
			   STATUS           mandatory
			   DESCRIPTION
			   "The value of this object provides the state
			    of the Cooler Current Analog parameter. (0-Hidden	
			          1-Read-Only, 2-Updateable)."
			   ::= { gx2Em870AnalogEntry 53}

		em870minValueCoolerCurrent        OBJECT-TYPE
			   SYNTAX           Float
			   ACCESS           read-only
			   STATUS           mandatory
			   DESCRIPTION
			   "The value of this object provides the minimum value
			    the Cooler Current Analog parameter can achive.
	   		   This value is a floating point number that is represented as an IEEE 32 bit number."
			   ::= { gx2Em870AnalogEntry 54}

		em870maxValueCoolerCurrent        OBJECT-TYPE
			   SYNTAX           Float
			   ACCESS           read-only
			   STATUS           mandatory
			   DESCRIPTION
			   "The value of this object provides the maximum value
			    the Cooler Current Analog parameter can achive.
			   This value is a floating point number that is represented as an IEEE 32 bit number."
			   ::= { gx2Em870AnalogEntry 55}

		em870alarmStateCoolerCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Cooler Current Analog parameter."
			   ::= { gx2Em870AnalogEntry 56}

-- New Parameter

		em870labelLaserTemp            OBJECT-TYPE
			   SYNTAX           DisplayString (SIZE (0..80))
			   ACCESS           read-only
			   STATUS           optional
			   DESCRIPTION
			   "The value of this object provides the label of the
			    Laser Temp Analog parameter."
			   ::= { gx2Em870AnalogEntry 57}

		em870uomLaserTemp              OBJECT-TYPE
			   SYNTAX           DisplayString (SIZE (0..80))
			   ACCESS           read-only
			   STATUS           optional
			   DESCRIPTION
			   "The value of this object provides the Unit of Measure of the
			    Laser Temp Analog parameter."
			   ::= { gx2Em870AnalogEntry 58}

		em870majorHighLaserTemp        OBJECT-TYPE
			   SYNTAX           Float 
			   ACCESS           read-only
			   STATUS           mandatory
			   DESCRIPTION
			   "The value of this object provides the Major High alarm value
			    of the Laser Temp Analog parameter.
			   This value is a floating point number that is represented as an IEEE 32 bit number."
			   ::= { gx2Em870AnalogEntry 59}


		em870majorLowLaserTemp         OBJECT-TYPE
			   SYNTAX           Float 
			   ACCESS           read-only
			   STATUS           mandatory
			   DESCRIPTION
			   "The value of this object provides the Major Low alarm value
			    of the Laser Temp Analog parameter.
			   This value is a floating point number that is represented as an IEEE 32 bit number."
			   ::= { gx2Em870AnalogEntry 60}

		em870minorHighLaserTemp        OBJECT-TYPE
			   SYNTAX           Float
			   ACCESS           read-only
			   STATUS           mandatory
			   DESCRIPTION
			   "The value of this object provides the Minor High alarm value
			    of the Laser Temp Analog parameter.
			   This value is a floating point number that is represented as an IEEE 32 bit number."
			   ::= { gx2Em870AnalogEntry 61}

		em870minorLowLaserTemp         OBJECT-TYPE
			   SYNTAX           Float 
			   ACCESS           read-only
			   STATUS           mandatory
			   DESCRIPTION
			   "The value of this object provides the Minor Low alarm value
			    of the Laser Temp Analog parameter.
			   This value is a floating point number that is represented as an IEEE 32 bit number."
			   ::= { gx2Em870AnalogEntry 62}

		em870currentValueLaserTemp     OBJECT-TYPE
			   SYNTAX           Float 
			   ACCESS           read-only
			   STATUS           mandatory
			   DESCRIPTION
			   "The value of this object provides the Current value
			    of the Laser Temp Analog parameter.
			   This value is a floating point number that is represented as an IEEE 32 bit number."
			   ::= { gx2Em870AnalogEntry 63}

		em870stateFlagLaserTemp        OBJECT-TYPE
			   SYNTAX           INTEGER
								{
								hidden(1),
								read-only(2),
								updateable(3)
								}
			   ACCESS           read-only
			   STATUS           mandatory
			   DESCRIPTION
			   "The value of this object provides the state
			    of the Laser Temp Analog parameter. (0-Hidden	
			          1-Read-Only, 2-Updateable)."
			   ::= { gx2Em870AnalogEntry 64}

		em870minValueLaserTemp         OBJECT-TYPE
			   SYNTAX           Float
			   ACCESS           read-only
			   STATUS           mandatory
			   DESCRIPTION
			   "The value of this object provides the minimum value
			    the Laser TempAnalog parameter can achive.
			   This value is a floating point number that is represented as an IEEE 32 bit number."
			   ::= { gx2Em870AnalogEntry 65}

		em870maxValueLaserTemp         OBJECT-TYPE
			   SYNTAX           Float
			   ACCESS           read-only
			   STATUS           mandatory
			   DESCRIPTION
			   "The value of this object provides the maximum value
			    the Laser Temp Analog parameter can achive.
   			   This value is a floating point number that is represented as an IEEE 32 bit number."
			   ::= { gx2Em870AnalogEntry 66}

		em870alarmStateLaserTemp       OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Laser Temp Analog parameter."
			   ::= { gx2Em870AnalogEntry 67}

-- New Parameter

		em870labelModTemp              OBJECT-TYPE
			   SYNTAX           DisplayString (SIZE (0..80))
			   ACCESS           read-only
			   STATUS           optional
			   DESCRIPTION
			   "The value of this object provides the label of the
			    Module Temperature Analog parameter."
			   ::= { gx2Em870AnalogEntry 68}

		em870uomModTemp                OBJECT-TYPE
			   SYNTAX           DisplayString (SIZE (0..80))
			   ACCESS           read-only
			   STATUS           optional
			   DESCRIPTION
			   "The value of this object provides the Unit of Measure of the
			    Module Temperature Analog parameter."
			   ::= { gx2Em870AnalogEntry 69}

		em870majorHighModTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2Em870AnalogEntry 70}


		em870majorLowModTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2Em870AnalogEntry 71}

		em870minorHighModTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2Em870AnalogEntry 72}

		em870minorLowModTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2Em870AnalogEntry 73}

		em870currentValueModTemp       OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2Em870AnalogEntry 74}

		em870stateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2Em870AnalogEntry 75}

		em870minValueModTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2Em870AnalogEntry 76}

		em870maxValueModTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2Em870AnalogEntry 77}

		em870alarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Em870AnalogEntry 78}




-- New Parameter

		em870labelFanCurrent           OBJECT-TYPE
			   SYNTAX           DisplayString (SIZE (0..80))
			   ACCESS           read-only
			   STATUS           optional
			   DESCRIPTION
			   "The value of this object provides the label of the
			    Fan Current Analog parameter."
			   ::= { gx2Em870AnalogEntry 79}

		em870uomFanCurrent             OBJECT-TYPE
			   SYNTAX           DisplayString (SIZE (0..80))
			   ACCESS           read-only
			   STATUS           optional
			   DESCRIPTION
			   "The value of this object provides the Unit of Measure of the
			    Fan Current Analog parameter."
			   ::= { gx2Em870AnalogEntry 80}

		em870majorHighFanCurrent       OBJECT-TYPE
			   SYNTAX           Float 
			   ACCESS           read-only
			   STATUS           mandatory
			   DESCRIPTION
			   "The value of this object provides the Major High alarm value
			    of the Fan Current Analog parameter.
			   This value is a floating point number that is represented as an IEEE 32 bit number."
			   ::= { gx2Em870AnalogEntry 81}


		em870majorLowFanCurrent        OBJECT-TYPE
			   SYNTAX           Float 
			   ACCESS           read-only
			   STATUS           mandatory
			   DESCRIPTION
			   "The value of this object provides the Major Low alarm value
			    of the Fan Current Analog parameter.
			   This value is a floating point number that is represented as an IEEE 32 bit number."
			   ::= { gx2Em870AnalogEntry 82}

		em870minorHighFanCurrent       OBJECT-TYPE
			   SYNTAX           Float
			   ACCESS           read-only
			   STATUS           mandatory
			   DESCRIPTION
			   "The value of this object provides the Minor High alarm value
			    of the Fan Current Analog parameter.
			   This value is a floating point number that is represented as an IEEE 32 bit number."
			   ::= { gx2Em870AnalogEntry 83}

		em870minorLowFanCurrent        OBJECT-TYPE
			   SYNTAX           Float 
			   ACCESS           read-only
			   STATUS           mandatory
			   DESCRIPTION
			   "The value of this object provides the Minor Low alarm value
			    of the Fan Current Analog parameter.
			   This value is a floating point number that is represented as an IEEE 32 bit number."
			   ::= { gx2Em870AnalogEntry 84}

		em870currentValueFanCurrent    OBJECT-TYPE
			   SYNTAX           Float 
			   ACCESS           read-only
			   STATUS           mandatory
			   DESCRIPTION
			   "The value of this object provides the Current value
			    of the Fan Current Analog parameter.
			   This value is a floating point number that is represented as an IEEE 32 bit number."
			   ::= { gx2Em870AnalogEntry 85}

		em870stateFlagFanCurrent       OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2Em870AnalogEntry 86}

		em870minValueFanCurrent        OBJECT-TYPE
			   SYNTAX           Float
			   ACCESS           read-only
			   STATUS           mandatory
			   DESCRIPTION
			   "The value of this object provides the minimum value
			    the Fan Current Analog parameter can achive.
			   This value is a floating point number that is represented as an IEEE 32 bit number."
			   ::= { gx2Em870AnalogEntry 87}

		em870maxValueFanCurrent        OBJECT-TYPE
			   SYNTAX           Float
			   ACCESS           read-only
			   STATUS           mandatory
			   DESCRIPTION
			   "The value of this object provides the maximum value
			    the Fan Current Analog parameter can achive.
			   This value is a floating point number that is represented as an IEEE 32 bit number."
			   ::= { gx2Em870AnalogEntry 88}

		em870alarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Em870AnalogEntry 89}

-- New Parameter

		em870label12Volt               OBJECT-TYPE
			   SYNTAX           DisplayString (SIZE (0..80))
			   ACCESS           read-only
			   STATUS           optional
			   DESCRIPTION
			   "The value of this object provides the label of the
			    12v Current Analog parameter."
			   ::= { gx2Em870AnalogEntry 90}

		em870uom12Volt                 OBJECT-TYPE
			   SYNTAX           DisplayString (SIZE (0..80))
			   ACCESS           read-only
			   STATUS           optional
			   DESCRIPTION
			   "The value of this object provides the Unit of Measure of the
			    12v Current Analog parameter."
			   ::= { gx2Em870AnalogEntry 91}

		em870majorHigh12Volt           OBJECT-TYPE
			   SYNTAX           Float 
			   ACCESS           read-only
			   STATUS           mandatory
			   DESCRIPTION
			   "The value of this object provides the Major High alarm value
			    of the 12v Current Analog parameter.
			   This value is a floating point number that is represented as an IEEE 32 bit number."
			   ::= { gx2Em870AnalogEntry 92}


		em870majorLow12Volt            OBJECT-TYPE
			   SYNTAX           Float 
			   ACCESS           read-only
			   STATUS           mandatory
			   DESCRIPTION
			   "The value of this object provides the Major Low alarm value
			    of the 12v Current Analog parameter.
			   This value is a floating point number that is represented as an IEEE 32 bit number."
			   ::= { gx2Em870AnalogEntry 93}

		em870minorHigh12Volt           OBJECT-TYPE
			   SYNTAX           Float
			   ACCESS           read-only
			   STATUS           mandatory
			   DESCRIPTION
			   "The value of this object provides the Minor High alarm value
			    of the 12v Current Analog parameter.
			   This value is a floating point number that is represented as an IEEE 32 bit number."
			   ::= { gx2Em870AnalogEntry 94}

		em870minorLow12Volt            OBJECT-TYPE
			   SYNTAX           Float 
			   ACCESS           read-only
			   STATUS           mandatory
			   DESCRIPTION
			   "The value of this object provides the Minor Low alarm value
			    of the 12v Current Analog parameter.
			   This value is a floating point number that is represented as an IEEE 32 bit number."
			   ::= { gx2Em870AnalogEntry 95}

		em870currentValue12Volt        OBJECT-TYPE
			   SYNTAX           Float 
			   ACCESS           read-only
			   STATUS           mandatory
			   DESCRIPTION
			   "The value of this object provides the Current value
			    of the 12v Current Analog parameter.
			   This value is a floating point number that is represented as an IEEE 32 bit number."
			   ::= { gx2Em870AnalogEntry 96}

		em870stateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2Em870AnalogEntry 97}

		em870minValue12Volt            OBJECT-TYPE
			   SYNTAX           Float
			   ACCESS           read-only
			   STATUS           mandatory
			   DESCRIPTION
			   "The value of this object provides the minimum value
			    the 12v Current Analog parameter can achive.
			   This value is a floating point number that is represented as an IEEE 32 bit number."
			   ::= { gx2Em870AnalogEntry 98}

		em870maxValue12Volt            OBJECT-TYPE
			   SYNTAX           Float
			   ACCESS           read-only
			   STATUS           mandatory
			   DESCRIPTION
			   "The value of this object provides the maximum value
			    the 12v Current Analog parameter can achive.
			   This value is a floating point number that is represented as an IEEE 32 bit number."
			   ::= { gx2Em870AnalogEntry 99}

		em870alarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2Em870AnalogEntry 100}

-- ************************ Digital parameters **********************************

-- NONE

-- *********** STATUS *****************
		gx2Em870StatusTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2Em870StatusEntry 1}

--New Parameter
		em870labelBoot               	OBJECT-TYPE
			   SYNTAX       		DisplayString (SIZE (0..80))         
			   ACCESS           	read-only
			   STATUS           	optional
			   DESCRIPTION
			   "The value of this object provides the label of the
			    Boot Status  Status parameter."
			   ::= { gx2Em870StatusEntry 2}

		em870valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Em870StatusEntry 3}

		em870stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Em870StatusEntry  4}



--New Parameter
		em870labelFlash               	OBJECT-TYPE
			   SYNTAX       		DisplayString (SIZE (0..80))         
			   ACCESS           	read-only
			   STATUS           	optional
			   DESCRIPTION
			   "The value of this object provides the label of the
			    Flash Status  Status parameter."
			   ::= { gx2Em870StatusEntry 5}

		em870valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Em870StatusEntry 6}

		em870stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Em870StatusEntry  7}

--New Parameter
		em870labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Em870StatusEntry 8}

		em870valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Em870StatusEntry 9}

		em870stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Em870StatusEntry  10}


--New Parameter
		em870labelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2Em870StatusEntry 11}

		em870valueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Em870StatusEntry 12}

		em870stateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Em870StatusEntry  13}


            -- ************ FACTORY DATA ****************
		gx2Em870FactoryTableIndex			OBJECT-TYPE
			   SYNTAX				INTEGER (1..4294967295)
			   ACCESS				read-only
			   STATUS				mandatory
			   DESCRIPTION			
			   "The value of this object identifies the network
			    element. This index is equal to the
			    hfcCommonTableIndex for the same element."
			   ::= { gx2Em870FactoryEntry 1}

		em870bootControlByte          	OBJECT-TYPE
			   SYNTAX       		INTEGER
			   ACCESS           	read-only
			   STATUS           	mandatory
			   DESCRIPTION
			   "The value of this object indicates which bank the firmware
			    is currently being boot from."
			   ::= { gx2Em870FactoryEntry 2}

		em870bootStatusByte          	OBJECT-TYPE
			   SYNTAX       		INTEGER
			   ACCESS           	read-only
			   STATUS           	mandatory
			   DESCRIPTION
			   "This object indicates the status of the last boot"
			   ::= { gx2Em870FactoryEntry 3}

		em870bank1CRC          		OBJECT-TYPE
			   SYNTAX       		INTEGER
			   ACCESS           	read-only
			   STATUS           	mandatory
			   DESCRIPTION
			   "This object provides the CRC code of bank 0."
			   ::= { gx2Em870FactoryEntry 4}

		em870bank2CRC          		OBJECT-TYPE
			   SYNTAX       		INTEGER
			   ACCESS           	read-only
			   STATUS           	mandatory
			   DESCRIPTION
			   "This object provides the CRC code of bank 1."
			   ::= { gx2Em870FactoryEntry 5}

		em870prgEEPROMByte          		OBJECT-TYPE
			   SYNTAX       		INTEGER
			   ACCESS           	read-only
			   STATUS           	mandatory
			   DESCRIPTION
			   "This object indicates if the EEPROM has been programmed"
			   ::= { gx2Em870FactoryEntry 6}

		em870factoryCRC          		OBJECT-TYPE
			   SYNTAX       		INTEGER
			   ACCESS           	read-only
			   STATUS           	mandatory
			   DESCRIPTION
			   "This object provides the CRC code for the Factory data."
			   ::= { gx2Em870FactoryEntry 7}

		em870calculateCRC          		OBJECT-TYPE
			   SYNTAX       		INTEGER
					    		{
							factory(1),
							na(2),
							alarm(3)
					    		}
			   ACCESS           	read-only
			   STATUS           	mandatory
			   DESCRIPTION
			   "This object indicates which of the Emnums will have the CRC calculated."
			   ::= { gx2Em870FactoryEntry 8}

		em870hourMeter          		OBJECT-TYPE
			   SYNTAX       		INTEGER
			   ACCESS           	read-only
			   STATUS           	mandatory
			   DESCRIPTION
			   "This object provides the hour meter reading of the module."
			   ::= { gx2Em870FactoryEntry 9}

		em870flashPrgCntA          		OBJECT-TYPE
			   SYNTAX       		INTEGER
			   ACCESS           	read-only
			   STATUS           	mandatory
			   DESCRIPTION
			   "This object provides the number of times Bank 1 flash has been 
                      programmed."
			   ::= { gx2Em870FactoryEntry 10}

		em870flashPrgCntB          		OBJECT-TYPE
			   SYNTAX       		INTEGER
			   ACCESS           	read-only
			   STATUS           	mandatory
			   DESCRIPTION
			   "This object provides the number of times Bank 1 flash has been 
                      programmed."
			   ::= { gx2Em870FactoryEntry 11}

		em870flashBankARev          		OBJECT-TYPE
			   SYNTAX       		DisplayString (SIZE (0..80))
			   ACCESS           	read-only
			   STATUS           	mandatory
			   DESCRIPTION
			   "This object provides the revision of flash bank 0."
			   ::= { gx2Em870FactoryEntry 12}

		em870flashBankBRev          		OBJECT-TYPE
			   SYNTAX       		DisplayString (SIZE (0..80))
			   ACCESS           	read-only
			   STATUS           	mandatory
			   DESCRIPTION
			   "This object provides the revision of flash bank 1."
			   ::= { gx2Em870FactoryEntry 13}



-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                        EM870 Module traps
-- **************************************************************************
   trapEM870ConfigChangeInteger TRAP-TYPE
       ENTERPRISE gx2Em870
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapEM870ConfigChangeDisplayString TRAP-TYPE
       ENTERPRISE gx2Em870
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2

  trapEM870FanCurrentAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Fan Current 
	 parameter goes out of range.
	 trapAdditionalInfoInteger variable contains current reading of 
	 the this parameter."
  ::= 3

  trapEM87012vAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules 12 Volt parameter goes out of range.
	 trapAdditionalInfoInteger variable contains current reading of 
	 the this parameter."
  ::= 4

  trapEM870ModuleTempAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Module Temperature goes out of range."
  ::= 5

  trapEM870OmiOffsetAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules OMI level parameter 
	 goes out of range.
	 trapAdditionalInfoInteger variable contains current reading of 
	 the this parameter."
  ::= 6

  trapEM870OpticalOutputPowerAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Optical Output power parameter 
	 goes out of range.
	 trapAdditionalInfoInteger variable contains current reading of 
	 the this parameter."
  ::= 7

  trapEM870FlashAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error during
	Flash memory operations."
  ::= 8

  trapEM870BankBootAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules detects an error while booting
	from bank 0 or bank 1."
  ::= 9

	trapEM870AlarmDataCRCAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 10

	trapEM870FactoryDataCRCAlarm TRAP-TYPE
	ENTERPRISE gx2Em870
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 11

  END
