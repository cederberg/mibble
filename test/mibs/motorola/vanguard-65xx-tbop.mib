-- Version 1.5, modified 02/12/98

        TBOP-OPT-MIB DEFINITIONS ::= BEGIN

        IMPORTS
            Counter
                FROM RFC1155-SMI

            OBJECT-TYPE
                FROM RFC-1212;

        -- Codex MIB Group definitions

                  codex OBJECT IDENTIFIER ::= { enterprises 449 }
         cdxProductSpecific OBJECT IDENTIFIER ::= { codex 2 }
                cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

        cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

          cdx6500Controls OBJECT IDENTIFIER ::= { cdx6500 4 }

        -- Textual conventions

        Counter16 ::= INTEGER (0..65535)

        DisplayString ::= OCTET STRING


        -- The TBOP Port Configuration Table

        cdx6500PPCTTBOPPortTable OBJECT-TYPE
            SYNTAX SEQUENCE OF Cdx6500PPCTTBOPPortEntry
            ACCESS not-accessible
            STATUS mandatory
            DESCRIPTION
                "This table contains TBOP Port configuration parameters."
        ::= { cdx6500PCTPortProtocolGroup 7 }

        cdx6500PPCTTBOPPortEntry OBJECT-TYPE
            SYNTAX Cdx6500PPCTTBOPPortEntry
            ACCESS not-accessible
            STATUS mandatory
            DESCRIPTION
                "Each PortEntry contains the configuration
                 parameters for one TBOP port."
            INDEX { cdx6500TBOPCfgPortNumber }
        ::= { cdx6500PPCTTBOPPortTable 1 }

        Cdx6500PPCTTBOPPortEntry ::=
            SEQUENCE {
                cdx6500TBOPCfgPortNumber
                    INTEGER,
                cdx6500TBOPCfgPortEIAOpt
                    INTEGER,
                cdx6500TBOPCfgPortClockType
                    INTEGER,
                cdx6500TBOPCfgPortClockSpeed
                    INTEGER,
                cdx6500TBOPCfgPortTxCoding
                    INTEGER,
                cdx6500TBOPCfgPortByteCount
                    INTEGER,
                cdx6500TBOPCfgPortOptions
                    INTEGER,
                cdx6500TBOPCfgPortRTSCTSDelay
                    INTEGER,
                cdx6500TBOPCfgPortDcdOnDelay
                    INTEGER,
                cdx6500TBOPCfgPortAutoCallMnem
                    DisplayString,
                cdx6500TBOPCfgPortAutoCallTO
                    INTEGER,
                cdx6500TBOPCfgPortMaxAutoTries
                    INTEGER,
                cdx6500TBOPCfgPortSubAddress
                    DisplayString,
                cdx6500TBOPCfgPortCUG
                    DisplayString,
                cdx6500TBOPCfgPortEnableBill
                    INTEGER
                }
        
        cdx6500TBOPCfgPortNumber OBJECT-TYPE
            SYNTAX INTEGER (1..54)
            ACCESS read-only
            STATUS mandatory
            DESCRIPTION
                "Port number of the port being used by TBOP."
        ::= { cdx6500PPCTTBOPPortEntry 1 }
        
        cdx6500TBOPCfgPortEIAOpt OBJECT-TYPE
            SYNTAX INTEGER {
                    simp       (0),
                    dtr        (1),
                    dtrd       (2),
                    dtrp       (8),
                    newvalSimp (50)
                    }
            ACCESS read-only
            STATUS mandatory
            DESCRIPTION
                "Specifies the control signal handshake and clocking
                 required for a connection to be made to this port
                 legal values are :
                 simp   - Simple, no control signals required.
                 dtr    - Dedicated, require the data terminal ready
                          signal (DTR).
                 dtrd   - Same as DTR, except data set ready (DSR)
                          drops between calls.
                 dtrp  -  Same as DTR, except DSR/DCD/CTS are held
                          low in the idle state.
                 newvalSimp - same functionality as 'simp', new enumeration
                          added for RFC1155 compatibility."
        ::= { cdx6500PPCTTBOPPortEntry 2 }
        
        cdx6500TBOPCfgPortClockType OBJECT-TYPE
            SYNTAX INTEGER {
                    int       (0),
                    ext       (1),
                    newvalInt (50)
                    }
            ACCESS read-only
            STATUS mandatory
            DESCRIPTION
                "int - internal clock source.
                 ext - external clock source.
                 newval - same functionality as 'int', new enumeration
                       added for RFC1155 compatibility."
        ::= { cdx6500PPCTTBOPPortEntry 3 }
        
        cdx6500TBOPCfgPortClockSpeed OBJECT-TYPE
            SYNTAX INTEGER (1200..384000)
            ACCESS read-only
            STATUS mandatory
            DESCRIPTION
                "This is the speed of the port in bits per second,
                 Clock Source = int."
        ::= { cdx6500PPCTTBOPPortEntry 4 }
        
        cdx6500TBOPCfgPortTxCoding OBJECT-TYPE
            SYNTAX INTEGER {
                    nrz       (0),
                    nrzi      (1),
                    newvalNrz (50)
                    }
            ACCESS read-only
            STATUS mandatory
            DESCRIPTION
                "This is the data encoding used on the TBOP port.
                 nrz  - Non Return to Zero.
                 nrzi - Non Return to Zero Inverted.
                 newvalNrz - same functionality as 'nrz', new enumeration
                        added for RFC1155 compatibility."
        ::= { cdx6500PPCTTBOPPortEntry 5 }
        
        cdx6500TBOPCfgPortByteCount OBJECT-TYPE
            SYNTAX INTEGER (126..1036)
            ACCESS read-only
            STATUS mandatory
            DESCRIPTION
                "This is the number of bytes collected from the line
                 before data is forwarded. Legal values are :
                 126, 254, 382, 510, 638, 766, 894, and 1036"
        ::= { cdx6500PPCTTBOPPortEntry 6 }
        
        cdx6500TBOPCfgPortEIASigAction OBJECT-TYPE
            SYNTAX DisplayString (SIZE(3..15))
            ACCESS read-only
            STATUS mandatory
            DESCRIPTION
                "This specifies the EIA signaling actions allowed on
                 the port:
                 NONE   - none
                 SWITCH - switched carrier
                 CTS    - raise CTS in response to RTS
                 A combination of CTS and SWITCH may be specified by summing
                 (e.g. SWITCH+CTS)."
        ::= { cdx6500PPCTTBOPPortEntry 7 }
        
        cdx6500TBOPCfgPortOptions OBJECT-TYPE
            SYNTAX INTEGER {
                    none       (0),  
                    marki      (1),
                    cbr        (2),
                    newvalNone (50),
                    nc         (100)
                    }
            ACCESS read-only
            STATUS mandatory
            DESCRIPTION
                "Select options on this TBOP port as follows:
                 none  - port uses flag idle between frame exchanges and
                         operates with as little as 2 idle flags between
                         frames.   
                 marki - port uses mark idle between frame exchanges.
                         (Required by System 36 - AS/400 series).
                 cbr   - for constant bit rate applications, the port operates
                         with as little as 1 idle flag between frames. Also,
                         if the outbound queue overflows, all frames on this
                         queue will be purged.
                 newvalNone - same functionality as 'none', new enumeration
                         added for RFC1155 compatibility.
                 nc    - parameter not configured."
        ::= { cdx6500PPCTTBOPPortEntry 8 }
        
        cdx6500TBOPCfgPortRTSCTSDelay OBJECT-TYPE
            SYNTAX INTEGER (2..200)
            ACCESS read-only
            STATUS mandatory
            DESCRIPTION
                "This specifies how long the TBOP port will delay CTS
                 after RTS is raised when EIA Signaling Action = CTS.
                 The delay is specified in 50 milliseconds units
                 (1 = 50 milliseconds)."
        ::= { cdx6500PPCTTBOPPortEntry 9 }
        
        cdx6500TBOPCfgPortDcdOnDelay OBJECT-TYPE
            SYNTAX INTEGER (1..255)
            ACCESS read-only
            STATUS mandatory
            DESCRIPTION
                "This specifies the length of time that DCD is held
                 high before data is transmitted to the attached
                 device. This is used when EIA Signaling Action = SWITCH.
                 The delay is specified in milliseconds."
        ::= { cdx6500PPCTTBOPPortEntry 10 }
        
        cdx6500TBOPCfgPortAutoCallMnem OBJECT-TYPE
            SYNTAX DisplayString (SIZE(0..8))
            ACCESS read-only
            STATUS mandatory
            DESCRIPTION
                "This mnemonic name is used for auto calling."
        ::= { cdx6500PPCTTBOPPortEntry 11 }
        
        cdx6500TBOPCfgPortAutoCallTO OBJECT-TYPE
            SYNTAX INTEGER (5..255)
            ACCESS read-only
            STATUS mandatory
            DESCRIPTION
                "This is the time interval in seconds between call
                 attempts when auto calling."
        ::= { cdx6500PPCTTBOPPortEntry 12 }
        
        cdx6500TBOPCfgPortMaxAutoTries OBJECT-TYPE
            SYNTAX INTEGER (0..255)
            ACCESS read-only
            STATUS mandatory
            DESCRIPTION
                "This specifies the number of times the TBOP port will
                 attempt to call. A value of 0 will allow unlimited attempts."
        ::= { cdx6500PPCTTBOPPortEntry 13 }
        
        cdx6500TBOPCfgPortSubAddress OBJECT-TYPE
            SYNTAX DisplayString (SIZE(0..3))
            ACCESS read-only
            STATUS mandatory
            DESCRIPTION
                "Calls addressed to this node, with this subaddress
                 will be routed to this TBOP port."
        ::= { cdx6500PPCTTBOPPortEntry 14 }
        
        cdx6500TBOPCfgPortCUG OBJECT-TYPE
            SYNTAX DisplayString (SIZE(2..23))
            ACCESS read-only
            STATUS mandatory
            DESCRIPTION
                "The TBOP port may be a member of up to 8 different
                 Closed User Groups. Each CUG membership must be a two
                 digit number (except --) and separated by a comma.
                 ( e.g. 12,34,56,09,02,03 ).
                 --    - No CUG Membership
                 00-99 - CUG Membership"
        ::= { cdx6500PPCTTBOPPortEntry 15 }
        
        cdx6500TBOPCfgPortEnableBill OBJECT-TYPE
            SYNTAX INTEGER {
                    off       (0),
                    on        (1),
                    newvalOff (50)
                    }
            ACCESS read-only
            STATUS mandatory
            DESCRIPTION
                "This controls whether billing (accounting) records
                 will be created for calls on this TBOP port.
                 newvalOff - same functionality as 'off', new enumeration
                 added for RFC1155 compatibility."
        ::= { cdx6500PPCTTBOPPortEntry 16 }

        -- TBOP Port Statistics

        cdx6500PPSTTBOPPortTable OBJECT-TYPE
            SYNTAX SEQUENCE OF Cdx6500PPSTTBOPPortEntry
            ACCESS not-accessible
            STATUS mandatory
            DESCRIPTION
                "This table holds statistics items for TBOP ports"
        ::= { cdx6500PSTPortProtocolGroup 7 }

        cdx6500PPSTTBOPPortEntry OBJECT-TYPE
            SYNTAX Cdx6500PPSTTBOPPortEntry
            ACCESS not-accessible
            STATUS mandatory
            DESCRIPTION
                "This entry holds the statistics items for one TBOP port."
            INDEX { cdx6500TBOPStPortNumber }
        ::= { cdx6500PPSTTBOPPortTable 1 }
        
        Cdx6500PPSTTBOPPortEntry ::=
            SEQUENCE {
                cdx6500TBOPStPortNumber
                    INTEGER,
                cdx6500TBOPStPortStatus
                    DisplayString,
                cdx6500TBOPStPortState
                    DisplayString,
                cdx6500TBOPStPortSpeed
                    INTEGER,
                cdx6500TBOPStOverrunErrors
                    Counter16,
                cdx6500TBOPStUnderrunErrors
                    Counter16,
                cdx6500TBOPStCRCErrors
                    Counter16,
                cdx6500TBOPStPortRxChars
                    Counter,
                cdx6500TBOPStPortRxCharsSec
                    INTEGER,
                cdx6500TBOPStPortRxFrames
                    Counter,
                cdx6500TBOPStPortRxFramesSec
                    INTEGER,
                cdx6500TBOPStPortTxChars
                    Counter,
                cdx6500TBOPStPortTxCharsSec
                    INTEGER,
                cdx6500TBOPStPortTxFrames
                    Counter,
                cdx6500TBOPStPortTxFramesSec
                    INTEGER,
                cdx6500TBOPStPortRxUtil
                    INTEGER,
                cdx6500TBOPStPortTxUtil
                    INTEGER,
                cdx6500TBOPStPortFramesQueued
                    Counter
                }
        
        cdx6500TBOPStPortNumber OBJECT-TYPE
            SYNTAX INTEGER (1..54)
            ACCESS read-only
            STATUS mandatory
            DESCRIPTION
                "The port number for this TBOP entry."
        ::= { cdx6500PPSTTBOPPortEntry 1 }

        cdx6500TBOPStPortStatus OBJECT-TYPE
            SYNTAX DisplayString (SIZE(2..8))
            ACCESS read-only
            STATUS mandatory
            DESCRIPTION
                "Specifies current port Status.
                 Up       : Port is enabled by the CTP
                 Disabled : Port is disabled by CTP
                 Busy Out : The port is busy out by the CTP
                 Down     : Port is not enabled disables, or busy
                            out by the CTP.
                 Note     : Port Status indicates Down state only if
                            the TBOP port CMEM record entry portEnable
                            gets corrupted. "
        ::= { cdx6500PPSTTBOPPortEntry 2 }

        cdx6500TBOPStPortState OBJECT-TYPE
            SYNTAX DisplayString (SIZE(0..30))
            ACCESS read-only
            STATUS mandatory
            DESCRIPTION
                "The EIA state of the port."
        ::= { cdx6500PPSTTBOPPortEntry 3 }
        
        cdx6500TBOPStPortSpeed OBJECT-TYPE
            SYNTAX INTEGER
            ACCESS read-only
            STATUS mandatory
            DESCRIPTION
                "The measured port speed in bits per second."
        ::= { cdx6500PPSTTBOPPortEntry 4 }        
        
        cdx6500TBOPStOverrunErrors OBJECT-TYPE
            SYNTAX Counter16
            ACCESS read-only
            STATUS mandatory
            DESCRIPTION
                "Total number of overrun errors counted by the I/O driver."
        ::= { cdx6500PPSTTBOPPortEntry 5 }

        cdx6500TBOPStUnderrunErrors OBJECT-TYPE
            SYNTAX Counter16
            ACCESS read-only
            STATUS mandatory
            DESCRIPTION
                "Total number of underrun errors counted by the I/O driver."
        ::= { cdx6500PPSTTBOPPortEntry 6 }

        cdx6500TBOPStCRCErrors OBJECT-TYPE
            SYNTAX Counter16
            ACCESS read-only
            STATUS mandatory
            DESCRIPTION
                "Total number of CRC errors counted by the I/O driver."
        ::= { cdx6500PPSTTBOPPortEntry 7 }

        cdx6500TBOPStPortRxChars OBJECT-TYPE
            SYNTAX Counter
            ACCESS read-only
            STATUS mandatory
            DESCRIPTION
                "Total number of data characters received since last boot
                 or statistics reset, header characters are not included."
        ::= { cdx6500PPSTTBOPPortEntry 8 }
        
        cdx6500TBOPStPortRxCharsSec OBJECT-TYPE
            SYNTAX INTEGER
            ACCESS read-only
            STATUS mandatory
            DESCRIPTION
                "The average number of characters received per second."
        ::= { cdx6500PPSTTBOPPortEntry 9 }
        
        cdx6500TBOPStPortRxFrames OBJECT-TYPE
            SYNTAX Counter
            ACCESS read-only
            STATUS mandatory
            DESCRIPTION
                "Total number of SDLC frames received since last boot
                 or statistices reset."
        ::= { cdx6500PPSTTBOPPortEntry 10 }
        
        cdx6500TBOPStPortRxFramesSec OBJECT-TYPE
            SYNTAX INTEGER
            ACCESS read-only
            STATUS mandatory
            DESCRIPTION
                "The average number of frames received per second."
        ::= { cdx6500PPSTTBOPPortEntry 11 }
        
        cdx6500TBOPStPortTxChars OBJECT-TYPE
            SYNTAX Counter
            ACCESS read-only
            STATUS mandatory
            DESCRIPTION
                "Total number of data characters transmitted since last boot
                 or statistics reset, header characters are not included."
        ::= { cdx6500PPSTTBOPPortEntry 12 }
        
        cdx6500TBOPStPortTxCharsSec OBJECT-TYPE
            SYNTAX INTEGER
            ACCESS read-only
            STATUS mandatory
            DESCRIPTION
                "The average number of characters transmitted per second."
        ::= { cdx6500PPSTTBOPPortEntry 13 }
        
        cdx6500TBOPStPortTxFrames OBJECT-TYPE
            SYNTAX Counter
            ACCESS read-only
            STATUS mandatory
            DESCRIPTION
                "Total number of SDLC frames trnsmitted since last boot or
                 statistics reset."
        ::= { cdx6500PPSTTBOPPortEntry 14 }
        
        cdx6500TBOPStPortTxFramesSec OBJECT-TYPE
            SYNTAX INTEGER
            ACCESS read-only
            STATUS mandatory
            DESCRIPTION
                "The average number of frames transmitted per second."
        ::= { cdx6500PPSTTBOPPortEntry 15 }
        
        cdx6500TBOPStPortRxUtil OBJECT-TYPE
            SYNTAX INTEGER (0..100)
            ACCESS read-only
            STATUS mandatory
            DESCRIPTION
                "Percentage of port receive bandwidth used."
        ::= { cdx6500PPSTTBOPPortEntry 16 }

        cdx6500TBOPStPortTxUtil OBJECT-TYPE
            SYNTAX INTEGER (0..100)
            ACCESS read-only
            STATUS mandatory
            DESCRIPTION
                "Percentage of port transmit bandwidth used."
        ::= { cdx6500PPSTTBOPPortEntry 17 }

        cdx6500TBOPStPortFramesQueued OBJECT-TYPE
            SYNTAX Counter
            ACCESS read-only
            STATUS mandatory
            DESCRIPTION
                "Number of SDLC frames queued to the I/O drivers."
        ::= { cdx6500PPSTTBOPPortEntry 18 }

        END
