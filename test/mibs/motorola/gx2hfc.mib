GX2HFC-MIB DEFINITIONS ::= BEGIN


    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger
					      FROM NLSBBN-TRAPS-MIB;


		-- This MIB module uses the extended OBJECT-TYPE macro as
		-- defined in RFC1212 and the TRAP-TYPE macro as defined
		-- in RFC 1215.

		--REVISION	"1" Jan 20, 2003
		--DESCRIPTION
		--		Added revision and description comment section

		-- This is the MIB module to manage  Hybrid Fiber Coax (HFC)
		-- subnetworks.

	hfc  OBJECT IDENTIFIER ::= {motproxies 1}

	hfcCommon OBJECT IDENTIFIER ::= { hfc 1}
	hfcDevices  OBJECT IDENTIFIER ::= { hfc 2}

		-- This MIB module contains the HFC common network information
		-- group and the HFC devices group.
		-- The HFC common network information group contains the
		-- HFC Common Table which gives the network topology
		-- and basic static information on all network elements contained in the network. 

		-- The HFC devices group contains per network element class a
		-- descriptor of the class with definitions of class specific
		-- parameters and a list of all network elements of this class that
		-- are currently contained in the network topology with their class
		-- specific parameters.
		
		-- The following values are defined for use as
		-- possible values of the device types that will be
		-- supported in the hybrid fiber coax systems.
		-- Each device type node is the root of a subtree consisting
		-- of two parts: the descriptor and the network elment list.
		-- Each device subtree may is defined a separate MIB module. This
		-- gives maximum MIB design flexibility including cases where
		-- that device is served directly by a resident agent and not
		-- by a proxy agent as is the case in this version of the
		-- HFC MIB.

--    **********************************************************************************

	gx2						OBJECT IDENTIFIER ::= {hfcDevices 1}
		-- gx2 control module Proxy Agent

	hfcUnknownType          OBJECT IDENTIFIER ::= {hfcDevices 2}
		-- An unknown type class.

	gx2Cm				OBJECT IDENTIFIER ::= {hfcDevices 3}
		-- GX2 Control Module GX2-Cm100.
	gx2Lm				OBJECT IDENTIFIER ::= {hfcDevices 4}
		-- GX2 Laser Module GX2-LM1000B.
	gx2Lmc			OBJECT IDENTIFIER ::= {hfcDevices 5}
		-- GX2 Laser Module GX2-LM1000C.
	gx2Rx200
				OBJECT IDENTIFIER ::= {hfcDevices 6}
		-- GX2 Return Path GX2-RX200
	gx2Psdc
				OBJECT IDENTIFIER ::= {hfcDevices 7}
		-- GX2 DC/AC Power Supply GX2-PSAC GX2-PSDC
	gx2Rsw200
				OBJECT IDENTIFIER ::= {hfcDevices 8}
		-- GX2 RF Switch GX2-RSW200
	gx2Rx1000
				OBJECT IDENTIFIER ::= {hfcDevices 9}
		-- GX2 Forward Path GX2-RX1000
	gx2Lm870C
				OBJECT IDENTIFIER ::= {hfcDevices 10}
		-- GX2 1310 FP XMTR GX2-LM870

	gx2EDFA
				OBJECT IDENTIFIER ::= {hfcDevices 11}
		-- GX2 1310 FPR GX2-EDFA

	gx2Em870
				OBJECT IDENTIFIER ::= {hfcDevices 12}
		-- GX2 1550 EM TX GX2-EM870

	gx2Drr3x
				OBJECT IDENTIFIER ::= {hfcDevices 13}
		-- GX2 Drr3X

	gx2Drr4x
				OBJECT IDENTIFIER ::= {hfcDevices 14}
		-- GX2 Drr4X

	gx2Osw10b
				OBJECT IDENTIFIER ::= {hfcDevices 15}
		-- GX2 Optical Switch GX2-OSW10B

	gx2Dm870
				OBJECT IDENTIFIER ::= {hfcDevices 16}
		-- GX2 1550 DM TX GX2-DM870

	gx2OA100BD
				OBJECT IDENTIFIER ::= {hfcDevices 17}
		-- GX2 GX2-OA100BD

	gx2Rsw1000b
				OBJECT IDENTIFIER ::= {hfcDevices 18}
		-- GX2 GX2-gx2Rsw1000b

	gx2Dm200
				OBJECT IDENTIFIER ::= {hfcDevices 19}
		-- GX2 1550 DM TX GX2-DM200

	gx2CEB
				OBJECT IDENTIFIER ::= {hfcDevices 20}
		-- GX2 COOL EMBEDDED BOARD

	gx2Drr2x
				OBJECT IDENTIFIER ::= {hfcDevices 21}
		-- GX2 DRR2X DIGITAL RETURN 

	gx2RFA1000
				OBJECT IDENTIFIER ::= {hfcDevices 22}
		-- GX2 GX2-gx2RFA1000

-- ***********************************************************************************
       --    HFC Common Network Information
       --
       -- This table contains common static information about the network elements
       -- that is independent from the fact that the network element is communicated
       -- to via a Proxy Agent.

	       hfcCommonTable                    OBJECT-TYPE
			 SYNTAX             SEQUENCE OF HfcCommonTableEntry
			 ACCESS             not-accessible
			 STATUS             mandatory
			 DESCRIPTION
			  "This table contains information on the HFC
			   network configuration. Each manageable piece
			   of equipment is defined by one row."
			 ::= { hfcCommon 1 }

	       hfcCommonTableEntry               OBJECT-TYPE
			 SYNTAX             HfcCommonTableEntry
			 ACCESS             not-accessible
			 STATUS             mandatory
			 DESCRIPTION
			  "This list contains information about a single piece
			   of equipment."
			 INDEX { hfcCommonTableIndex }
			 ::= { hfcCommonTable 1}

	       HfcCommonTableEntry    ::= SEQUENCE  
			 {
			 hfcCommonTableIndex			-- Device Table index
			    INTEGER (1..4294967295),
			 hfcUnitName				-- Current device name
			    DisplayString (SIZE (0..80)),
			 hfcUnitTypeDescriptorPointer		-- OID pointing at the device type 
			    OBJECT IDENTIFIER,
			 hfcUnitHwVersion				-- Hardware version number
			    DisplayString (SIZE (0..80)),
			 hfcUnitFwVersion				-- Firmware version number
			    DisplayString (SIZE (0..80)),
			 hfcUnitModelNumber				-- unique device model name (ex: gi_cm1_n)
			    DisplayString (SIZE (0..80)),
			 hfcUnitLocation				-- Headend, rack, shelf position
			    DisplayString (SIZE (0..80)),
			 hfcUnitSerialNumber			-- serial number of device
			    DisplayString (SIZE (0..80)),
			 hfcUnitAdministrativeState		-- Security:ready-only/operator/factory (always set to 2)
			    INTEGER,					
			 hfcUnitOperationalState		-- Always set to 1
			    INTEGER,
			 hfcUnitAlarmStatus			-- Overall status of the device
			    INTEGER,
			 hfcUnitAvailabilityStatus		-- Always set to 10
			    INTEGER,
			 hfcLogicalRfNetworkDescriptor	-- OID net used - always set to 0
			    OBJECT IDENTIFIER,
			 hfcUnitDetected				-- local time stamp - date and time
			    DisplayString (SIZE (0..20)),
			 hfcNELastTrapTimeStamp			-- Time stamp of last trap - always set to 0 
			    TimeTicks,
			 hfcPhysicalAddress			-- Physical address of device (IP address)
			    DisplayString (SIZE (0..80)),	
			 hfcDateCode				-- Date code
			    DisplayString (SIZE (0..80)),
		 	 hfcNeighbor1IPAddress           	-- Neighbor 1 address
			    DisplayString (SIZE (0..80)),
			 hfcNeighbor2IPAddress              -- Neighbor 2 address 
			    DisplayString (SIZE (0..80)),
			 hfcfinshedGoodsPartNumber          -- finshed goods part number
			    DisplayString (SIZE (0..80)),
			 hfcManufactureLocation		      -- manufacture location
			    DisplayString (SIZE (0..80)),
			 hfcDeviceSlotLocation
			    INTEGER,
			 hfcBelongsTo
			    DisplayString (SIZE (0..80)),
			 hfcModuleType
			    INTEGER,	
			 hfcDevicePositionData
			    INTEGER,
			 hfcExtendableSlotData
			    DisplayString (SIZE (0..80)),
			 hfcActualModelNumber			
			    DisplayString (SIZE (0..80))
							
			 }
			 

		hfcCommonTableIndex              OBJECT-TYPE
			SYNTAX              INTEGER (1..4294967295)
			ACCESS              read-only
			STATUS              mandatory
			DESCRIPTION
			"The value of this object identifies the network
			 element being proxied by the agent.  This index will be used 
			 in corresponding HFC device group table.
			 This index is sequential number."
			::= { hfcCommonTableEntry 1}


		hfcUnitName                 OBJECT-TYPE
			SYNTAX              DisplayString (SIZE (0..80))
			ACCESS              read-write
			STATUS              mandatory
			DESCRIPTION
			"The value of this object is the name of the network
			 element being proxied by the agent."
			::= { hfcCommonTableEntry 2}


		hfcUnitTypeDescriptorPointer     OBJECT-TYPE
			SYNTAX              OBJECT IDENTIFIER
			ACCESS              read-only
			STATUS              mandatory
			DESCRIPTION
			"The value of this object is pointer to the type descriptor
			 of the network element in the corresponding HFC device group table.
			This object is not used for GX2 devices."
			::= { hfcCommonTableEntry 3}


		hfcUnitHwVersion                 OBJECT-TYPE
			SYNTAX              DisplayString (SIZE (0..80))
			ACCESS              read-only
			STATUS              mandatory
			DESCRIPTION
			"The value of this object is the hardware version of
			 the network element being proxied by the agent."
			::= { hfcCommonTableEntry 4}


		hfcUnitFwVersion                 OBJECT-TYPE
			SYNTAX              DisplayString (SIZE (0..80))
			ACCESS              read-only
			STATUS              mandatory
			DESCRIPTION
			"The value of this object is the firmware version of
			 the network element being proxied by the agent."
			::= { hfcCommonTableEntry 5}


		hfcUnitModelNumber               OBJECT-TYPE
			SYNTAX              DisplayString (SIZE (0..80))
			ACCESS              read-only
			STATUS              mandatory
			DESCRIPTION
			"The value of this object is a unique device model name
			 for the network element being proxied by the agent."
			::= { hfcCommonTableEntry 6}

		hfcUnitLocation                  OBJECT-TYPE
			SYNTAX              DisplayString (SIZE (0..80))
			ACCESS              read-write
			STATUS              mandatory
			DESCRIPTION
			"The value of this object is the location of
			 the network element being proxied by the agent. The
			response string consistes of the Headend number, rack number
			and the shelf position. The parameters are seperated by a comma.
			The shelf position start from the top of the rack with a value of one."
			::= { hfcCommonTableEntry 7}

		hfcUnitSerialNumber              OBJECT-TYPE
			SYNTAX              DisplayString (SIZE (0..80))
			ACCESS              read-only
			STATUS              mandatory
			DESCRIPTION
			"The value of this object is the serial number of
			 the network element being proxied by the agent."
			::= { hfcCommonTableEntry 8}



		hfcUnitAdministrativeState       OBJECT-TYPE
			SYNTAX              INTEGER
					    {
					     readOnly(1),
					     operatorAccess(2),
					     factoryAccess(3)
					    }
			ACCESS              read-only
			STATUS              mandatory
			DESCRIPTION
			"The current Adminsitrative state of the network elment
			 is defined in ISO/IEC 10164-2."
			::= { hfcCommonTableEntry 9}


		hfcUnitOperationalState          OBJECT-TYPE
			SYNTAX              INTEGER
					    {
					     enabled(1),
					     disabled(2)
					    }
			ACCESS              read-only
			STATUS              mandatory
			DESCRIPTION
			"The current Operational state of the network elment
			 is defined in ISO/IEC 10164-2."
			::= { hfcCommonTableEntry 10}


		hfcUnitAlarmStatus               OBJECT-TYPE
			SYNTAX              INTEGER
					    {
					     ok(1),
					     undetermined(2),
					     warning(3),
					     minor(4),
					     major(5),
					     critical(6)
					     }
			ACCESS               read-only
			STATUS               mandatory
			DESCRIPTION
			"The of thihs object is the current alarm state of the network elment."
			::= { hfcCommonTableEntry 11}


		hfcUnitAvailabilityStatus        OBJECT-TYPE
			SYNTAX              INTEGER
					    {
					     inTest(1),
					     failed(2),
					     powerOff(3),
					     offLine(4),
					     offDuty(5),
					     dependency(6),
					     degraded(7),
					     notInstalled(8),
					     logFull(9),
					     available(10)
					    }
			ACCESS               read-only
			STATUS               mandatory
			DESCRIPTION
			"The of thihs object is the current Availability state of the network elment."
			::= { hfcCommonTableEntry 12}
				

		hfcLogicalRfNetworkDescriptor    OBJECT-TYPE
			SYNTAX                   OBJECT IDENTIFIER
			ACCESS                   read-only
			STATUS                   mandatory
			DESCRIPTION
			"The value of this object is the object identifier
			 of the descriptor containg the definition of the
			 relationship of this network element to logical
			 RF networks and elements. If such a descriptor
			 does not exist the value of this object is {0 0}."
			::= { hfcCommonTableEntry 13}


		hfcUnitDetected                  OBJECT-TYPE
			SYNTAX              DisplayString (SIZE (0..20))
			ACCESS              read-only
			STATUS              mandatory
			DESCRIPTION
			"The value of this object is the date and time when 
			 the network element was detected."
			::= { hfcCommonTableEntry 14}


		hfcNELastTrapTimeStamp           OBJECT-TYPE
			SYNTAX              TimeTicks
			ACCESS              read-only
			STATUS              mandatory
			DESCRIPTION
			"The value of this object is the date when the network
			 element was last updated."
			::= { hfcCommonTableEntry 15} 

		hfcPhysicalAddress                 OBJECT-TYPE
			SYNTAX              DisplayString (SIZE (0..80))
			ACCESS              read-only
			STATUS              mandatory
			DESCRIPTION
			"The value of this object is the Physical address of the
			 network element."
			::= { hfcCommonTableEntry 16} 

		hfcDateCode                 OBJECT-TYPE
			SYNTAX              DisplayString (SIZE (0..80))
			ACCESS              read-only
			STATUS              mandatory
			DESCRIPTION
			"The value of this object is the hardware version of
			 the network element Date code."
			::= { hfcCommonTableEntry 17}			

		hfcNeighbor1IPAddress                 OBJECT-TYPE
			SYNTAX              DisplayString (SIZE (0..80))
			ACCESS              read-only
			STATUS              mandatory
			DESCRIPTION
			"The value of this object is the IP address of
                  the network element Neighbor 1 - zero if not used."
			::= { hfcCommonTableEntry 18}			

		hfcNeighbor2IPAddress                 OBJECT-TYPE
			SYNTAX              DisplayString (SIZE (0..80))
			ACCESS              read-only
			STATUS              mandatory
			DESCRIPTION
			"The value of this object is the IP address of
                  the network element Neighbor 2 - zero if not used."
			::= { hfcCommonTableEntry 19}			

		hfcfinshedGoodsPartNumber                 OBJECT-TYPE
			SYNTAX              DisplayString (SIZE (0..80))
			ACCESS              read-only
			STATUS              mandatory
			DESCRIPTION
			"The value of this object is the finshed goods
			part number of the network element."
			::= { hfcCommonTableEntry 20}

		hfcManufactureLocation                 OBJECT-TYPE
			SYNTAX              DisplayString (SIZE (0..80))
			ACCESS              read-only
			STATUS              mandatory
			DESCRIPTION
			"The value of this object is the location where the 
			network element was manufactured."
			::= { hfcCommonTableEntry 21}

		hfcDeviceSlotLocation                 OBJECT-TYPE
			SYNTAX              INTEGER
			ACCESS              read-only
			STATUS              mandatory
			DESCRIPTION
			"The value of this object indicates which slot the
		      device in plugged into."
			::= { hfcCommonTableEntry 22}
	
		hfcBelongsTo			OBJECT-TYPE
			SYNTAX              DisplayString (SIZE (0..80))
			ACCESS              read-only
			STATUS              mandatory
			DESCRIPTION
			"The value of this object indicates which Control Module
			this device is control by. The value will be the serial number 
			of that Control Module"
			::= { hfcCommonTableEntry 23}

		 hfcModuleType		OBJECT-TYPE
			SYNTAX              INTEGER
			ACCESS              read-only
			STATUS              mandatory
			DESCRIPTION
			"The value of this object indicates the
		      device Model type number."
			::= { hfcCommonTableEntry 24}

		hfcDevicePositionData	  OBJECT-TYPE
			SYNTAX              INTEGER
			ACCESS              read-only
			STATUS              mandatory
			DESCRIPTION
			"The value of this object provides size and width informaton of the device.
			 The first byte of the data indicates the number of slots the device occupies.
			The second byte is the offset of the connector. It provides the position of where
			the connector is located on the back of the device. (0=left most position)"
			::= { hfcCommonTableEntry 25}

		
		hfcExtendableSlotData	  OBJECT-TYPE
			SYNTAX              DisplayString (SIZE (0..80))
			ACCESS              read-only
			STATUS              mandatory
			DESCRIPTION
			"The value of this object provides the location/side of the device.
			The first byte is the number of the slot the device occupies.
			The second byte is the depth of the device in the network. The last byte is
			the side of the device. 1=side A, 2=side B. ..."
			::= { hfcCommonTableEntry 26}

		hfcActualModelNumber	  OBJECT-TYPE
			SYNTAX              DisplayString (SIZE (0..80))
			ACCESS              read-only
			STATUS              mandatory
			DESCRIPTION
			"The value of this object is the actual device model name
			 for the network element being proxied by the agent."
			 ::= { hfcCommonTableEntry 27}
-- ****************************************************************************


-- **************************************************************************
--                          GX2 traps
-- **************************************************************************
   trapHfcNewNEFound TRAP-TYPE
       ENTERPRISE gx2
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	 "This trap is isssued if a Proxy Agent Detected A New NE.
	  trapPerceivedSeverity - 'indeterminate'
	  trapChangedObjectId - This points to the entry in the HFC common 
	  table for the new Network Element."
	  
  ::= 1


  trapHfcNewNELost TRAP-TYPE
       ENTERPRISE gx2
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is isssued if a Proxy Agent lost communication with NE. 
	 trapPerceivedSeverity - 'critical'
	 trapChangedObjectId - This points to the entry in the HFC common
	 table for the lost Network Element."
  ::= 2


  trapToBeSendQueueOverflow TRAP-TYPE
       ENTERPRISE gx2
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapNETrapLastTrapTimeStamp
	       }
       DESCRIPTION
	 "This trap is issued if SNMP agent's TrapToBeSendQueue is full.
	  trapPerceivedSeverity - 'major'
	  trapNetworkElemModelNumber - Model # of the Agent
	  trapNetworkElemSerialNum - Serial # of the Agent
	  trapNetworkElemOperState - from Ident MIB
	  trapNetworkElemAlarmStatus - from Ident MIB   
	  trapNetworkElemAdminState - from Ident MIB
	  trapNetworkElemAvailStatus - from Ident MIB"
  ::= 3

	trapHfcNameChange TRAP-TYPE
       	ENTERPRISE gx2
       	VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	 "This trap is isssued when an element name has changed."
	  
  ::= 4

END
