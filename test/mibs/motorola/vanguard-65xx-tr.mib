-- Version 1.3, modified 02/12/98

        TR-OPT-MIB DEFINITIONS ::= BEGIN

        IMPORTS 
            Counter
                FROM RFC1155-SMI          
            
            OBJECT-TYPE 
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual conventions
        MacAddress ::= OCTET STRING (SIZE (6))    

        DisplayString ::= OCTET STRING


        -- The Dot5 Configuration Table

        -- This table contains configuration information in addition
        -- to that included in RFC1321.

        cdx6500PPCTdot5PortTable OBJECT-TYPE
            SYNTAX SEQUENCE OF Cdx6500PPCTdot5PortEntry
            ACCESS not-accessible
            STATUS mandatory
            DESCRIPTION
                "This table contains Token Ring interface parameters and 
                 state variables, one entry per 802.5 interface."
        ::= { cdx6500PCTPortProtocolGroup 9 }

        cdx6500PPCTdot5PortEntry OBJECT-TYPE
            SYNTAX Cdx6500PPCTdot5PortEntry
            ACCESS not-accessible
            STATUS mandatory
            DESCRIPTION
                "A list of Token Ring status and parameter
                 values for an 802.5 interface."
            INDEX { cdx6500dot5IfIndex }
        ::= { cdx6500PPCTdot5PortTable 1 }

        Cdx6500PPCTdot5PortEntry ::= 
            SEQUENCE {
                cdx6500dot5IfIndex
                    INTEGER,
                cdx6500dot5LanCableType
                    INTEGER,
                cdx6500dot5PortMacAddress
                    MacAddress,
                cdx6500dot5LocalRingNumber
                    INTEGER,
                cdx6500dot5EarlyTokenRelease
                    INTEGER,
                cdx6500dot5TransmitQueueLimit
                    INTEGER
                }

        cdx6500dot5IfIndex OBJECT-TYPE
            SYNTAX INTEGER
            ACCESS read-only
            STATUS mandatory
            DESCRIPTION
                "This object is the port number for the LAN Interface."
        ::= { cdx6500PPCTdot5PortEntry 1 }

        cdx6500dot5LanCableType OBJECT-TYPE
            SYNTAX INTEGER {
                    utp       (0),
                    stp       (1),
                    unknown   (3),
                    newvalUtp (50)
                    }
            ACCESS read-only
            STATUS mandatory
            DESCRIPTION
                "Specifies the type of cable and therefore 
                 which connector is used for LAN interface.
                 utp       : Unshielded twisted pair
                 stp       : Shielded twisted pair.
                 newvalUtp : same functionality as 'utp', new enumeration
                             added for RFC1155 compatibility."
        ::= { cdx6500PPCTdot5PortEntry 2 }

        cdx6500dot5PortMacAddress OBJECT-TYPE
            SYNTAX MacAddress
            ACCESS read-only
            STATUS mandatory
            DESCRIPTION
                "Specifies the MAC address of the LAN port.
                 The entered value of 00-00-00-00-00-00
                 will be replaced by the Burned In Address
                 (BIA) if the LAN hardware is present."
        ::= { cdx6500PPCTdot5PortEntry 3 }

        cdx6500dot5LocalRingNumber OBJECT-TYPE
            SYNTAX INTEGER 
            ACCESS read-only
            STATUS mandatory
            DESCRIPTION
                "This parameter specifies the local ring number to which 
                 this port is attached. It is used as default if a value 
                 is not obtained from Ring Parameter Server."
        ::= { cdx6500PPCTdot5PortEntry 4 }

        cdx6500dot5EarlyTokenRelease OBJECT-TYPE
            SYNTAX INTEGER {
                    disable       (0),
                    enable        (1),
                    newvalDisable (50)
                    }
            ACCESS read-only
            STATUS mandatory
            DESCRIPTION
                "This parameter controls whether this station operating on 
                 a 16 Mbps ring will perform early token release.
                 This parameter has no effect for 4 Mbps rings where 
                 early token release is not used.
                 newvalDisable : same functionality as 'disable', new enumeration
                 added for RFC1155 compatibility."
        ::= { cdx6500PPCTdot5PortEntry 5 }

        cdx6500dot5TransmitQueueLimit OBJECT-TYPE
            SYNTAX INTEGER
            ACCESS read-only
            STATUS mandatory
            DESCRIPTION
                "Number of frames that can be queued on the transmitter 
                 before any frame is dropped."
        ::= { cdx6500PPCTdot5PortEntry 6 }


        -- This table contains statistics and error counter which are
        -- specific to 802.5 interfaces. These objects are in addition
        -- to those listed in RFC1231.

        cdx6500PPSTdot5PortTable OBJECT-TYPE
            SYNTAX SEQUENCE OF Cdx6500PPSTdot5Entry
            ACCESS not-accessible
            STATUS mandatory
            DESCRIPTION
                "A table containing Token Ring statistics, one entry 
                 per 802.5 interface. All the statistics are defined using
                 the syntax Counter as 32-bit wrap around counters.  
                 Thus, if an interface's hardware maintains these statistics 
                 in 16-bit counters, then the agent must read the hardware's 
                 counters frequently enough to prevent loss of significance, 
                 in order to maintain 32-bit counters in software."
        ::= { cdx6500PSTPortProtocolGroup 9 }

        cdx6500PPSTdot5PortEntry OBJECT-TYPE
            SYNTAX Cdx6500PPSTdot5Entry
            ACCESS not-accessible
            STATUS mandatory
            DESCRIPTION
                "An entry contains the 802.5 statistics for a particular 
                 interface."
            INDEX { cdx6500dot5StatsIfIndex }
        ::= { cdx6500PPSTdot5PortTable 1 }

        Cdx6500PPSTdot5Entry ::= 
            SEQUENCE {
                cdx6500dot5StatsIfIndex
                    INTEGER,
                cdx6500dot5StatsPortType
                    INTEGER,
                cdx6500dot5StatsDataBytesRx
                    Counter,
                cdx6500dot5StatsDataBytesTx
                    Counter,
                cdx6500dot5StatsFrameSizeExc
                    Counter,
                cdx6500dot5StatsShortFrames
                    Counter,
                cdx6500dot5StatsTransmitDiscards
                    Counter,
                cdx6500dot5StatsPortStatus
                    INTEGER,
                cdx6500dot5StatsLastStatReset
                    DisplayString,
                cdx6500dot5StatsClearStats
                    INTEGER
                }


        cdx6500dot5StatsIfIndex OBJECT-TYPE
            SYNTAX INTEGER
            ACCESS read-only
            STATUS mandatory
            DESCRIPTION
                "The value of this object identifies the 802.5
                 interface for which this entry contains
                 management information."
        ::= { cdx6500PPSTdot5PortEntry 1 }

        cdx6500dot5StatsPortType OBJECT-TYPE
            SYNTAX INTEGER {
                    tr (28)
                    }
            ACCESS read-only
            STATUS mandatory
            DESCRIPTION
                "The currently running value of the Port type."
        ::= { cdx6500PPSTdot5PortEntry 2 }

        cdx6500dot5StatsDataBytesRx OBJECT-TYPE
            SYNTAX Counter
            ACCESS read-only
            STATUS mandatory
            DESCRIPTION
                "This counter is incremented for each data
                 byte received by the LAN port."
        ::= { cdx6500PPSTdot5PortEntry 3 }

        cdx6500dot5StatsDataBytesTx OBJECT-TYPE
            SYNTAX Counter
            ACCESS read-only
            STATUS mandatory
            DESCRIPTION
                "This counter is incremented for each data byte transmitted 
                 by the LAN port."
        ::= { cdx6500PPSTdot5PortEntry 4 }

        cdx6500dot5StatsFrameSizeExc OBJECT-TYPE
            SYNTAX Counter
            ACCESS read-only
            STATUS mandatory
            DESCRIPTION
                "This counter is incremented when the LAN port observes 
                 a frame that can not be forwarded because of excessive 
                 length."
        ::= { cdx6500PPSTdot5PortEntry 5 }

        cdx6500dot5StatsShortFrames OBJECT-TYPE
            SYNTAX Counter
            ACCESS read-only
            STATUS mandatory
            DESCRIPTION
                "This counter is incremented when the LAN port observes 
                 a receive or transmitted frame which is less than 18 bytes."
        ::= { cdx6500PPSTdot5PortEntry 6 }

        cdx6500dot5StatsTransmitDiscards OBJECT-TYPE
            SYNTAX Counter
            ACCESS read-only
            STATUS mandatory
            DESCRIPTION
                "This counter is incremented when the LAN port discards 
                 the frame because the transmit queue exceeds the maximum 
                 queue length."
        ::= { cdx6500PPSTdot5PortEntry 7 }

        cdx6500dot5StatsPortStatus OBJECT-TYPE
            SYNTAX INTEGER {
                    disabled       (0),
                    enabled        (1),
                    up             (3),
                    down           (4),
                    newvalDisabled (50)
                    }
            ACCESS read-only
            STATUS mandatory
            DESCRIPTION
                "Indicates the status of the LAN port.
                 newvalDisabled : same functionality as 'disabled', new enumeration
                 added for RFC1155 compatibility."
        ::= { cdx6500PPSTdot5PortEntry 8 }

        cdx6500dot5StatsLastStatReset OBJECT-TYPE
            SYNTAX DisplayString
            ACCESS read-only
            STATUS mandatory
            DESCRIPTION
                "Time stamp when the statistics were last reset."
        ::= { cdx6500PPSTdot5PortEntry 9 }

        cdx6500dot5StatsClearStats OBJECT-TYPE
            SYNTAX INTEGER {
                    reset (1)
                    }
            ACCESS write-only
            STATUS mandatory
            DESCRIPTION
                "This is the command to reset the LAN port statistics."
        ::= { cdx6500PPSTdot5PortEntry 10 }

        END
