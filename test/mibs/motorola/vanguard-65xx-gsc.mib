-- Version 1.5, modified 02/12/98

        GSC-OPT-MIB DEFINITIONS ::= BEGIN

        IMPORTS
            Counter
                FROM RFC1155-SMI
            OBJECT-TYPE
                FROM RFC-1212;

        -- Codex MIB Group definitions

                         codex OBJECT IDENTIFIER ::= { enterprises 449 }
            cdxProductSpecific OBJECT IDENTIFIER ::= { codex 2 }
                       cdx6500 OBJECT IDENTIFIER ::= { cdxProductSpecific 1 }

         cdx6500Configuration  OBJECT IDENTIFIER ::= { cdx6500 2 }
       cdx6500CfgProtocolGroup OBJECT IDENTIFIER ::= { cdx6500Configuration 1 }
   cdx6500PCTPortProtocolGroup OBJECT IDENTIFIER ::= { cdx6500CfgProtocolGroup 1 }
cdx6500PCTStationProtocolGroup OBJECT IDENTIFIER ::= { cdx6500CfgProtocolGroup 3 }

             cdx6500Statistics OBJECT IDENTIFIER ::= { cdx6500 3 }
      cdx6500StatProtocolGroup OBJECT IDENTIFIER ::= { cdx6500Statistics 1 }
   cdx6500PSTPortProtocolGroup OBJECT IDENTIFIER ::= { cdx6500StatProtocolGroup 1 }
cdx6500PSTStationProtocolGroup OBJECT IDENTIFIER ::= { cdx6500StatProtocolGroup 3 }

               cdx6500Controls OBJECT IDENTIFIER ::= { cdx6500 4 }

        -- Textual conventions

        DisplayString ::= OCTET STRING

        -- The GSC Port Configuration Table
        -- This table contains Configuration parameters
        -- related to a GSC port

        cdx6500PPCTGSCPortTable OBJECT-TYPE
            SYNTAX SEQUENCE OF Cdx6500PPCTGSCPortEntry
            ACCESS not-accessible
            STATUS mandatory
            DESCRIPTION
                "This table contains GSC port configuration parameters."
        ::= { cdx6500PCTPortProtocolGroup 29 }

        cdx6500PPCTGSCPortEntry OBJECT-TYPE
            SYNTAX Cdx6500PPCTGSCPortEntry
            ACCESS not-accessible
            STATUS mandatory
            DESCRIPTION
                "Configuration parameters relevant to a GSC port."
            INDEX { cdx6500GSCPCfgPortNumber }
        ::= { cdx6500PPCTGSCPortTable 1 }

        Cdx6500PPCTGSCPortEntry ::= 
             SEQUENCE {
                 cdx6500GSCPCfgPortNumber
                     INTEGER,
                 cdx6500GSCPCfgPortType
                     INTEGER,
                 cdx6500GSCPCfgSubtype
                     INTEGER,
                 cdx6500GSCPCfgClockSpeed
                     INTEGER,
                 cdx6500GSCPCfgNumStations
                     INTEGER,
                 cdx6500GSCPCfgMinPollPeriod
                     INTEGER,
                 cdx6500GSCPCfgPollRespTimer
                     INTEGER,
                 cdx6500GSCPCfgAckTimeOut
                     INTEGER,
                 cdx6500GSCPCfgInterCharTimeOut
                     INTEGER,
                 cdx6500GSCPCfgBroadcastHoldTimeOut
                     INTEGER,
                 cdx6500GSCPCfgSolicitedTimeOut
                     INTEGER,
                 cdx6500GSCPCfgIdleDiscTimeOut
                     INTEGER,
                 cdx6500GSCPCfgAutocallRetryTimeOut
                     INTEGER,
                 cdx6500GSCPCfgMaxAutocallRetries
                     INTEGER,
                 cdx6500GSCPCfgN1
                     INTEGER,
                 cdx6500GSCPCfgN2
                     INTEGER,
                 cdx6500GSCPCfgNumRetries
                     INTEGER,
                 cdx6500GSCPCfgPortAddress
                     DisplayString,
                 cdx6500GSCPCfgPortOptions
                     DisplayString,
                 cdx6500GSCPCfgConnType
                     INTEGER,
                 cdx6500GSCPCfgWakeUpTimer
                     INTEGER
                 }

        cdx6500GSCPCfgPortNumber OBJECT-TYPE
            SYNTAX INTEGER (1..54)
            ACCESS read-only
            STATUS mandatory
            DESCRIPTION
                "Port number of the port being used by GSC"
        ::= { cdx6500PPCTGSCPortEntry 1 }

        cdx6500GSCPCfgPortType OBJECT-TYPE
            SYNTAX INTEGER {
                    gsc (51)
                    }
            ACCESS read-only
            STATUS mandatory
            DESCRIPTION
              "The Port Type of the port."
        ::= { cdx6500PPCTGSCPortEntry 2 }

        cdx6500GSCPCfgSubtype OBJECT-TYPE
            SYNTAX INTEGER {
                    gscTpad (1),
                    gscHpad (2)
                    }
            ACCESS read-only
            STATUS mandatory
            DESCRIPTION
                "The GSC port sub-type.
                 gscHpad - Port is functioning as a host PAD.
                 gscTpad - Port is functioning as a terminal PAD."
        ::= { cdx6500PPCTGSCPortEntry 3 }
     
        cdx6500GSCPCfgClockSpeed OBJECT-TYPE
            SYNTAX INTEGER {
                    speed1200  (4),
                    speed1800  (8),
                    speed2400  (13),
                    speed4800  (14),
                    speed9600  (15),
                    speed19200 (16),
                    nc         (100)
                    }
            ACCESS read-only
            STATUS mandatory
            DESCRIPTION
                "This is the clock speed of the port in bits per second,
                 when internal clocking is used."
        ::= { cdx6500PPCTGSCPortEntry 4 }

        cdx6500GSCPCfgNumStations OBJECT-TYPE
            SYNTAX INTEGER (1..24)
            ACCESS read-only
            STATUS mandatory
            DESCRIPTION
                "The number of stations/devices configured on this port."
        ::= { cdx6500PPCTGSCPortEntry 5 }

        cdx6500GSCPCfgMinPollPeriod OBJECT-TYPE
            SYNTAX INTEGER (1..1000)
            ACCESS read-only
            STATUS mandatory
            DESCRIPTION
              "The minimum time the TPAD waits between polls. Specified
               in 50 ms increments (i.e. 1 means 50 ms)."
        ::= { cdx6500PPCTGSCPortEntry 6 }

        cdx6500GSCPCfgPollRespTimer OBJECT-TYPE
            SYNTAX INTEGER (1..1000)
            ACCESS read-only
            STATUS mandatory
            DESCRIPTION
                "The maximum time the TPAD waits for a response from the
                 terminal after a poll. Specified in 50 ms increments 
                 (i.e. 5 means 250 ms)."
        ::= { cdx6500PPCTGSCPortEntry 7 }

        cdx6500GSCPCfgAckTimeOut OBJECT-TYPE
            SYNTAX INTEGER (1..1000)
            ACCESS read-only
            STATUS mandatory
            DESCRIPTION
                "The maximum time the TPAD or HPAD waits for acknowledgement
                 for a transmitted frame. Specified in 50 ms increments
                 (i.e. 5 means 250 ms)."
        ::= { cdx6500PPCTGSCPortEntry 8 }

        cdx6500GSCPCfgInterCharTimeOut OBJECT-TYPE
            SYNTAX INTEGER (1..5)
            ACCESS read-only
            STATUS mandatory
            DESCRIPTION
                "The maximum time period allowed between received characters.
                 Specified in  50 ms increments (i.e. 5 means 250 ms)."
        ::= { cdx6500PPCTGSCPortEntry 9 }

        cdx6500GSCPCfgBroadcastHoldTimeOut OBJECT-TYPE
            SYNTAX INTEGER (1..1000)
            ACCESS read-only
            STATUS mandatory
            DESCRIPTION
                "The time the TPAD holds a broadcast frame from one station,
                 when it detects a dropped frame, while waiting for the 
                 missing frame from another station.
                 Specified in  50 ms increments (i.e. 5 means 250 ms)."
        ::= { cdx6500PPCTGSCPortEntry 10 }

        cdx6500GSCPCfgSolicitedTimeOut OBJECT-TYPE
            SYNTAX INTEGER (1..1000)
            ACCESS read-only
            STATUS mandatory
            DESCRIPTION
                "Specifies the time that the TPAD waits for a SAD message in 
                 response to a PAD message, before re-transmitting the PAD
                 message. Specified in 50 ms increments 
                 (i.e. 60 means 3 seconds)."
        ::= { cdx6500PPCTGSCPortEntry 11 }

        cdx6500GSCPCfgIdleDiscTimeOut OBJECT-TYPE
            SYNTAX INTEGER (1..100)
            ACCESS read-only
            STATUS mandatory
            DESCRIPTION
                "The period that the HPAD waits to receive a UAD-frame,
                 SAD-frame or poll from the polling controller before 
                 clearing the call to the TPAD.
                 Specified in minutes (i.e. 5 means 5 minutes)."
        ::= { cdx6500PPCTGSCPortEntry 12 }

        cdx6500GSCPCfgAutocallRetryTimeOut OBJECT-TYPE
            SYNTAX INTEGER (1..1000)
            ACCESS read-only
            STATUS mandatory
            DESCRIPTION
                "Specifies the time to wait between subsequent autocall
                 attempts. Specified in 50 ms increments.
                 (i.e. 4 means 200 ms)."
        ::= { cdx6500PPCTGSCPortEntry 13 }

        cdx6500GSCPCfgMaxAutocallRetries OBJECT-TYPE
            SYNTAX INTEGER (0..1000)
            ACCESS read-only
            STATUS mandatory
            DESCRIPTION
                "The maximum number of autocall attempts allowed. The port is
                 disabled when the limit is reached."
        ::= { cdx6500PPCTGSCPortEntry 14 }

        cdx6500GSCPCfgN1 OBJECT-TYPE
            SYNTAX INTEGER (1..100)
            ACCESS read-only
            STATUS mandatory
            DESCRIPTION
                "The number of good responses a TPAD must receive before
                 changing a stations state from UP to DOWN ."
        ::= { cdx6500PPCTGSCPortEntry 15 }

        cdx6500GSCPCfgN2 OBJECT-TYPE
            SYNTAX INTEGER (1..100)
            ACCESS read-only
            STATUS mandatory
            DESCRIPTION
                "The number of good responses a TPAD must receive before
                 changing a stations state from DOWN to UP."
        ::= { cdx6500PPCTGSCPortEntry 16 }

        cdx6500GSCPCfgNumRetries OBJECT-TYPE
            SYNTAX INTEGER (1..100)
            ACCESS read-only
            STATUS mandatory
            DESCRIPTION
                "The number of times the TPAD or HPAD will retry a selection
                 procedure before discarding a frame."
        ::= { cdx6500PPCTGSCPortEntry 17 }

        cdx6500GSCPCfgPortAddress OBJECT-TYPE
            SYNTAX DisplayString (SIZE (0..15))
            ACCESS read-only
            STATUS mandatory
            DESCRIPTION
                "When a GSC port makes a call,this address is inserted
                 into the calling address field."
        ::= { cdx6500PPCTGSCPortEntry 18 }

        cdx6500GSCPCfgPortOptions OBJECT-TYPE
            SYNTAX DisplayString
            ACCESS read-only
            STATUS mandatory
            DESCRIPTION
                "The port options specified :
                 NONE - No option specified. "
        ::= { cdx6500PPCTGSCPortEntry 19 }
           
        cdx6500GSCPCfgConnType OBJECT-TYPE
            SYNTAX INTEGER {
                    simp  (1),
                    simpa (16),
                    nc    (100)
                    }
            ACCESS read-only
            STATUS mandatory
            DESCRIPTION
                "Specifies the control signal handshake and clocking
                 required for a connection to be made to this port.
                 simp  - simple, no control signals required.
                 simpa - CTS follows RTS, but no control signals required.
                 nc    - Skipped during configuration."
        ::= { cdx6500PPCTGSCPortEntry 20 }

        cdx6500GSCPCfgWakeUpTimer OBJECT-TYPE
            SYNTAX INTEGER (0..30)
            ACCESS read-only
            STATUS mandatory
            DESCRIPTION
                "Specifies the time to wait after autocall attempts are
                 exhausted before attempting another autocall cycle. A
                 value of 0 will prevent subsequent attempts until the 
                 station is booted."
        ::= { cdx6500PPCTGSCPortEntry 21 }


        -- The GSC Station Configuration Table
        -- This table contains Configuration parameters
        -- for the GSC station.

        cdx6500SPCTGSCStationTable OBJECT-TYPE
            SYNTAX SEQUENCE OF Cdx6500SPCTGSCStationEntry
            ACCESS not-accessible
            STATUS mandatory
            DESCRIPTION
                "This table contains GSC station configuration parameters."
        ::= { cdx6500PCTStationProtocolGroup 8 }

        cdx6500SPCTGSCStationEntry OBJECT-TYPE
            SYNTAX Cdx6500SPCTGSCStationEntry
            ACCESS not-accessible
            STATUS mandatory
            DESCRIPTION
                "Each StationEntry contains the configuration parameters
                 for one GSC station."
            INDEX { cdx6500GSCSCfgPortNumber, cdx6500GSCSCfgStationNumber }
        ::= { cdx6500SPCTGSCStationTable 1 }        

        Cdx6500SPCTGSCStationEntry ::= 
            SEQUENCE {
                cdx6500GSCSCfgPortNumber
                    INTEGER,
                cdx6500GSCSCfgStationNumber
                    INTEGER,
                cdx6500GSCSCfgStationAddress
                    INTEGER,
                cdx6500GSCSCfgRemoteAddress
                    INTEGER,
                cdx6500GSCSCfgAutocallMnem
                    DisplayString,
                cdx6500GSCSCfgProtocolId
                    DisplayString,
                cdx6500GSCSCfgBillingRecords
                    INTEGER,
                cdx6500GSCSCfgStationOptions
                    DisplayString
                }

        cdx6500GSCSCfgPortNumber OBJECT-TYPE
            SYNTAX INTEGER (1..54)
            ACCESS read-only
            STATUS mandatory
            DESCRIPTION
                "Port number of the port being used by GSC."
        ::= { cdx6500SPCTGSCStationEntry 1 }

        cdx6500GSCSCfgStationNumber OBJECT-TYPE
            SYNTAX INTEGER (1..24)
            ACCESS read-only
            STATUS mandatory
            DESCRIPTION
                "The number of devices on the multidrop line.
                 Also used for routing purposes."
        ::= { cdx6500SPCTGSCStationEntry 2 }

        cdx6500GSCSCfgStationAddress OBJECT-TYPE
            SYNTAX INTEGER (0..29)
            ACCESS read-only
            STATUS mandatory
            DESCRIPTION
                "The device address on the local line."
        ::= { cdx6500SPCTGSCStationEntry 3 }
       
        cdx6500GSCSCfgRemoteAddress OBJECT-TYPE
            SYNTAX INTEGER (0..29)
            ACCESS read-only
            STATUS mandatory
            DESCRIPTION
                "The device address on the remote line."
        ::= { cdx6500SPCTGSCStationEntry 4 }

        cdx6500GSCSCfgAutocallMnem OBJECT-TYPE
            SYNTAX DisplayString (SIZE(0..8))
            ACCESS read-only
            STATUS mandatory
            DESCRIPTION
                "Identifies the entry in the Autocall Mnemonic table which
                 specifies the X.25 call request parameters for this 
                 station.This is valid only if the port subtype is HPAD."
        ::= { cdx6500SPCTGSCStationEntry 5 }

        cdx6500GSCSCfgProtocolId OBJECT-TYPE
            SYNTAX DisplayString 
            ACCESS read-only
            STATUS mandatory
            DESCRIPTION
                "The protocol ID inserted in outgoing calls and checked for
                 incoming calls."
        ::= { cdx6500SPCTGSCStationEntry 6 }

        cdx6500GSCSCfgBillingRecords OBJECT-TYPE
            SYNTAX INTEGER {
                    billingOff (1),
                    billingOn  (2)
                    }
            ACCESS read-only
            STATUS mandatory
            DESCRIPTION
                "billingOff - Billing records are not generated.
                 billingOn  - Billing records are generated."
        ::= { cdx6500SPCTGSCStationEntry 7 }

        cdx6500GSCSCfgStationOptions OBJECT-TYPE
            SYNTAX DisplayString (SIZE(4..9))
            ACCESS read-only
            STATUS mandatory
            DESCRIPTION
                "GSC station options:
                 NONE - no option specified
                 IBRO - Inband Broadcast frames supported on this channel.
                 One or more options may be specified by summing (separating 
                 them by a plus sign)."
        ::= { cdx6500SPCTGSCStationEntry 8 }
                    
        -- GSC Port Statistics

        cdx6500PPSTGSCPortTable  OBJECT-TYPE
            SYNTAX SEQUENCE OF Cdx6500PPSTGSCPortEntry
            ACCESS not-accessible
            STATUS mandatory
            DESCRIPTION
                "This table holds statistics items for GSC ports."
        ::= { cdx6500PSTPortProtocolGroup 30 }

        cdx6500PPSTGSCPortEntry OBJECT-TYPE
            SYNTAX Cdx6500PPSTGSCPortEntry
            ACCESS not-accessible
            STATUS mandatory
            DESCRIPTION
                "Statistics parameters pertaining to GSC Ports."
            INDEX { cdx6500GSCPStatPortNumber }
        ::= { cdx6500PPSTGSCPortTable 1 }

        Cdx6500PPSTGSCPortEntry ::=
            SEQUENCE {
                cdx6500GSCPStatPortNumber
                    INTEGER,
                cdx6500GSCPStatPortType
                    INTEGER,
                cdx6500GSCPStatSubtype
                    INTEGER,
                cdx6500GSCPStatPortStatus
                    INTEGER,
                cdx6500GSCPStatPortSpeed
                    INTEGER,
                cdx6500GSCPStatLastStatsReset
                    DisplayString,
                cdx6500GSCPStatCharsIn
                    Counter,
                cdx6500GSCPStatCharsOut
                    Counter,
                cdx6500GSCPStatCharsInPerSec
                    INTEGER,
                cdx6500GSCPStatCharsOutPerSec
                    INTEGER,
                cdx6500GSCPStatOverrunErrs
                    Counter,
                cdx6500GSCPStatChecksumErrs
                    Counter,
                cdx6500GSCPStatOverlengthFrames
                    Counter,
                cdx6500GSCPStatPollRespTimeOuts
                    Counter,
                cdx6500GSCPStatIntercharTimeOuts
                    Counter,
                cdx6500GSCPStatAckTimeOuts
                    Counter,
                cdx6500GSCPStatPADFrames
                    Counter,
                cdx6500GSCPStatSADFrames
                    Counter,
                cdx6500GSCPStatUADFrames
                    Counter,
                cdx6500GSCPStatBROFrames
                    Counter,
                cdx6500GSCPStatPADChars
                    Counter,
                cdx6500GSCPStatSADChars
                    Counter,
                cdx6500GSCPStatUADChars
                    Counter,
                cdx6500GSCPStatENQs
                    Counter,
                cdx6500GSCPStatPACChars
                    Counter,
                cdx6500GSCPStatSACChars
                    Counter,
                cdx6500GSCPStatUACChars
                    Counter,
                cdx6500GSCPStatPolls
                    Counter
                }


        cdx6500GSCPStatPortNumber OBJECT-TYPE
              SYNTAX INTEGER (1..54)
              ACCESS read-only
              STATUS mandatory
              DESCRIPTION
                  "The port number of the GSC port."
        ::= { cdx6500PPSTGSCPortEntry 1 }

        cdx6500GSCPStatPortType OBJECT-TYPE
              SYNTAX INTEGER {
                      gsc (51)
                      }
              ACCESS read-only
              STATUS mandatory
              DESCRIPTION
                  "The port type."
        ::= { cdx6500PPSTGSCPortEntry 2 }

        cdx6500GSCPStatSubtype OBJECT-TYPE
              SYNTAX INTEGER {
                      gscTpad (1),
                      gscHpad (2)
                      }
              ACCESS read-only
              STATUS mandatory
              DESCRIPTION
                  "The port sub-type.
                   gscHpad - port is functioning as a host PAD.
                   gscTpad - Port is functioning as a terminal PAD."
        ::= { cdx6500PPSTGSCPortEntry 3 }

        cdx6500GSCPStatPortStatus OBJECT-TYPE
            SYNTAX INTEGER {
                    disabled       (0),
                    enabled        (1),
                    busyOut        (2),
                    up             (3),
                    down           (4),
                    newvalDisabled (50)
                    }
            ACCESS read-only
            STATUS mandatory
            DESCRIPTION
                "Status of the port:
                 disabled - Port is disabled.
                 enabled  - Port is enabled.
                 busyOut  - The port is busied out.
                 up       - At least one station on the port is 
                            not down or disabled.
                 down     - All stations on the port are either down 
                            or disabled.
                 newvalDisabled - same functionality as 'disabled', new
                            enumeration added for RFC1155 compatibility."
        ::= { cdx6500PPSTGSCPortEntry 4 }

        cdx6500GSCPStatPortSpeed OBJECT-TYPE
            SYNTAX INTEGER
            ACCESS read-only
            STATUS mandatory
            DESCRIPTION
                "The measured port speed in bits per second."
        ::= { cdx6500PPSTGSCPortEntry 5 }

        cdx6500GSCPStatLastStatsReset OBJECT-TYPE
            SYNTAX DisplayString
            ACCESS read-only
            STATUS mandatory
            DESCRIPTION
                "The time when the port statistics were last reset."
        ::= { cdx6500PPSTGSCPortEntry 6 }

        cdx6500GSCPStatCharsIn OBJECT-TYPE
            SYNTAX Counter
            ACCESS read-only
            STATUS mandatory
            DESCRIPTION
                "Number of characters received on the line, including 
                 data and control characters."
        ::= { cdx6500PPSTGSCPortEntry 7 }

        cdx6500GSCPStatCharsOut OBJECT-TYPE
            SYNTAX Counter
            ACCESS read-only
            STATUS mandatory
            DESCRIPTION
                "Number of characters transmitted on the line, 
                 including data and control characters."
        ::= { cdx6500PPSTGSCPortEntry 8 }

        cdx6500GSCPStatCharsInPerSec OBJECT-TYPE
            SYNTAX INTEGER
            ACCESS read-only
            STATUS mandatory
            DESCRIPTION
                "Number of characters received per second on the line,
                 including data and control characters."
        ::= { cdx6500PPSTGSCPortEntry 9 }

        cdx6500GSCPStatCharsOutPerSec OBJECT-TYPE
            SYNTAX INTEGER
            ACCESS read-only
            STATUS mandatory
            DESCRIPTION
                "Number of characters transmitted per second on the line,
                 including data and control characters."
        ::= { cdx6500PPSTGSCPortEntry 10 }

        cdx6500GSCPStatOverrunErrs OBJECT-TYPE
            SYNTAX Counter
            ACCESS read-only
            STATUS mandatory
            DESCRIPTION
                "The number of overrun errors detected on the line."
        ::= { cdx6500PPSTGSCPortEntry 11 }

        cdx6500GSCPStatChecksumErrs OBJECT-TYPE
            SYNTAX Counter
            ACCESS read-only
            STATUS mandatory
            DESCRIPTION
                "The number of frames received with checksum errors."
        ::= { cdx6500PPSTGSCPortEntry 12 }

        cdx6500GSCPStatOverlengthFrames OBJECT-TYPE
            SYNTAX Counter
            ACCESS read-only
            STATUS mandatory
            DESCRIPTION
                "The number of frames received that were over length."
        ::= { cdx6500PPSTGSCPortEntry 13 }

        cdx6500GSCPStatPollRespTimeOuts OBJECT-TYPE
            SYNTAX Counter
            ACCESS read-only
            STATUS mandatory
            DESCRIPTION
                "The number of times a poll was issued without response
                 from the terminal."
        ::= { cdx6500PPSTGSCPortEntry 14 }

        cdx6500GSCPStatIntercharTimeOuts OBJECT-TYPE
            SYNTAX Counter
            ACCESS read-only
            STATUS mandatory
            DESCRIPTION
                "The number of receive frames aborted because of 
                 inter-character timeouts."
        ::= { cdx6500PPSTGSCPortEntry 15 }

        cdx6500GSCPStatAckTimeOuts OBJECT-TYPE
            SYNTAX Counter
            ACCESS read-only
            STATUS mandatory
            DESCRIPTION
                "The number of transmitted frames which were not
                 acknowledged."
        ::= { cdx6500PPSTGSCPortEntry 16 }

        cdx6500GSCPStatPADFrames OBJECT-TYPE
            SYNTAX Counter
            ACCESS read-only
            STATUS mandatory
            DESCRIPTION
                "The number of PAD frames received (TPAD) or 
                 transmitted (HPAD)."
        ::= { cdx6500PPSTGSCPortEntry 17 }

        cdx6500GSCPStatSADFrames OBJECT-TYPE
            SYNTAX Counter
            ACCESS read-only
            STATUS mandatory
            DESCRIPTION
                "The number of SAD frames transmitted (TPAD) or
                 received (HPAD)."
        ::= { cdx6500PPSTGSCPortEntry 18 }

        cdx6500GSCPStatUADFrames OBJECT-TYPE
            SYNTAX Counter
            ACCESS read-only
            STATUS mandatory
            DESCRIPTION
                "The number of UAD frames transmitted (TPAD) or 
                 received (HPAD)."
        ::= { cdx6500PPSTGSCPortEntry 19 }

        cdx6500GSCPStatBROFrames OBJECT-TYPE
            SYNTAX Counter
            ACCESS read-only
            STATUS mandatory
            DESCRIPTION
                "The number of BRO frames transmitted (TPAD) or
                 received (HPAD)."
        ::= { cdx6500PPSTGSCPortEntry 20 }

        cdx6500GSCPStatPADChars OBJECT-TYPE
            SYNTAX Counter
            ACCESS read-only
            STATUS mandatory
            DESCRIPTION
                "The number of PAD characters received (TPAD) or 
                 transmitted (HPAD)."
        ::= { cdx6500PPSTGSCPortEntry 21 }

        cdx6500GSCPStatSADChars OBJECT-TYPE
            SYNTAX Counter
            ACCESS read-only
            STATUS mandatory
            DESCRIPTION
                "The number of SAD characters transmitted (TPAD) or
                 received (HPAD)."
        ::= { cdx6500PPSTGSCPortEntry 22 }

        cdx6500GSCPStatUADChars OBJECT-TYPE
            SYNTAX Counter
            ACCESS read-only
            STATUS mandatory
            DESCRIPTION
                "The number of UAD characters transmitted (TPAD) or
                 received (HPAD)."
        ::= { cdx6500PPSTGSCPortEntry 23 }

        cdx6500GSCPStatENQs OBJECT-TYPE
            SYNTAX Counter
            ACCESS read-only
            STATUS mandatory
            DESCRIPTION
                "The number of ENQ characters received (TPAD) or 
                 transmitted (HPAD)."
        ::= { cdx6500PPSTGSCPortEntry 24 }

        cdx6500GSCPStatPACChars OBJECT-TYPE
            SYNTAX Counter
            ACCESS read-only
            STATUS mandatory
            DESCRIPTION
                "The number of PAC characters received (TPAD) or 
                 transmitted (HPAD)."
        ::= { cdx6500PPSTGSCPortEntry 25 }

        cdx6500GSCPStatSACChars OBJECT-TYPE
            SYNTAX Counter
            ACCESS read-only
            STATUS mandatory
            DESCRIPTION
                "The number of SAC characters transmitted (TPAD) or 
                 received (HPAD)."
        ::= { cdx6500PPSTGSCPortEntry 26 }

        cdx6500GSCPStatUACChars OBJECT-TYPE
            SYNTAX Counter
            ACCESS read-only
            STATUS mandatory
            DESCRIPTION
                "The number of UAC characters transmitted (TPAD) or 
                 received (HPAD)."
        ::= { cdx6500PPSTGSCPortEntry 27 }

        cdx6500GSCPStatPolls OBJECT-TYPE
            SYNTAX Counter
            ACCESS read-only
            STATUS mandatory
            DESCRIPTION
                "The number of polls transmitted (TPAD) or received (HPAD)."
        ::= { cdx6500PPSTGSCPortEntry 28 }

        -- GSC Station Statistics Table

        cdx6500SPSTGSCStationTable OBJECT-TYPE
            SYNTAX SEQUENCE OF Cdx6500SPSTGSCStationEntry
            ACCESS not-accessible
            STATUS mandatory
            DESCRIPTION
                "Statistics parameters relevant to GSC stations."
        ::= { cdx6500PSTStationProtocolGroup 7 }

        cdx6500SPSTGSCStationEntry OBJECT-TYPE
            SYNTAX Cdx6500SPSTGSCStationEntry
            ACCESS not-accessible
            STATUS mandatory
            DESCRIPTION
                "This table holds statistics parameters pertaining to 
                 GSC stations."
            INDEX { cdx6500GSCSStatPortNumber, cdx6500GSCSStatStationNum }
        ::= { cdx6500SPSTGSCStationTable 1 }

        Cdx6500SPSTGSCStationEntry ::=
            SEQUENCE {
                cdx6500GSCSStatPortNumber
                    INTEGER,
                cdx6500GSCSStatStationNum
                    INTEGER,
                cdx6500GSCSStatPortType
                    INTEGER,
                cdx6500GSCSStatSubtype
                    INTEGER,
                cdx6500GSCSStatStationAddress
                    INTEGER,
                cdx6500GSCSStatStationStatus
                    INTEGER,
                cdx6500GSCSStatLastStatsReset
                    DisplayString,
                cdx6500GSCSStatCharsIn
                    Counter,
                cdx6500GSCSStatCharsOut
                    Counter,
                cdx6500GSCSStatCharsInPerSec
                    INTEGER,
                cdx6500GSCSStatCharsOutPerSec
                    INTEGER,
                cdx6500GSCSStatChecksumErrs
                    Counter,
                cdx6500GSCSStatOverlengthFrames
                    Counter,
                cdx6500GSCSStatPollRespTimeOuts
                    Counter,
                cdx6500GSCSStatIntercharTimeOuts
                    Counter,
                cdx6500GSCSStatAckTimeOuts
                    Counter,
                cdx6500GSCSStatPADFrames
                    Counter,
                cdx6500GSCSStatSADFrames
                    Counter,
                cdx6500GSCSStatUADFrames
                    Counter,
                cdx6500GSCSStatBROFrames
                    Counter,
                cdx6500GSCSStatPADChars
                    Counter,
                cdx6500GSCSStatSADChars
                    Counter,
                cdx6500GSCSStatUADChars
                    Counter,
                cdx6500GSCSStatENQ
                    Counter,
                cdx6500GSCSStatPACChars
                    Counter,
                cdx6500GSCSStatSACChars
                    Counter,
                cdx6500GSCSStatUACChars
                    Counter,
                cdx6500GSCSStatPolls
                    Counter,
                cdx6500GSCSStatPADMessages
                    Counter,
                cdx6500GSCSStatUADMessages
                    Counter,
                cdx6500GSCSStatSADMessages
                    Counter,
                cdx6500GSCSStatBROMessages
                    Counter,
                cdx6500GSCSStatSolicitAbort
                    Counter,
                cdx6500GSCSStatStatusEnq
                    Counter,
                cdx6500GSCSStatDeviceUp
                    Counter,
                cdx6500GSCSStatDeviceDown
                    Counter,
                cdx6500GSCSStatCallCurrentStatus
                    INTEGER,
                cdx6500GSCSStatLastClrCauseCode
                    DisplayString,
                cdx6500GSCSStatLastClrDiagCode
                    DisplayString,
                cdx6500GSCSStatLastInCalledAddress
                    DisplayString,
                cdx6500GSCSStatLastInCallingAddress
                    DisplayString,
                cdx6500GSCSStatLastInCallFacilities
                    DisplayString,
                cdx6500GSCSStatLastInCallCUD
                    DisplayString,
                cdx6500GSCSStatLastOutCalledAddress
                    DisplayString,
                cdx6500GSCSStatLastOutCallingAddress
                    DisplayString,
                cdx6500GSCSStatLastOutCallFacilities
                    DisplayString,
                cdx6500GSCSStatLastOutCallCUD
                    DisplayString
                }

        cdx6500GSCSStatPortNumber OBJECT-TYPE
            SYNTAX INTEGER (1..54)
            ACCESS read-only
            STATUS mandatory
            DESCRIPTION
                "The port number of the GSC port."
        ::= { cdx6500SPSTGSCStationEntry 1 }

        cdx6500GSCSStatStationNum OBJECT-TYPE
            SYNTAX INTEGER (1..24)
            ACCESS read-only
            STATUS mandatory
            DESCRIPTION
                "The GSC station number."
        ::= { cdx6500SPSTGSCStationEntry 2 }

        cdx6500GSCSStatPortType OBJECT-TYPE 
            SYNTAX INTEGER {
                    gsc(51)
                    }
            ACCESS read-only
            STATUS mandatory
            DESCRIPTION
                "This indicates the port type."
        ::= { cdx6500SPSTGSCStationEntry 3 }

        cdx6500GSCSStatSubtype OBJECT-TYPE
            SYNTAX INTEGER {
                    gscTpad (1),
                    gscHpad (2)
                    }
            ACCESS read-only
            STATUS mandatory
            DESCRIPTION
                "Indicates the sub-type of the associated port.
                 gscHpad - Associated port is functioning as a host PAD.
                 gscTpad - Associated port is functioning as a terminal PAD."
        ::= { cdx6500SPSTGSCStationEntry 4}

        cdx6500GSCSStatStationAddress OBJECT-TYPE
            SYNTAX INTEGER (0..29)
            ACCESS read-only
            STATUS mandatory
            DESCRIPTION
                "Configure station address."
        ::= { cdx6500SPSTGSCStationEntry 5 }

        cdx6500GSCSStatStationStatus OBJECT-TYPE
            SYNTAX INTEGER {
                    disabled       (0),
                    enabled        (1),
                    busyOut        (2),
                    up             (3),
                    down           (4),
                    newvalDisabled (50)
                    }
            ACCESS read-only
            STATUS mandatory
            DESCRIPTION
                "The station status:
                 disabled - Station is disabled.
                 enabled  - Station is enabled.
                 busyOut  - Station is busied out.
                 up       - Station is up.
                 down     - Station is down.
                 newvalDisabled - same functionality as 'disabled', new
                            enumeration added for RFC1155 compatibility."
        ::= { cdx6500SPSTGSCStationEntry 6 }

        cdx6500GSCSStatLastStatsReset OBJECT-TYPE
            SYNTAX DisplayString
            ACCESS read-only
            STATUS mandatory
            DESCRIPTION
                "Time when the station statistics were last reset."
        ::= { cdx6500SPSTGSCStationEntry 7 }

        cdx6500GSCSStatCharsIn OBJECT-TYPE
            SYNTAX Counter
            ACCESS read-only
            STATUS mandatory
            DESCRIPTION
                "Number of characters received on the line, including
                 data and control characters."
        ::= { cdx6500SPSTGSCStationEntry 8 }

        cdx6500GSCSStatCharsOut OBJECT-TYPE
            SYNTAX Counter
            ACCESS read-only
            STATUS mandatory
            DESCRIPTION
                "Number of characters transmitted on the line, including
                 data and control characters."
        ::= { cdx6500SPSTGSCStationEntry 9 }

        cdx6500GSCSStatCharsInPerSec OBJECT-TYPE
            SYNTAX INTEGER
            ACCESS read-only
            STATUS mandatory
            DESCRIPTION
                "Number of characters received per second on the line,
                 including data and control characters."
        ::= { cdx6500SPSTGSCStationEntry 10 }

        cdx6500GSCSStatCharsOutPerSec OBJECT-TYPE
            SYNTAX INTEGER
            ACCESS read-only
            STATUS mandatory
            DESCRIPTION
                "Number of characters transmitted per second on the line, 
                 including data and control characters."
        ::= { cdx6500SPSTGSCStationEntry 11 }

        cdx6500GSCSStatChecksumErrs OBJECT-TYPE
            SYNTAX Counter
            ACCESS read-only
            STATUS mandatory
            DESCRIPTION
                "The number of frames received with checksum errors."
        ::= { cdx6500SPSTGSCStationEntry 12 }

        cdx6500GSCSStatOverlengthFrames OBJECT-TYPE
            SYNTAX Counter
            ACCESS read-only
            STATUS mandatory
            DESCRIPTION
                "The number of frames received that were overlength."
        ::= { cdx6500SPSTGSCStationEntry 13 }

        cdx6500GSCSStatPollRespTimeOuts OBJECT-TYPE
            SYNTAX Counter
            ACCESS read-only
            STATUS mandatory
            DESCRIPTION
                "The number of times a poll was issued without response 
                 from the terminal (TPAD only)."
        ::= { cdx6500SPSTGSCStationEntry 14 }
                                  
        cdx6500GSCSStatIntercharTimeOuts OBJECT-TYPE
            SYNTAX Counter
            ACCESS read-only
            STATUS mandatory
            DESCRIPTION
                "The number of receive frames aborted because of 
                 inter-character timeouts."
        ::= { cdx6500SPSTGSCStationEntry 15 }

        cdx6500GSCSStatAckTimeOuts OBJECT-TYPE
            SYNTAX Counter
            ACCESS read-only
            STATUS mandatory
            DESCRIPTION
                "The number of transmitted frames which were not acknowledged."
        ::= { cdx6500SPSTGSCStationEntry 16 }

        cdx6500GSCSStatPADFrames OBJECT-TYPE
            SYNTAX Counter
            ACCESS read-only
            STATUS mandatory
            DESCRIPTION
                "The number of PAD frames received (TPAD) or 
                 transmitted (HPAD)."
        ::= { cdx6500SPSTGSCStationEntry 17 }

        cdx6500GSCSStatSADFrames OBJECT-TYPE
            SYNTAX Counter
            ACCESS read-only
            STATUS mandatory
            DESCRIPTION
                "The number of SAD frames transmitted (TPAD) or 
                 received (HPAD)."
        ::= { cdx6500SPSTGSCStationEntry 18 }

        cdx6500GSCSStatUADFrames OBJECT-TYPE
            SYNTAX Counter
            ACCESS read-only
            STATUS mandatory
            DESCRIPTION
                "The number of UAD frames transmitted (TPAD) or 
                 received (HPAD)."
        ::= { cdx6500SPSTGSCStationEntry 19 }

        cdx6500GSCSStatBROFrames OBJECT-TYPE
            SYNTAX Counter
            ACCESS read-only
            STATUS mandatory
            DESCRIPTION
                "The number of BRO frames transmitted (TPAD) or 
                 received (HPAD)."
        ::= { cdx6500SPSTGSCStationEntry 20 }

        cdx6500GSCSStatPADChars OBJECT-TYPE
            SYNTAX Counter
            ACCESS read-only
            STATUS mandatory
            DESCRIPTION
                "The number of PAD characters received (TPAD) or 
                 transmitted (HPAD)."
        ::= { cdx6500SPSTGSCStationEntry 21 }

        cdx6500GSCSStatSADChars OBJECT-TYPE
            SYNTAX Counter
            ACCESS read-only
            STATUS mandatory
            DESCRIPTION
                "The number of SAD characters transmitted (TPAD) or 
                 received (HPAD)."
        ::= { cdx6500SPSTGSCStationEntry 22 }

        cdx6500GSCSStatUADChars OBJECT-TYPE
            SYNTAX Counter
            ACCESS read-only
            STATUS mandatory
            DESCRIPTION
                "The number of UAD characters transmitted (TPAD) or 
                 received (HPAD)."
        ::= { cdx6500SPSTGSCStationEntry 23 }

        cdx6500GSCSStatENQ OBJECT-TYPE
            SYNTAX Counter
            ACCESS read-only
            STATUS mandatory
            DESCRIPTION
                "The number of ENQ characters received (TPAD) or 
                 transmitted (HPAD)."
        ::= { cdx6500SPSTGSCStationEntry 24 }

        cdx6500GSCSStatPACChars OBJECT-TYPE
            SYNTAX Counter
            ACCESS read-only
            STATUS mandatory
            DESCRIPTION
                "The number of PAC characters received (TPAD) or 
                 transmitted (HPAD)."
        ::= { cdx6500SPSTGSCStationEntry 25 }

        cdx6500GSCSStatSACChars OBJECT-TYPE
            SYNTAX Counter
            ACCESS read-only
            STATUS mandatory
            DESCRIPTION
                "The number of SAC characters transmitted (TPAD) or 
                 received (HPAD)."
        ::= { cdx6500SPSTGSCStationEntry 26 }

        cdx6500GSCSStatUACChars OBJECT-TYPE
            SYNTAX Counter
            ACCESS read-only
            STATUS mandatory
            DESCRIPTION
                "The number of UAC characters transmitted (TPAD) or 
                 received (HPAD)."
        ::= { cdx6500SPSTGSCStationEntry 27 }

        cdx6500GSCSStatPolls OBJECT-TYPE
            SYNTAX Counter
            ACCESS read-only
            STATUS mandatory
            DESCRIPTION
                "The number of Polls transmitted (TPAD) or 
                 received (HPAD)."
        ::= { cdx6500SPSTGSCStationEntry 28 }

        cdx6500GSCSStatPADMessages OBJECT-TYPE
            SYNTAX Counter
            ACCESS read-only
            STATUS mandatory
            DESCRIPTION
                "The number of PAD Messages received (HPAD) or 
                 transmitted (TPAD)."
        ::= { cdx6500SPSTGSCStationEntry 29 }

        cdx6500GSCSStatUADMessages OBJECT-TYPE
            SYNTAX Counter
            ACCESS read-only
            STATUS mandatory
            DESCRIPTION
                "The number of UAD Messages received (TPAD) or 
                 transmitted (HPAD)."
        ::= { cdx6500SPSTGSCStationEntry 30 }

        cdx6500GSCSStatSADMessages OBJECT-TYPE
            SYNTAX Counter
            ACCESS read-only
            STATUS mandatory
            DESCRIPTION
                "The number of SAD Messages received (TPAD) or 
                 transmitted (HPAD)."
        ::= { cdx6500SPSTGSCStationEntry 31 }

        cdx6500GSCSStatBROMessages OBJECT-TYPE
            SYNTAX Counter
            ACCESS read-only
            STATUS mandatory
            DESCRIPTION
                "The number of BRO Messages received (TPAD) or 
                 transmitted (HPAD)."
        ::= { cdx6500SPSTGSCStationEntry 32 }

        cdx6500GSCSStatSolicitAbort OBJECT-TYPE
            SYNTAX Counter
            ACCESS read-only
            STATUS mandatory
            DESCRIPTION
                "The number of SOLICIT ABORT Messages received (TPAD) or 
                 transmitted (HPAD)."
        ::= { cdx6500SPSTGSCStationEntry 33 }

        cdx6500GSCSStatStatusEnq OBJECT-TYPE
            SYNTAX Counter
            ACCESS read-only
            STATUS mandatory
            DESCRIPTION
                "The number of   STATUS ENQ Messages received (HPAD) or 
                 transmitted (TPAD)."
        ::= { cdx6500SPSTGSCStationEntry 34 }

        cdx6500GSCSStatDeviceUp OBJECT-TYPE
            SYNTAX Counter
            ACCESS read-only
            STATUS mandatory
            DESCRIPTION
                "The number of DEVICE UP Messages received (TPAD) or 
                 transmitted (HPAD)."
        ::= { cdx6500SPSTGSCStationEntry 35 }

        cdx6500GSCSStatDeviceDown OBJECT-TYPE
            SYNTAX Counter
            ACCESS read-only
            STATUS mandatory
            DESCRIPTION
                "The number of DEVICE DOWN Messages received (TPAD) or 
                 transmitted (HPAD)."
        ::= { cdx6500SPSTGSCStationEntry 36 }

        cdx6500GSCSStatCallCurrentStatus OBJECT-TYPE
            SYNTAX INTEGER {
                    inhibited    (1),
                    disconnected (2),
                    calling      (3),
                    called       (4),
                    connected    (5),
                    notDefined   (6)
                    }
            ACCESS read-only
            STATUS mandatory
            DESCRIPTION
                "The current status of the call.
                 inhibited     :Current Status = Disconnected.
                 disconnected  :Current Status = Disconnected.
                 calling       :Current Status = Calling.
                 called        :Current Status = Called.
                 connected     :Current Status = Connected (data transfer).
                 notDefined    :Current Status = Undefined."
        ::= { cdx6500SPSTGSCStationEntry 37 }

        cdx6500GSCSStatLastClrCauseCode OBJECT-TYPE
            SYNTAX DisplayString
            ACCESS read-only
            STATUS mandatory
            DESCRIPTION
                "Last clear cause code."
        ::= { cdx6500SPSTGSCStationEntry 38 }

        cdx6500GSCSStatLastClrDiagCode OBJECT-TYPE
            SYNTAX DisplayString
            ACCESS read-only
            STATUS mandatory
            DESCRIPTION
                "Last clear diagnostic code."
        ::= { cdx6500SPSTGSCStationEntry 39 }

        cdx6500GSCSStatLastInCalledAddress OBJECT-TYPE
            SYNTAX DisplayString
            ACCESS read-only
            STATUS mandatory
            DESCRIPTION
                "The called address in the last inbound call."
        ::= { cdx6500SPSTGSCStationEntry 40 }

        cdx6500GSCSStatLastInCallingAddress OBJECT-TYPE
            SYNTAX DisplayString
            ACCESS read-only
            STATUS mandatory
            DESCRIPTION
                "The calling address in the last inbound call."
        ::= { cdx6500SPSTGSCStationEntry 41 }

        cdx6500GSCSStatLastInCallFacilities OBJECT-TYPE
            SYNTAX DisplayString
            ACCESS read-only
            STATUS mandatory
            DESCRIPTION
                "The facilities in the last inbound call."
        ::= { cdx6500SPSTGSCStationEntry 42 }

        cdx6500GSCSStatLastInCallCUD OBJECT-TYPE
            SYNTAX DisplayString
            ACCESS read-only
            STATUS mandatory
            DESCRIPTION
                "The Call User Data in the last inbound call."
        ::= { cdx6500SPSTGSCStationEntry 43 }

        cdx6500GSCSStatLastOutCalledAddress OBJECT-TYPE
            SYNTAX DisplayString
            ACCESS read-only
            STATUS mandatory
            DESCRIPTION
                "The called address in the last outbound call."
        ::= { cdx6500SPSTGSCStationEntry 44 }

        cdx6500GSCSStatLastOutCallingAddress OBJECT-TYPE
            SYNTAX DisplayString
            ACCESS read-only
            STATUS mandatory
            DESCRIPTION
                "The calling address in the last outbound call."
        ::= { cdx6500SPSTGSCStationEntry 45 }

        cdx6500GSCSStatLastOutCallFacilities OBJECT-TYPE
            SYNTAX DisplayString
            ACCESS read-only
            STATUS mandatory
            DESCRIPTION
                "The facilities in the last outbound call."
        ::= { cdx6500SPSTGSCStationEntry 46 }

        cdx6500GSCSStatLastOutCallCUD OBJECT-TYPE
            SYNTAX DisplayString
            ACCESS read-only
            STATUS mandatory
            DESCRIPTION
                "The Call User Data in the last outbound call."
        ::= { cdx6500SPSTGSCStationEntry 47 }

        -- Control objects

        cdx6500ContGSC  OBJECT IDENTIFIER ::= { cdx6500Controls 12 }

        cdx6500ContGSCPTable OBJECT-TYPE
            SYNTAX SEQUENCE OF Cdx6500ContGSCPTableEntry
            ACCESS not-accessible
            STATUS mandatory
            DESCRIPTION
                "This table contains the port control objects"
        ::= { cdx6500ContGSC 1 }

        cdx6500ContGSCPTableEntry OBJECT-TYPE
            SYNTAX Cdx6500ContGSCPTableEntry
            ACCESS not-accessible
            STATUS mandatory
            DESCRIPTION
                "Each entry represents a port control parameter."
            INDEX { cdx6500ContGSCPPortNum }
        ::= { cdx6500ContGSCPTable 1 }

        Cdx6500ContGSCPTableEntry ::= 
            SEQUENCE {
                cdx6500ContGSCPPortNum
                    INTEGER,
                cdx6500ContGSCPBootPort
                    INTEGER,
                cdx6500ContGSCPEnablePort
                    INTEGER,
                cdx6500ContGSCPDisablePort
                    INTEGER
                }
            
        cdx6500ContGSCPPortNum  OBJECT-TYPE
            SYNTAX INTEGER (1..54)
            ACCESS not-accessible
            STATUS mandatory
            DESCRIPTION
                "GSC port Number."
        ::= { cdx6500ContGSCPTableEntry 1 }

        cdx6500ContGSCPBootPort OBJECT-TYPE
            SYNTAX INTEGER {
                    boot   (1),
                    noBoot (2)
                    }
            ACCESS write-only
            STATUS mandatory
            DESCRIPTION
                "Boot the specified GSC port.
                 boot   : Boot the port
                 noBoot : Do not boot the port."
        ::= { cdx6500ContGSCPTableEntry 2 }

        cdx6500ContGSCPEnablePort OBJECT-TYPE
            SYNTAX INTEGER {
                    enable   (1),
                    noEnable (2)
                    }
            ACCESS write-only
            STATUS mandatory
            DESCRIPTION
                "Enable the specified GSC port.
                 enable   : Enable the GSC port.
                 noEnable : Do not enable the GSC port."
        ::= { cdx6500ContGSCPTableEntry 3 }

        cdx6500ContGSCPDisablePort OBJECT-TYPE
            SYNTAX INTEGER {
                    disable   (1),
                    noDisable (2)
                    }
            ACCESS write-only
            STATUS mandatory
            DESCRIPTION
                "Disable the specified GSC port.
                 disable   : Disable the GSC port.
                 noDisable : Do not disable the GSC port."
        ::= { cdx6500ContGSCPTableEntry 4 }

        cdx6500ContGSCSTable OBJECT-TYPE
            SYNTAX SEQUENCE OF Cdx6500ContGSCSTableEntry
            ACCESS not-accessible
            STATUS mandatory
            DESCRIPTION
                "This table contains the station control objects."
        ::= { cdx6500ContGSC 2 }

        cdx6500ContGSCSTableEntry OBJECT-TYPE
            SYNTAX Cdx6500ContGSCSTableEntry
            ACCESS not-accessible
            STATUS mandatory
            DESCRIPTION
                "Each entry represents a station control parameter."
            INDEX { cdx6500ContGSCSPortNum, cdx6500ContGSCSStnNum }
        ::= { cdx6500ContGSCSTable 1 }

        Cdx6500ContGSCSTableEntry ::= 
            SEQUENCE {
                cdx6500ContGSCSPortNum
                    INTEGER,
                cdx6500ContGSCSStnNum
                    INTEGER,
                cdx6500ContGSCSBootStation
                    INTEGER,
                cdx6500ContGSCSEnableStation
                    INTEGER,
                cdx6500ContGSCSDisableStation
                    INTEGER
                }

        cdx6500ContGSCSPortNum  OBJECT-TYPE
            SYNTAX INTEGER (1..54)
            ACCESS not-accessible
            STATUS mandatory
            DESCRIPTION
                "The GSC Port Number."
        ::= { cdx6500ContGSCSTableEntry 1 }

        cdx6500ContGSCSStnNum OBJECT-TYPE
            SYNTAX INTEGER (1..24)
            ACCESS not-accessible
            STATUS mandatory
            DESCRIPTION
                "The GSC Station Number."
        ::= { cdx6500ContGSCSTableEntry 2 }

        cdx6500ContGSCSBootStation OBJECT-TYPE
            SYNTAX INTEGER {
                    boot   (1),
                    noBoot (2)
                    }
            ACCESS write-only
            STATUS mandatory
            DESCRIPTION
                "Boot the specified GSC station
                 boot   : Boot the station.
                 noBoot : Do not boot the station."
        ::= { cdx6500ContGSCSTableEntry 3 }

        cdx6500ContGSCSEnableStation OBJECT-TYPE
            SYNTAX INTEGER {
                    enable   (1),
                    noEnable (2)
                    }
            ACCESS write-only
            STATUS mandatory
            DESCRIPTION
                "Enable the specified GSC station.
                 enable   : Enable the Station.
                 noEnable : Do not enable the Station."
        ::= { cdx6500ContGSCSTableEntry 4 }

        cdx6500ContGSCSDisableStation OBJECT-TYPE
            SYNTAX INTEGER {
                    disable   (1),
                    noDisable (2) }
            ACCESS write-only
            STATUS mandatory
            DESCRIPTION
                "Disable the specified GSC station.
                 disable   : Disable the station.
                 noDisable : Do not disable the station."
        ::= { cdx6500ContGSCSTableEntry 5 }
          
        END
