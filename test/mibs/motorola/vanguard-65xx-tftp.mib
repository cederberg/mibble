-- Version 1.6, modified 11/18/98

        TFTP-OPT-MIB DEFINITIONS ::= BEGIN

        IMPORTS
            IpAddress
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

          cdx6500Statistics OBJECT IDENTIFIER ::= { cdx6500 3 }
       cdx6500StatTFTPGroup OBJECT IDENTIFIER ::= { cdx6500Statistics 3 }

            cdx6500Controls OBJECT IDENTIFIER ::= { cdx6500 4 }
            cdx6500ContTFTP OBJECT IDENTIFIER ::= { cdx6500Controls 2 }

        -- Textual Conventions

        DisplayString ::= OCTET STRING

        -- TFTP Statistics objects

        cdx6500StatTFTPoperation OBJECT-TYPE
            SYNTAX INTEGER {
                    configurationDownloadToCurrentBank   (1), 
                    configurationDownloadToAlternateBank (2),
                    configurationUploadFromCurrentBank   (3), 
                    configurationUploadFromAlternateBank (4), 
                    softwareDownloadToCurrentBank        (5), 
                    softwareDownloadToAlternateBank      (6),
                    configurationRestoreFromScript       (7),
                    configurationRestoreToScript         (9),
                    noOperation                          (100)
                    }
            ACCESS read-only
            STATUS mandatory
            DESCRIPTION
                "Type and target of the last TFTP transfer or the one in
                 progress, configuration download, configuration upload,
                 software download, current or alternate bank. Configuration
                 transfers will only be supported to/from the current bank at
                 release 4.0."
        ::= { cdx6500StatTFTPGroup 1 } 

        cdx6500StatTFTPIPaddress OBJECT-TYPE
            SYNTAX IpAddress
            ACCESS read-only
            STATUS mandatory
            DESCRIPTION
                "IP address of the remote TFTP application."
        ::= { cdx6500StatTFTPGroup 2 } 

        cdx6500StatTFTPfilename OBJECT-TYPE
            SYNTAX DisplayString
            ACCESS read-only
            STATUS mandatory
            DESCRIPTION
                "File name used in the TFTP RRQ or WRQ message."
        ::= { cdx6500StatTFTPGroup 3 } 

        cdx6500StatTFTPtimestamp OBJECT-TYPE
            SYNTAX DisplayString
            ACCESS read-only
            STATUS mandatory   
            DESCRIPTION
                "Time of last operation. A null terminated string in the form
                 `dd-mm-yyyy hh:mm:ss'. This will represent the starting time
                  if the operation is in progress and the ending time if the
                 operation has completed."
        ::= { cdx6500StatTFTPGroup 4 } 

        cdx6500StatTFTPbytecount OBJECT-TYPE
            SYNTAX INTEGER
            ACCESS read-only
            STATUS mandatory
            DESCRIPTION
                "Total number of bytes transferred. This will represent a
                 running total while the operation is in progress, and the 
                 final total after the operation has completed."
        ::= { cdx6500StatTFTPGroup 5 } 

        cdx6500StatTFTPstatus OBJECT-TYPE
            SYNTAX DisplayString
            ACCESS read-only
            STATUS mandatory
            DESCRIPTION
                "Status of the latest configuration operation including an
                 operation in progress. Possible status messages are: 
                 'TFTP: No transfers since node last booted',
                 'TFTP: Transfer in progress'
                 'TFTP: Operation successful'
                 'TFTP: CMEM access failure'
                 'TFTP: Local transfer failure, <TFTP error message>,
                        Error Code = <TFTP error code>' 
                 'TFTP: Remote transfer failure, <TFTP error message>,
                        Error Code = <TFTP error code>' 
                 'TFTP: System failure'
                 'TFTP: UDP registration failure'
                 'TFTP: Flash erasure in progress'
                 'TFTP: Flash erasure failure'
                 'TFTP: Flash write failure'
                 'TFTP: Error in software image file'
                 'TFTP: Configuration script upload/download partial success'
                 'TFTP: Configuration script upload/download failure'"
        ::= { cdx6500StatTFTPGroup 6 } 

        -- TFTP Controls Group

        cdx6500ContTFTPoperation OBJECT-TYPE
            SYNTAX INTEGER {
                    configurationDownloadToCurrentBank   (1), 
                    configurationDownloadToAlternateBank (2),
                    configurationUploadFromCurrentBank   (3), 
                    configurationUploadFromAlternateBank (4), 
                    softwareDownloadToCurrentBank        (5), 
                    softwareDownloadToAlternateBank      (6),
                    configurationRestoreFromScript       (7),
                    configurationRestoreToScript         (9),
                    noOperation                          (100)
                    }
            ACCESS read-write
            STATUS mandatory
            DESCRIPTION
                "Type and target of the TFTP transfer, configuration download,
                 configuration upload, software download, current or alternate
                 bank.  Configuration transfers will only be supported to/from
                 the current bank at release 4.0.
                 Note that value 'noOperation' is not valid for the write
                 operation."
        ::= { cdx6500ContTFTP 1 }   

        cdx6500ContTFTPIPaddress OBJECT-TYPE
            SYNTAX IpAddress
            ACCESS read-write
            STATUS mandatory
            DESCRIPTION
                "IP address of the remote TFTP application." 
        ::= { cdx6500ContTFTP 2 }   

        cdx6500ContTFTPfilename OBJECT-TYPE
            SYNTAX DisplayString
            ACCESS read-write
            STATUS mandatory
            DESCRIPTION
                "File name to be used in the TFTP RRQ or WRQ message."
        ::= { cdx6500ContTFTP 3 }   

        cdx6500ContTFTPinitiateorder OBJECT-TYPE
            SYNTAX INTEGER {
                    start (1)
                    }
            ACCESS write-only
            STATUS mandatory
            DESCRIPTION
                "Order to initiate the TFTP transfer."
        ::= { cdx6500ContTFTP 4 }

        END
