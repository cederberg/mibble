-- Version 1.3, modified 02/12/98
        
        TDLC-OPT-MIB DEFINITIONS ::= BEGIN

        IMPORTS
            Counter
                FROM RFC1155-SMI 

            OBJECT-TYPE
                FROM RFC-1212;


        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Convention

        DisplayString ::= OCTET STRING

        -- The TDLC Port Configuration Table
        -- This table contains Configuration parameters related to
        -- a TDLC PAD port.

  
        cdx6500PPCTTDLCPortTable OBJECT-TYPE
            SYNTAX SEQUENCE OF Cdx6500PPCTTDLCPortEntry
            ACCESS not-accessible
            STATUS mandatory
            DESCRIPTION
                "This table contains the TDLC port configuration parameters."
        ::= { cdx6500PCTPortProtocolGroup 33 }         
        
        cdx6500PPCTTDLCPortEntry OBJECT-TYPE
            SYNTAX Cdx6500PPCTTDLCPortEntry
            ACCESS not-accessible
            STATUS mandatory
            DESCRIPTION
                "Entries in the TDLC port configuration table."     
            INDEX { tdlcPCfgPortNumber }
        ::= { cdx6500PPCTTDLCPortTable 1 }

        Cdx6500PPCTTDLCPortEntry ::=
            SEQUENCE {
                tdlcPCfgPortNumber
                    INTEGER,
                tdlcPCfgPortType
                    INTEGER,
                tdlcPCfgPortSpeed
                    INTEGER,
                tdlcPCfgConnType 
                    INTEGER,
                tdlcPCfgCRCOption
                    INTEGER,
                tdlcPCfgTANControl
                    INTEGER,
                tdlcPCfgPagTerminalID
                    INTEGER,
                tdlcPCfgResponseControl
                    INTEGER
                }

        tdlcPCfgPortNumber OBJECT-TYPE
            SYNTAX INTEGER (1..54)
            ACCESS read-only
            STATUS mandatory
            DESCRIPTION
                "Port Number of the TDLC port."
        ::= { cdx6500PPCTTDLCPortEntry 1 }

        tdlcPCfgPortType OBJECT-TYPE
            SYNTAX INTEGER {
                    tdlc (49)
                    }
            ACCESS read-only
            STATUS mandatory
            DESCRIPTION
                "Specifies the type of access protocol for this port."
        ::= { cdx6500PPCTTDLCPortEntry 2 }

        tdlcPCfgPortSpeed OBJECT-TYPE
            SYNTAX INTEGER {
                   speed300   (3),
                   speed1200  (4),
                   speed2400  (13),
                   speed4800  (14),
                   speed9600  (15),
                   speed19200 (16)
                   }
            ACCESS read-only
            STATUS mandatory
            DESCRIPTION
                "Specifies port speed in bits per second.
                 speed300   : 300  bits per second.
                 speed1200  : 1200 bits per second.
                 speed2400  : 2400 bits per second.
                 speed4800  : 4800 bits per second.
                 speed9600  : 9600 bits per second.
                 speed19200 : 19200 bits per second."
        ::= { cdx6500PPCTTDLCPortEntry 3 }
 
        tdlcPCfgConnType OBJECT-TYPE
            SYNTAX INTEGER {
                    simp    (1),
                    dtr     (2),
                    nc      (100)
                    }
            ACCESS read-only
            STATUS mandatory
            DESCRIPTION
                "This specifies the control signal handshake and 
                 clocking required for a connection to be made to 
                 this port.
                 simp  - simple, no control signals required.
                 dtr   - dedicated, require the data terminal ready 
                         signal (dtr).
                 nc    - Skipped during configuration."
        ::= { cdx6500PPCTTDLCPortEntry 4 }

        tdlcPCfgCRCOption OBJECT-TYPE
            SYNTAX INTEGER {
                    normal (1),
                    transp (2),
                    nc     (100)
                    }
            ACCESS read-only
            STATUS mandatory
            DESCRIPTION
                "This specifies CRC checking and generation for TNPP
                 data frames.
                 normal - 2 Bytes Binary CRC.
                 transp - 4 Bytes ASCII CRC.
                 nc     - Skipped during configuration."
        ::= { cdx6500PPCTTDLCPortEntry 5 }

        tdlcPCfgTANControl OBJECT-TYPE
            SYNTAX INTEGER {
                    no  (1), 
                    yes (2),
                    nc  (100)
                    }
            ACCESS read-only
            STATUS mandatory
            DESCRIPTION
                "This specifies whether to accept the control characters
                 ACK, NAK, CAN and RS in TNPP data frames.
                 no   - Not Accepted.
                 yes  - Accepted.
                 nc   - Skipped during configuration."
        ::= { cdx6500PPCTTDLCPortEntry 6 }
    
        tdlcPCfgPagTerminalID OBJECT-TYPE
            SYNTAX INTEGER (1..256)         
            ACCESS read-only
            STATUS mandatory
            DESCRIPTION
                "This specifies the identifier for the paging terminal
                 connected."
        ::= { cdx6500PPCTTDLCPortEntry 7 }

        tdlcPCfgResponseControl OBJECT-TYPE
            SYNTAX INTEGER {
                    no  (1),
                    yes (2),
                    nc  (100)
                    }
            ACCESS read-only
            STATUS mandatory
            DESCRIPTION
                "This specifies whether to respond to the paging terminal 
                 when the TFRI does not have connection with TFR.
                 yes  - Will respond only when the TFRI has connection 
                        with TFR.
                 no   - Will respond irrespective of TFRI connection 
                        with TFR."
        ::= { cdx6500PPCTTDLCPortEntry 8 }

        -- TDLC Port Statistics

        cdx6500PPSTTDLCPStatTable OBJECT IDENTIFIER ::=
            { cdx6500PSTPortProtocolGroup 34 }

        tdlcPGenStatTable OBJECT-TYPE
            SYNTAX SEQUENCE OF TDLCPGenStatEntry
            ACCESS not-accessible
            STATUS mandatory
            DESCRIPTION
                "This table contains the TDLC Port statistics
                 general parameters."
        ::= { cdx6500PPSTTDLCPStatTable  1 }
        
        tdlcPGenStatEntry OBJECT-TYPE
            SYNTAX TDLCPGenStatEntry
            ACCESS not-accessible
            STATUS mandatory
            DESCRIPTION
                "Entries in the TDLC port statistics 
                 general parameter table."
            INDEX { tdlcPGStatPortNumber }
        ::= { tdlcPGenStatTable 1 }

        TDLCPGenStatEntry  ::= 
            SEQUENCE {
                tdlcPGStatPortNumber
                    INTEGER,
                tdlcPGStatPortType
                    INTEGER,
                tdlcPGStatPortStatus
                    INTEGER,
                tdlcPGStatPortSpeed
                    INTEGER,
                tdlcPGStatPortUtilIn
                    INTEGER,
                tdlcPGStatPortUtilOut
                    INTEGER,
                tdlcPGStatParityErrors
                    Counter,
                tdlcPGStatOverrunErrors
                    Counter,
                tdlcPGStatFramingErrors
                    Counter
                }
         
        tdlcPGStatPortNumber OBJECT-TYPE
            SYNTAX INTEGER (1..54)
            ACCESS read-only
            STATUS mandatory
            DESCRIPTION
                "Port Number of the TDLC port."
        ::= { tdlcPGenStatEntry 1 }           

        tdlcPGStatPortType OBJECT-TYPE
            SYNTAX INTEGER {
                    tdlc   (48)
                    }
            ACCESS read-only
            STATUS mandatory
            DESCRIPTION 
                "This indicates the type of access protocol for this port."
        ::= { tdlcPGenStatEntry 2 } 

        tdlcPGStatPortStatus OBJECT-TYPE
            SYNTAX INTEGER {
                    disabled (1),
                    up       (2)
                    }
            ACCESS read-only
            STATUS mandatory
            DESCRIPTION
                "This indicates the operational status of the port.
                 disabled : port is disabled.
                 up       : port is up."
        ::= { tdlcPGenStatEntry 3 } 

        tdlcPGStatPortSpeed OBJECT-TYPE
            SYNTAX INTEGER 
            ACCESS read-only
            STATUS mandatory
            DESCRIPTION
                "This indicates port speed in bits per second."
        ::= { tdlcPGenStatEntry 4 }

        tdlcPGStatPortUtilIn OBJECT-TYPE
            SYNTAX INTEGER
            ACCESS read-only
            STATUS mandatory
            DESCRIPTION
                "This indicates the port utilization for the line to
                 port direction."
        ::= { tdlcPGenStatEntry 5 } 

        tdlcPGStatPortUtilOut OBJECT-TYPE
            SYNTAX INTEGER
            ACCESS read-only
            STATUS mandatory
            DESCRIPTION
                "This indicates the port utilization for the port to
                 line direction."
        ::= { tdlcPGenStatEntry 6 }

        tdlcPGStatParityErrors OBJECT-TYPE
            SYNTAX Counter
            ACCESS read-only
            STATUS mandatory
            DESCRIPTION
                "This indicates the number of parity errors counted 
                 by the I/O driver."
        ::= { tdlcPGenStatEntry  7 }

        tdlcPGStatOverrunErrors OBJECT-TYPE
            SYNTAX Counter
            ACCESS read-only
            STATUS mandatory
            DESCRIPTION
                "This indicates the number of overrun errors 
                 detected by the I/O driver."
        ::= { tdlcPGenStatEntry  8 }
 
        tdlcPGStatFramingErrors OBJECT-TYPE
            SYNTAX Counter
            ACCESS read-only
            STATUS mandatory
            DESCRIPTION
                "This indicates the number of framing errors
                 counted by the I/O driver." 
        ::= { tdlcPGenStatEntry 9 }

        tdlcPDataSummaryStatTable OBJECT-TYPE
            SYNTAX SEQUENCE OF TDLCPDataSummaryStatEntry
            ACCESS not-accessible
            STATUS mandatory
            DESCRIPTION
                "This table contains the TNPP port statistics
                 data summary parameters."
        ::= { cdx6500PPSTTDLCPStatTable  2 }

        tdlcPDataSummaryStatEntry OBJECT-TYPE
            SYNTAX TDLCPDataSummaryStatEntry
            ACCESS not-accessible
            STATUS mandatory
            DESCRIPTION
                "Entries in the TDLC port statistics
                 data summary parameter table."
            INDEX { tdlcPDSStatPortNumber }
        ::= { tdlcPDataSummaryStatTable 1 } 

        TDLCPDataSummaryStatEntry ::=
            SEQUENCE {
                tdlcPDSStatPortNumber
                    INTEGER,
                tdlcPDSStatTotalCharIn
                    Counter,
                tdlcPDSStatTotalCharOut
                    Counter,
                tdlcPDSStatTotalFramesIn
                    Counter,
                tdlcPDSStatTotalFramesOut
                    Counter,
                tdlcPDSStatCharInPerSec
                    INTEGER,
                tdlcPDSStatCharOutPerSec
                    INTEGER,
                tdlcPDSStatFramesInPerSec
                    INTEGER,
                tdlcPDSStatFramesOutPerSec
                    INTEGER 
                }

        tdlcPDSStatPortNumber OBJECT-TYPE
            SYNTAX INTEGER (1..54)
            ACCESS read-only
            STATUS mandatory
            DESCRIPTION
                "Port Number of the TDLC port."
        ::= { tdlcPDataSummaryStatEntry 1 }
        
        tdlcPDSStatTotalCharIn OBJECT-TYPE
            SYNTAX Counter 
            ACCESS read-only
            STATUS mandatory
            DESCRIPTION
                "This indicates the total number of characters
                 that have been received by the port."
        ::= { tdlcPDataSummaryStatEntry 2 }

        tdlcPDSStatTotalCharOut OBJECT-TYPE
            SYNTAX Counter
            ACCESS read-only
            STATUS mandatory
            DESCRIPTION
                "This indicates the total number of characters
                 that have been transmitted by the port."
        ::= { tdlcPDataSummaryStatEntry 3 }

        tdlcPDSStatTotalFramesIn OBJECT-TYPE
            SYNTAX Counter
            ACCESS read-only
            STATUS mandatory
            DESCRIPTION
                "This indicates the total number of frames that
                 have been received by the port."
        ::= { tdlcPDataSummaryStatEntry 4 }

        tdlcPDSStatTotalFramesOut OBJECT-TYPE
            SYNTAX Counter
            ACCESS read-only
            STATUS mandatory
            DESCRIPTION
                "This indicates the total number of frames that
                 have been received by the port."
        ::= { tdlcPDataSummaryStatEntry 5 }

        tdlcPDSStatCharInPerSec OBJECT-TYPE
            SYNTAX INTEGER
            ACCESS read-only
            STATUS mandatory
            DESCRIPTION
                "This indicates the rate at which characters 
                 have been received by the port per second."
        ::= { tdlcPDataSummaryStatEntry 6 }

        tdlcPDSStatCharOutPerSec OBJECT-TYPE
            SYNTAX INTEGER
            ACCESS read-only
            STATUS mandatory
            DESCRIPTION
                "This indicates the rate at which characters
                 have been transmitted by the port per second."
        ::= { tdlcPDataSummaryStatEntry 7 } 

        tdlcPDSStatFramesInPerSec OBJECT-TYPE
            SYNTAX INTEGER
            ACCESS read-only
            STATUS mandatory
            DESCRIPTION
                "This indicates the rate at which frames have
                 been received by the port per second."
        ::= { tdlcPDataSummaryStatEntry 8 }

        tdlcPDSStatFramesOutPerSec OBJECT-TYPE
            SYNTAX INTEGER
            ACCESS read-only
            STATUS mandatory
            DESCRIPTION
                "This indicates the rate at which frames have
                 been transmitted by the port per second."
        ::= { tdlcPDataSummaryStatEntry 9 } 

        tdlcPFrameSummaryStatTable OBJECT-TYPE
            SYNTAX SEQUENCE OF TDLCPFrameSummaryStatEntry
            ACCESS not-accessible
            STATUS mandatory
            DESCRIPTION
                "This table contains the TDLC Port statistics
                 frame summary parameters."
        ::= { cdx6500PPSTTDLCPStatTable  3 }

        tdlcPFrameSummaryStatEntry OBJECT-TYPE
            SYNTAX TDLCPFrameSummaryStatEntry
            ACCESS not-accessible
            STATUS mandatory
            DESCRIPTION
                "Entries in the TDLC port statistics 
                 frame summary parameter table."
            INDEX { tdlcPFSStatPortNumber }
        ::= { tdlcPFrameSummaryStatTable 1 }
 
        TDLCPFrameSummaryStatEntry ::=
            SEQUENCE {
                tdlcPFSStatPortNumber
                    INTEGER,
                tdlcPFSStatPagTerminalID
                    INTEGER,
                tdlcPFSStatLinkState
                    INTEGER,
                tdlcPFSStatCRCErrors
                    Counter,
                tdlcPFSStatLinkFramingErrors
                    Counter,
                tdlcPFSStatProtocolErrors
                    Counter,
                tdlcPFSStatENQFramesIn
                    Counter,
                tdlcPFSStatENQFramesOut
                    Counter,
                tdlcPFSStatEOTFramesIn
                    Counter,
                tdlcPFSStatEOTFramesOut
                    Counter,
                tdlcPFSStatACKFramesIn
                    Counter,
                tdlcPFSStatACKFramesOut
                    Counter,
                tdlcPFSStatNAKFramesIn
                    Counter,
                tdlcPFSStatNAKFramesOut
                    Counter,
                tdlcPFSStatRSFramesIn
                    Counter,
                tdlcPFSStatRSFramesOut
                    Counter,
                tdlcPFSStatCANFramesIn
                    Counter,
                tdlcPFSStatCANFramesOut
                    Counter,
                tdlcPFSStatDataFramesInPassed
                    Counter,
                tdlcPFSStatDataFramesOutPassed
                    Counter,
                tdlcPFSStatDataFramesInDiscarded
                    Counter,
                tdlcPFSStatDataFramesOutDiscarded
                    Counter
                }   

        tdlcPFSStatPortNumber OBJECT-TYPE
            SYNTAX INTEGER
            ACCESS read-only
            STATUS mandatory
            DESCRIPTION
                "Port Number of this port."
        ::= { tdlcPFrameSummaryStatEntry  1 }

        tdlcPFSStatPagTerminalID OBJECT-TYPE
            SYNTAX INTEGER (1..256)
            ACCESS read-only
            STATUS mandatory
            DESCRIPTION
                "This specifies the identifier for the paging 
                 terminal connected."
        ::= { tdlcPFrameSummaryStatEntry 2 }

        tdlcPFSStatLinkState OBJECT-TYPE
            SYNTAX INTEGER {
                    init            (1),
                    awaitEnqResp    (2),
                    ready           (3),
                    transmitting    (4),
                    trnsmitResponse (5),
                    na              (100)
                    }
            ACCESS read-only
            STATUS mandatory
            DESCRIPTION
                "This indicates the current link state.
                 init               -   Initialization state.
                 awaitEnqResp       -   Await enquiry response state.
                 ready              -   Ready to communicate state
                 transmitting       -   Transmitting state.
                 transmitResponse   -   Transmit response state.
                 na                 -   Value not available."
        ::= { tdlcPFrameSummaryStatEntry  3 }

        tdlcPFSStatCRCErrors OBJECT-TYPE
            SYNTAX Counter
            ACCESS read-only
            STATUS mandatory
            DESCRIPTION
                "This indicates the total number data frames
                 received with Cyclic Redundancy Check errors."
        ::= { tdlcPFrameSummaryStatEntry  4 }

        tdlcPFSStatLinkFramingErrors OBJECT-TYPE
            SYNTAX Counter
            ACCESS read-only
            STATUS mandatory
            DESCRIPTION
                "This indicates the total number of TNPP framing 
                 errors (Invalid Header,Invalid Control character,
                 Frame Size Exceeded, Incomplete Frame, etc.)."
        ::= { tdlcPFrameSummaryStatEntry  5 }

        tdlcPFSStatProtocolErrors OBJECT-TYPE
            SYNTAX Counter
            ACCESS read-only
            STATUS mandatory
            DESCRIPTION
                "This indicates the number of Protocol errors
                 due to unexpected events ."
        ::= { tdlcPFrameSummaryStatEntry  6 }

        tdlcPFSStatENQFramesIn OBJECT-TYPE
            SYNTAX Counter
            ACCESS read-only
            STATUS mandatory
            DESCRIPTION
                "This indicates the total number of  Enquiry
                 frames received by the port."
        ::= { tdlcPFrameSummaryStatEntry 7 }

        tdlcPFSStatENQFramesOut OBJECT-TYPE
            SYNTAX Counter
            ACCESS read-only
            STATUS mandatory
            DESCRIPTION
                "This indicates the total number of Enquiry
                 frames transmitted by the port." 
        ::= { tdlcPFrameSummaryStatEntry 8 }

        tdlcPFSStatEOTFramesIn OBJECT-TYPE
            SYNTAX Counter
            ACCESS read-only
            STATUS mandatory
            DESCRIPTION
                "This indicates the total number of 
                 End of Transmission frames received by the port."
        ::= { tdlcPFrameSummaryStatEntry 9 } 

        tdlcPFSStatEOTFramesOut OBJECT-TYPE
            SYNTAX Counter
            ACCESS read-only
            STATUS mandatory
            DESCRIPTION
                "This indicates the total number of 
                 End of Transmission frames transmitted by the port."
        ::= { tdlcPFrameSummaryStatEntry 10 }

        tdlcPFSStatACKFramesIn OBJECT-TYPE
            SYNTAX Counter
            ACCESS read-only
            STATUS mandatory
            DESCRIPTION
                "This indicates the total number of Acknowledgment
                 frames received by the port."
        ::= { tdlcPFrameSummaryStatEntry 11 } 

        tdlcPFSStatACKFramesOut OBJECT-TYPE
            SYNTAX Counter
            ACCESS read-only
            STATUS mandatory
            DESCRIPTION
                "This indicates the total number of Acknowledgment
                 frames transmitted by the port."
        ::= { tdlcPFrameSummaryStatEntry 12 }

        tdlcPFSStatNAKFramesIn OBJECT-TYPE
            SYNTAX Counter
            ACCESS read-only
            STATUS mandatory
            DESCRIPTION
                "This indicates the total number of Negative Acknowledgment
                 frames received by the port."
        ::= { tdlcPFrameSummaryStatEntry 13 }  

        tdlcPFSStatNAKFramesOut OBJECT-TYPE
            SYNTAX Counter
            ACCESS read-only
            STATUS mandatory
            DESCRIPTION
                "This indicates the total number of Negative Acknowledgment
                 frames transmitted."
        ::= { tdlcPFrameSummaryStatEntry 14 }

        tdlcPFSStatRSFramesIn OBJECT-TYPE
            SYNTAX Counter
            ACCESS read-only
            STATUS mandatory
            DESCRIPTION
                "This indicates the total number of Request to Stop
                 frames received by the port."
        ::= { tdlcPFrameSummaryStatEntry 15 }

        tdlcPFSStatRSFramesOut OBJECT-TYPE
            SYNTAX Counter
            ACCESS read-only
            STATUS mandatory
            DESCRIPTION
                "This indicates the total number of Request to Stop
                 frames transmitted by the port."
        ::= { tdlcPFrameSummaryStatEntry 16 }

        tdlcPFSStatCANFramesIn OBJECT-TYPE
            SYNTAX Counter
            ACCESS read-only
            STATUS mandatory
            DESCRIPTION
                "This indicates the total number of CANcel report
                 frames received by the port."
        ::= { tdlcPFrameSummaryStatEntry 17 }

        tdlcPFSStatCANFramesOut OBJECT-TYPE
            SYNTAX Counter
            ACCESS read-only
            STATUS mandatory
            DESCRIPTION   
                "This indicates the total number of CANcel report
                 frames transmitted by the port."
        ::= { tdlcPFrameSummaryStatEntry 18 } 
 
        tdlcPFSStatDataFramesInPassed OBJECT-TYPE
            SYNTAX Counter
            ACCESS read-only
            STATUS mandatory
            DESCRIPTION
                " This indicates the total number of valid data frames 
                  received by the port."
        ::= { tdlcPFrameSummaryStatEntry 19 }

        tdlcPFSStatDataFramesOutPassed OBJECT-TYPE
            SYNTAX Counter
            ACCESS read-only
            STATUS mandatory
            DESCRIPTION
                " This indicates the total number of valid data frames
                  transmitted by the port."
        ::= { tdlcPFrameSummaryStatEntry 20 } 
                  
        tdlcPFSStatDataFramesInDiscarded OBJECT-TYPE
            SYNTAX Counter
            ACCESS read-only
            STATUS mandatory
            DESCRIPTION
                " This indicates the total number of data frames received
                  by the  port and discarded."
        ::= { tdlcPFrameSummaryStatEntry 21 }

        tdlcPFSStatDataFramesOutDiscarded OBJECT-TYPE
            SYNTAX Counter
            ACCESS read-only
            STATUS mandatory
            DESCRIPTION
                "This indicates the total number of data frames transmitted
                 by the port and discarded."
        ::= { tdlcPFrameSummaryStatEntry 22 } 
            
        -- TDLC Control Objects

        cdx6500ContTDLCTable OBJECT IDENTIFIER ::=
            { cdx6500Controls 16 }

        -- The TDLC Port Control Table
        -- This table contains the port control parameters specified for TDLC

        cdx6500ContTDLCPortTable OBJECT-TYPE
            SYNTAX SEQUENCE OF Cdx6500ContTDLCPortEntry
            ACCESS not-accessible
            STATUS mandatory
            DESCRIPTION
                "This table contains the TDLC Port Control parameters."
        ::= { cdx6500ContTDLCTable 1 }  

        cdx6500ContTDLCPortEntry OBJECT-TYPE
            SYNTAX Cdx6500ContTDLCPortEntry
            ACCESS not-accessible
            STATUS mandatory
            DESCRIPTION
                "Entries in the TDLC Port Control Table."
            INDEX { tdlcPContPortNumber }
        ::= { cdx6500ContTDLCPortTable 1 } 

        Cdx6500ContTDLCPortEntry ::=
            SEQUENCE {
                tdlcPContPortNumber
                    INTEGER,
                tdlcPContPortControl
                    INTEGER
                }
       
        tdlcPContPortNumber OBJECT-TYPE
            SYNTAX INTEGER (1..54) 
            ACCESS not-accessible
            STATUS mandatory
            DESCRIPTION
                "Port number of the TDLC port."
        ::= { cdx6500ContTDLCPortEntry 1 }

        tdlcPContPortControl OBJECT-TYPE
            SYNTAX INTEGER {
                   boot       (1),
                   enable     (2),
                   disable    (3),
                   busyout    (4),
                   resetstats (5)
                   }
            ACCESS write-only
            STATUS mandatory
            DESCRIPTION
                "Control operations for the specified TDLC port.
                 boot       - Boots the TDLC Port.
                 enable     - Enables the TDLC Port.
                 disable    - Disables the TDLC Port.
                 busyout    - Busyout the  TDLC Port.
                 resetstats - Resets the TDLC port statistics."
        ::= { cdx6500ContTDLCPortEntry 2 }

        END
