-- Version 1.5, modified 02/12/98

        PAD-OPT-MIB DEFINITIONS ::= BEGIN

        IMPORTS
            Counter
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
     cdx6500CfgGeneralGroup OBJECT IDENTIFIER ::= { cdx6500Configuration 2 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Conventions

        Counter16 ::= INTEGER (0..65535)

        DisplayString ::= OCTET STRING


        -- PAD Port Objects

        -- The Pad Port Configuration Table
        -- This table contains Configuration paramaters 
        -- for the Pad Port table.

        cdx6500PPCTPadPortTable OBJECT-TYPE
            SYNTAX SEQUENCE OF Cdx6500PPCTPadPortEntry
            ACCESS not-accessible
            STATUS mandatory
            DESCRIPTION
                "All of the configuration parameters relevant
                 to the Pad Port table.  "
        ::= { cdx6500PCTPortProtocolGroup 1 }

        cdx6500PPCTPadPortEntry OBJECT-TYPE
            SYNTAX Cdx6500PPCTPadPortEntry
            ACCESS not-accessible
            STATUS mandatory
            DESCRIPTION
                "A row of Pad Port configuration parameters."
            INDEX { cdx6500padpCfgPortNum }
        ::= { cdx6500PPCTPadPortTable 1 }

        Cdx6500PPCTPadPortEntry ::=
            SEQUENCE {
                cdx6500padpCfgPortNum
                    INTEGER,
                cdx6500padpCfgConnectionType
                    INTEGER,
                cdx6500padpCfgPortControl
                    DisplayString,
                cdx6500padpCfgPortSpeed
                    INTEGER,
                cdx6500padpCfgAutoBaudSeq
                    INTEGER,
                cdx6500padpCfgDataBits
                    INTEGER,
                cdx6500padpCfgParity
                    INTEGER,
                cdx6500padpCfgStopBits
                    INTEGER,
                cdx6500padpCfgProfileName
                    DisplayString,
                cdx6500padpCfgCallControl
                    DisplayString,
                cdx6500padpCfgTermControl
                    DisplayString,
                cdx6500padpCfgPadPromptNum
                    INTEGER,
                cdx6500padpCfgRemoteParamNum
                    INTEGER,
                cdx6500padpCfgAutoCallMnem
                    DisplayString,
                cdx6500padpCfgAutoCallTimeout
                    INTEGER,
                cdx6500padpCfgMaxAutoCall
                    INTEGER,
                cdx6500padpCfgSubAddress
                    DisplayString,
                cdx6500padpCfgGroupSubaddress
                    DisplayString,
                cdx6500padpCfgCugMembership
                    DisplayString,
                cdx6500padpCfgBillingRecord
                    INTEGER,
                cdx6500padpCfgInviteToClr
                    INTEGER,
                cdx6500padpCfgCallAcceptTime
                    INTEGER,
                cdx6500padpCfgProtectionLevel
                    INTEGER,
                cdx6500padpCfgReconnectTimeout
                    INTEGER,
                cdx6500padpCfgReconnectTries
                    INTEGER,
                cdx6500padpCfgMaxRcvBufLength
                    INTEGER,
                cdx6500padpCfgCommandLanguage
                    INTEGER,
                cdx6500padpCfgNUIFacilityFormat
                    INTEGER,
                cdx6500padpCfgNUIVerifyTimer
                    INTEGER,
                cdx6500padpCfgMaxNUIViolations
                    INTEGER,
                cdx6500padpCfgActionTypeNUIV
                    INTEGER,
                cdx6500padpCfgCalledDTEAddress
                    DisplayString,
                cdx6500padpCfgCallingDTEIdent
                    DisplayString,
                cdx6500padpCfgCallingDTEPasswd
                    DisplayString,
                cdx6500padpCfgX28ResetService
                    DisplayString,
                cdx6500padpCfgX28ClearService
                    DisplayString,
                cdx6500padpCfgMAXMNEMFailures
                    INTEGER,
                cdx6500padpCfgActionTypeMNEMFail
                    INTEGER,
                cdx6500padpCfgActiveLineMessage
                    DisplayString,
                cdx6500padpCfgDelayActiveLine
                    INTEGER
                }

        cdx6500padpCfgPortNum OBJECT-TYPE
            SYNTAX INTEGER (1..54)
            ACCESS read-only
            STATUS mandatory
            DESCRIPTION
                "Specifies the number of the port that you are configuring. 
                 This number also serves as an entry number for the port you
                 are about to configure."
        ::= { cdx6500PPCTPadPortEntry 1 }
          
        cdx6500padpCfgConnectionType OBJECT-TYPE
            SYNTAX INTEGER {
                    simp       (0),
                    dtr        (1),
                    dtrd       (2),
                    emri       (3),
                    emdc       (4),
                    dimo       (5),
                    dimoa      (6),
                    dimob      (7),
                    dtrp       (8),
                    emdcio     (21),
                    newvalSimp (50)
                    }
            ACCESS read-only
            STATUS mandatory
            DESCRIPTION
                "Specify the control signal handshake and clocking required
                 for a connection to be made to this port:
                 simp   - simple, no control signals required.
                 dtr    - dedicated, require the data terminal ready 
                          signal (DTR).
                 dtrd   - same as DTR, except data set ready (DSR) drops 
                          between calls.
                 dtrp   - same as DTR, except DSR/DCD/CTS are held low in 
                          the idle state.
                 dimo   - port handshakes with attached dial modem.
                 dimoa  - same as DIMO except DSR never raised on incoming 
                          call from modem.
                 dimob  - same as DIMO except DSR follows DTR on incoming 
                          call from modem.
                 emri   - port emulates a dial modem with ring indicator (RI).
                 emdc   - port emulates a dial modem with data carrier 
                          detect (DCD).
                 emdcio - port emulates a dial modem with DCD for incoming 
                          and outgoing calls.
                 newvalSimp - same functionality as 'simp', new enumeration
                          added for RFc1155 compatibility."
        ::= { cdx6500PPCTPadPortEntry 2 }
          
        cdx6500padpCfgPortControl OBJECT-TYPE
            SYNTAX DisplayString (SIZE(2..4))
            ACCESS read-only
            STATUS mandatory
            DESCRIPTION
                "Specify any of the following port control options:
                 NONE  - no option specified.
                 MB    - raise Pin 22 when the port becomes disabled."
        ::= { cdx6500PPCTPadPortEntry 3 }
      
        cdx6500padpCfgPortSpeed OBJECT-TYPE
            SYNTAX INTEGER {
                    speed110       (0),
                    speed134       (1),
                    speed300       (2),
                    speed1200      (3),
                    speed600       (4),
                    speed75        (5),
                    speed150       (6),
                    speed1800      (7),
                    speed200       (8),
                    speed100       (9),
                    speed50        (10),
                    speed75to1200  (11),
                    speed2400      (12),
                    speed4800      (13),
                    speed9600      (14),
                    speed19200     (15),
                    speed38400     (16),
                    speed115200    (17),
                    speed57600     (18),
                    speed14400     (19),
                    speed28800     (20),
                    speed12000     (21),
                    speed16800     (22),
                    speed21600     (23),
                    speed24000     (24),
                    speed26400     (25),
                    speed33400     (26),
                    speed7200      (98),
                    speedAuto      (99),
                    newvalSpeed110 (50)
                    }
            ACCESS read-only
            STATUS mandatory
            DESCRIPTION
                "This is the speed of the port in bits per second (baud rate).
                 newvalSpeed110 : same as 'speed110', new enumeration added
                 for RFC1155 compliance."
        ::= { cdx6500PPCTPadPortEntry 4 }
      
        cdx6500padpCfgAutoBaudSeq OBJECT-TYPE
            SYNTAX INTEGER {
                    crOnly       (0),
                    crDotCr      (1),
                    tymnet       (2),
                    telenet      (3),
                    dotDotCr     (4),
                    spacePCr     (5),
                    newvalCrOnly (50)
                    }
            ACCESS read-only
            STATUS mandatory
            DESCRIPTION
                "This is the type of sequence used for autospeed detection 
                 on an autospeed port.
                 crOnly    - autospeed on <CR>
                 crDotCr   - autospeed on <CR>.<CR>
                 tymnet    - autospeed on a 
                 telenet   - autospeed on <CR><CR> for 1200 baud or lower
                             autospeed on @<CR> for 2400 baud or higher
                 dotDotCr  - autospeed on two or more dots followed by <CR>
                 spacePCr  - autospeed on <space>P<CR>
                 newvalCrOnly - same functionality as 'crOnly', new enumeration
                             added for RFC1155 compatibility."
        ::= { cdx6500PPCTPadPortEntry 5 }
          
        cdx6500padpCfgDataBits OBJECT-TYPE
            SYNTAX INTEGER (5..8)
            ACCESS read-only
            STATUS mandatory
            DESCRIPTION
                "This is the number of data bits per character the PAD 
                 port expects when it transmits and receives data from 
                 the attached device."
        ::= { cdx6500PPCTPadPortEntry 6 }
          
        cdx6500padpCfgParity OBJECT-TYPE
            SYNTAX INTEGER {
                    none       (0),
                    space      (1),
                    mark       (2),
                    even       (3),
                    odd        (4),
                    auto       (5),
                    autoA      (6),
                    newvalNone (50)
                    }
            ACCESS       read-only
            STATUS       mandatory
            DESCRIPTION
                "This is the parity the PAD port generates and expects when it
                 transmits and receives data from the attached device.
                 none   - no parity
                 space  - Space Parity
                 mark   - Mark Parity
                 even   - Even Parity
                 odd    - Odd Parity
                 auto   - Auto Parity ( 7 odd / 7 even / 7 ignore )
                 autoA  - Auto Parity ( 7 odd / 7 even / 8 none   ).
                 newvalNone - same functionality as 'none', new enumeration
                          added for RFC1155 compatibility."
        ::= { cdx6500PPCTPadPortEntry 7 }
          
        cdx6500padpCfgStopBits OBJECT-TYPE
            SYNTAX INTEGER {
                    stopBit1       (0),
                    stopBit1p5     (1),
                    stopBit2       (2),
                    newvalStopBit1 (50)
                    }
            ACCESS read-only
            STATUS mandatory
            DESCRIPTION
                "This is the number of stop bits that the PAD port 
                 generates when it transmits data to the attached device. 
                 This parameter has no effect on data that is received from 
                 the attached device.
                 stopBit1   - 1 Stop Bit.
                 stopBit1p5 - 1.5 Stop Bits.
                 stopBit2   - 2 Stop Bits.
                 newvalStopBit1 - same functionality as 'stopBit1', new
                              enumeration added for RFC1155 compatibility."
        ::= { cdx6500PPCTPadPortEntry 8 }
          
        cdx6500padpCfgProfileName OBJECT-TYPE
            SYNTAX DisplayString (SIZE(0..8))
            ACCESS read-only
            STATUS mandatory
            DESCRIPTION
                "This is the name of the PAD profile table to be used by 
                 this PAD port."
        ::= { cdx6500PPCTPadPortEntry 9 }
          
        cdx6500padpCfgCallControl OBJECT-TYPE
            SYNTAX DisplayString (SIZE(4..40))
            ACCESS read-only
            STATUS mandatory
            DESCRIPTION
                "This parameter allows call control to be used as follows:
                 NONE - no option specified
                 AUTO - automatic calling
                 AUTC - automatic calling when carriage return received
                 PCUD - pass call user data to user profiled for no service 
                        signals
                 IBAR - bar calls inbound from PAD user
                 OBAR - bar calls outbound to PAD user
                 MNEM - allow mnemonic calls only
                 EMNEM - allow extended mnemonic call (without DOT)
                 Any combination of above specified by summing 
                 (e.g. AUTO+IBAR+. . .)
                 TMNEM - Call Mnemonic (max 16 alphanumeric characters)
                         which is not resolved in the local node.
                 This option cannot be summed with any of the above."
        ::= { cdx6500PPCTPadPortEntry 10 }
          
        cdx6500padpCfgTermControl OBJECT-TYPE
            SYNTAX DisplayString (SIZE(3..60))
            ACCESS read-only
            STATUS mandatory
            DESCRIPTION
                "Specify options for the attached device:
                 NONE  - no option specified.
                 PASS  - require password entry to use this PAD facility.
                 LIM   - limit X.28 access to CALL and CLR commands only.
                 CUG   - check closed user group; otherwise, CUG passes 
                         transparently.
                 LCPY  - allow local copying to this PAD port.
                 7BIT  - use 7 data bits for character processing.
                 NADD  - prevent PAD port from receiving calling address 
                         and FAC service signals.
                 X28   - automatically return from X.28 mode to PAD mode 
                         after sending the X.28 commands.
                 CNUI  - Centralized NUI verification.
                 CUGOA - check closed user group but allow outgoing access;
                         otherwise, CUG passes transparently.
                 BMSG  - show the PAD Bulletin/Banner Message even if the PAD
                         Profile #6 is configured as 1 or 5.
                 ADDR  - does not show the calling address
                 Any combination of above specified by summing 
                 (e.g. PASS+LIM)."
        ::= { cdx6500PPCTPadPortEntry 11 }
          
        cdx6500padpCfgPadPromptNum OBJECT-TYPE
            SYNTAX INTEGER (0..8)
            ACCESS read-only
            STATUS mandatory
            DESCRIPTION
                "This parameter specifies which entry in the PAD Prompt Table
                 is used as a PAD prompt."
        ::= { cdx6500PPCTPadPortEntry 12 }
          
        cdx6500padpCfgRemoteParamNum OBJECT-TYPE
            SYNTAX INTEGER (0..6)
            ACCESS read-only
            STATUS mandatory
            DESCRIPTION
                "This specifies which entry in the Remote PAD Parameters Table
                 is sent to a remote PAD to update its X.3 characteristics when
                 it connects to this port:
                 0 - no remote PAD update is performed."
        ::= { cdx6500PPCTPadPortEntry 13 }
          
        cdx6500padpCfgAutoCallMnem OBJECT-TYPE
            SYNTAX DisplayString (SIZE(0..8))
            ACCESS read-only
            STATUS mandatory
            DESCRIPTION
                "This mnemonic name is used if this port is configured for 
                 auto-calling."
        ::= { cdx6500PPCTPadPortEntry 14 }
          
        cdx6500padpCfgAutoCallTimeout OBJECT-TYPE
            SYNTAX INTEGER (5..255)
            ACCESS read-only
            STATUS mandatory
            DESCRIPTION
                "This is the time interval in seconds between call attempts
                 when auto-calling."
        ::= { cdx6500PPCTPadPortEntry 15 }
          
        cdx6500padpCfgMaxAutoCall OBJECT-TYPE
            SYNTAX INTEGER (0..255)
            ACCESS read-only
            STATUS mandatory
            DESCRIPTION
                "This parameter is used to specify the number of times 
                 that the PAD port will attempt to call, when auto-calling
                 is enabled. A value of zero, will allow unlimited attempts."
        ::= { cdx6500PPCTPadPortEntry 16 }
      
        cdx6500padpCfgSubAddress OBJECT-TYPE
            SYNTAX DisplayString (SIZE(0..3))
            ACCESS read-only
            STATUS mandatory
            DESCRIPTION
                "Calls addressed to this node and with this subaddress will 
                 be routed to this port."
        ::= { cdx6500PPCTPadPortEntry 17 }
          
        cdx6500padpCfgGroupSubaddress OBJECT-TYPE
            SYNTAX DisplayString (SIZE(0..3))
            ACCESS read-only
            STATUS mandatory
            DESCRIPTION
                "The group subaddress is shared by one or more ports. 
                 Calls addressed to this node and with this subaddress 
                 will be routed to a port within the group."
        ::= { cdx6500PPCTPadPortEntry 18 }
      
        cdx6500padpCfgCugMembership OBJECT-TYPE
            SYNTAX DisplayString (SIZE(0..23))
            ACCESS read-only
            STATUS mandatory
            DESCRIPTION
                "The port may be a member of up to 8 different Closed User
                 Groups (CUGs). Each CUG membership must be a two digit number
                 (except --) and separated by a comma. 
                 ( e.g. 12,34,56,09,02,03 ).
                 --    - No CUG Membership
                 00-99 - CUG Membership"
        ::= { cdx6500PPCTPadPortEntry 19 }
          
        cdx6500padpCfgBillingRecord OBJECT-TYPE
            SYNTAX INTEGER {
                    off       (0),
                    on        (1),
                    newvalOff (50)
                    }
            ACCESS read-only
            STATUS mandatory
            DESCRIPTION
                "This controls whether billing (accounting) records will 
                 be created for calls on this port.
                 newvalOff : same functionality as 'off', new enumeration
                 added for RFC1155 compatibility."
        ::= { cdx6500PPCTPadPortEntry 20 }
          
        cdx6500padpCfgInviteToClr OBJECT-TYPE
            SYNTAX INTEGER {
                    none       (0),
                    clrwo      (1),
                    clrwd      (2),
                    newvalNone (50)
                    }
            ACCESS read-only
            STATUS mandatory
            DESCRIPTION
                "This specifies the handling of Invitation to Clear packet 
                 when received.
                 none  - Do nothing.
                 clrwo - Clear Call without performing a EIA disconnect.
                 clrwd - Clear Call and perform a EIA disconnect.
                 newvalNone - same functionality as 'none', new enumeration
                         added for RFC1155 compatibility."
        ::= { cdx6500PPCTPadPortEntry 21 }
          
        cdx6500padpCfgCallAcceptTime OBJECT-TYPE
            SYNTAX INTEGER (0..255)
            ACCESS read-only
            STATUS mandatory
            DESCRIPTION
                "Specifies the time (in seconds) that the user has to make a
                 successful call, after a call has been cleared, before being
                 automatically disconnected.  A maximum of three call attempts
                 are permitted when the Call Accept Timer is enabled.
                 1-255 - Call Accept Timeout (in seconds)
                 0     - Disables the Call Accept Timer."
        ::= { cdx6500PPCTPadPortEntry 22 }
          
        cdx6500padpCfgProtectionLevel OBJECT-TYPE
            SYNTAX INTEGER {
                    none       (0),
                    cpOnly     (1),
                    fullDcp    (2),
                    newvalNone (50)
                    }
               ACCESS read-only
            STATUS mandatory
            DESCRIPTION
                "This specifies the level of data or connection protection 
                 which will be applied to calls to or from this port.
                 The actual level for a call will be negotiated to the 
                 lesser of this level and the level configured for the other 
                 end of the call.
                 none     - No protection
                 cpOnly   - Connection protection only
                 fullDcp  - Full data and connection protection.
                 newvalNone - same functionality as 'none', new enumeration
                            added for RFC1155 compatibility."
        ::= { cdx6500PPCTPadPortEntry 23 }
          
        cdx6500padpCfgReconnectTimeout OBJECT-TYPE
            SYNTAX INTEGER (1..128)
            ACCESS read-only
            STATUS mandatory
            DESCRIPTION
                "This specifies the number of seconds that DCP on the 
                 originating side will wait between reconnection attempts."
        ::= { cdx6500PPCTPadPortEntry 24 }
          
        cdx6500padpCfgReconnectTries OBJECT-TYPE
            SYNTAX INTEGER (0..127)
            ACCESS read-only
            STATUS mandatory
            DESCRIPTION
                "This specifies the number of times that DCP on the originating
                 side will attempt to reconnect before clearing the call. If 0
                 is entered, it will not attempt to reconnect."
        ::= { cdx6500PPCTPadPortEntry 25 }

        cdx6500padpCfgMaxRcvBufLength OBJECT-TYPE
            SYNTAX INTEGER (1..128)
            ACCESS read-only
            STATUS mandatory
            DESCRIPTION
                "This specifies the number of characters received by the driver
                 before forwarding the packet. This parameter is configurable
                 only for PAD ports of CPU+ cards.
                 1 - 128 : Value stored in MRBLR."
        ::= { cdx6500PPCTPadPortEntry 26 }

        cdx6500padpCfgCommandLanguage OBJECT-TYPE
            SYNTAX INTEGER {
                    ccitt (1),
                    dpn   (2),
                    nc    (100)
                    }
            ACCESS read-only
            STATUS mandatory
            DESCRIPTION
                "This specifies the language for PAD commands.
                 ccitt : X.28 CCITT.
                 dpn   : DPN ITI.
                 nc    : Not configured."
        ::= { cdx6500PPCTPadPortEntry 27 }

        cdx6500padpCfgNUIFacilityFormat OBJECT-TYPE
            SYNTAX INTEGER {
                    odpn    (2),
                    ndpn    (3),
                    dpn1992 (4),
                    nc      (100)
                    }
            ACCESS read-only
            STATUS mandatory
            DESCRIPTION
                "This parameter specifies the format of the NUI facility field.
                 odpn    : Specifies the old DPN format.
                 ndpn    : Specifies the new DPN format.
                 dpn1992 : 1992 NUI format.
                 nc      : Not configured."
        ::= { cdx6500PPCTPadPortEntry 28 }

        cdx6500padpCfgNUIVerifyTimer OBJECT-TYPE
            SYNTAX INTEGER (5..180)
            ACCESS read-only
            STATUS mandatory
            DESCRIPTION
                "Specify the NUI verification timer in seconds.
                 The call is cleared when the timer expires."
        ::= { cdx6500PPCTPadPortEntry 29 }

        cdx6500padpCfgMaxNUIViolations OBJECT-TYPE
            SYNTAX INTEGER (0..10)
            ACCESS read-only
            STATUS mandatory
            DESCRIPTION
                "The maximum number of successive NUI verification failures
                 that can be tolerated when making verification attempts
                 through a pad port."
        ::= { cdx6500PPCTPadPortEntry 30 }

        cdx6500padpCfgActionTypeNUIV OBJECT-TYPE
            SYNTAX INTEGER {
                    none (1),
                    degr (2),
                    lock (3),
                    disc (4),
                    nc   (100)
                    }
            ACCESS read-only
            STATUS mandatory
            DESCRIPTION
                "This specifies the course of action to be taken if the 
                 NUI violations exceed the configured threshold count.
                 This parameter is effective only if the Port Control 
                 parameter is set to CNUI.
                 none : No action is taken .
                 disc : Port is disconnected.
                 degr : Port is busied-out for one minute then re-enabled.
                 lock : Port is disabled. Operator intervention is required 
                        to enable the port.
                 nc   : Not configured."
        ::= { cdx6500PPCTPadPortEntry 31 }

        cdx6500padpCfgCalledDTEAddress OBJECT-TYPE
            SYNTAX DisplayString (SIZE(0..15))
            ACCESS read-only
            STATUS mandatory
            DESCRIPTION
                "Called DTE Address for packets with Call Mnemonic."
        ::= { cdx6500PPCTPadPortEntry 32 }

        cdx6500padpCfgCallingDTEIdent OBJECT-TYPE
            SYNTAX DisplayString (SIZE(0..7))
            ACCESS read-only
            STATUS mandatory
            DESCRIPTION
                "Calling DTE Identifier for packets with Call Mnemonic."
        ::= { cdx6500PPCTPadPortEntry 33 }

        cdx6500padpCfgCallingDTEPasswd OBJECT-TYPE
            SYNTAX DisplayString (SIZE(0..7))
            ACCESS read-only
            STATUS mandatory
            DESCRIPTION
                "Calling DTE Password for packets with Call Mnemonic."
        ::= { cdx6500PPCTPadPortEntry 34 }

        cdx6500padpCfgX28ResetService OBJECT-TYPE
            SYNTAX DisplayString (SIZE(0..7))
            ACCESS read-only
            STATUS mandatory
            DESCRIPTION
                "This is the name of the X.28 Reset Service Signals table
                 to be used by this PAD port."
        ::= { cdx6500PPCTPadPortEntry 35 }

        cdx6500padpCfgX28ClearService OBJECT-TYPE
            SYNTAX DisplayString (SIZE(0..7))
            ACCESS read-only
            STATUS mandatory
            DESCRIPTION
                "This is the name of the X.28 Clear Service Signals table
                 to be used by this PAD port."
        ::= { cdx6500PPCTPadPortEntry 36 }

        cdx6500padpCfgMAXMNEMFailures OBJECT-TYPE
            SYNTAX INTEGER (0..255)
            ACCESS read-only
            STATUS mandatory
            DESCRIPTION
                "The maximum number of successive Mnemonic Call failures
                 that can be tolerated when making a call to the remote
                 using the mnemonic. This parameter is effective only if
                 the Port Control parameter is set to MNEM."
        ::= { cdx6500PPCTPadPortEntry 37 }

        cdx6500padpCfgActionTypeMNEMFail OBJECT-TYPE
            SYNTAX INTEGER {
                    none (1),
                    degr (2),
                    lock (3),
                    disc (4),
                    nc   (100)
                    }
            ACCESS read-only
            STATUS mandatory
            DESCRIPTION
                "This specifies the course of action to be taken if the
                 Mnemonic exceed the configured threshold count. This 
                 parameter is effective only if the Port Control parameter
                 is set to MNEM.
                 none : No action is taken 
                 disc : Port is disconnected.
                 degr : Port is busied-out for one minute then it is re-enabled.
                 lock : Port is disabled. Operator intervention is required 
                        to enable the port.
                 nc   : Not configured."
        ::= { cdx6500PPCTPadPortEntry 38 }

        cdx6500padpCfgActiveLineMessage OBJECT-TYPE
            SYNTAX DisplayString (SIZE(0..32))
            ACCESS read-only
            STATUS mandatory
            DESCRIPTION
                "The message to be printed when the line becomes active (DTR
                 goes high)."
        ::= { cdx6500PPCTPadPortEntry 39 }

        cdx6500padpCfgDelayActiveLine OBJECT-TYPE
            SYNTAX INTEGER (1..5)
            ACCESS read-only
            STATUS mandatory
            DESCRIPTION
                "When the line becomes active (DTR goes high), Active line 
                 message is sent after configured time.
                 This delay is in seconds."
        ::= { cdx6500PPCTPadPortEntry 40 }

        -- The Pad Port Statistics Table
          
        cdx6500PPSTPadPortTable OBJECT-TYPE
            SYNTAX SEQUENCE OF Cdx6500PPSTPadPortEntry
            ACCESS not-accessible
            STATUS mandatory
            DESCRIPTION
                "All of the statistics parameters relevant
                 to the Pad Port table."
        ::= { cdx6500PSTPortProtocolGroup 1 }
          
        cdx6500PPSTPadPortEntry OBJECT-TYPE
            SYNTAX Cdx6500PPSTPadPortEntry
            ACCESS not-accessible
            STATUS mandatory
            DESCRIPTION
                "A row of Pad Port statistics parameters."
            INDEX { cdx6500padpStatPortNum }
        ::= { cdx6500PPSTPadPortTable 1 }
          
        Cdx6500PPSTPadPortEntry ::=
            SEQUENCE {
                cdx6500padpStatPortNum
                    INTEGER,
                cdx6500padpStatPortStatus
                    INTEGER,
                cdx6500padpStatUtilizationIn
                    INTEGER,
                cdx6500padpStatUtilizationOut
                    INTEGER,
                cdx6500padpStatPortSpeed
                    INTEGER,
                cdx6500padpStatCharInTotal
                    Counter,
                cdx6500padpStatCharOutTotal
                    Counter,
                cdx6500padpStatCharsInPerSec
                    INTEGER,
                cdx6500padpStatCharsOutPerSec
                    INTEGER,
                cdx6500padpStatPktInTotal
                    Counter,
                cdx6500padpStatPktOutTotal
                    Counter,
                cdx6500padpStatPktsInPerSec
                    INTEGER,
                cdx6500padpStatPktsOutPerSec
                    INTEGER,
                cdx6500padpStatPktsQueued
                    INTEGER,
                cdx6500padpStatOverrunErrors
                    Counter16,
                cdx6500padpStatParityErrors
                    Counter16,
                cdx6500padpStatFramingErrors
                    Counter16,
                cdx6500padpStatCurrentStatus
                    DisplayString,
                cdx6500padpStatPortState
                    INTEGER
                }
          
        cdx6500padpStatPortNum OBJECT-TYPE
            SYNTAX INTEGER (1..54)
            ACCESS read-only
            STATUS mandatory
            DESCRIPTION
                "Number of the port."
        ::= { cdx6500PPSTPadPortEntry 1 }
          
        cdx6500padpStatPortStatus OBJECT-TYPE
            SYNTAX INTEGER {
                    disabled       (0),
                    busyout        (2),
                    up             (3),
                    newvalDisabled (50)
                    }
            ACCESS read-only
            STATUS mandatory
            DESCRIPTION
                "Status of the port: 
                 up       - port is up and running.
                 busyout  - port has been busied out.
                 disabled - port has been disabled.
                 newvalDisabled : same functionality 'disabled', new
                            new enumeration added RFC1155 compatibility."
        ::= { cdx6500PPSTPadPortEntry 2 }
          
        cdx6500padpStatUtilizationIn OBJECT-TYPE
            SYNTAX INTEGER (0..100)
            ACCESS read-only
            STATUS mandatory
            DESCRIPTION
                "Percentage of port bandwidth in use."
        ::= { cdx6500PPSTPadPortEntry 3 }
          
        cdx6500padpStatUtilizationOut OBJECT-TYPE
            SYNTAX INTEGER (0..100)
            ACCESS read-only
            STATUS mandatory
            DESCRIPTION
                "Percentage of port bandwidth in use."
        ::= { cdx6500PPSTPadPortEntry 4 }
          
        cdx6500padpStatPortSpeed OBJECT-TYPE
            SYNTAX INTEGER
            ACCESS read-only
            STATUS mandatory
            DESCRIPTION
                "The configured port speed."
        ::= { cdx6500PPSTPadPortEntry 5 }
          
        cdx6500padpStatCharInTotal OBJECT-TYPE
            SYNTAX Counter
            ACCESS read-only
            STATUS mandatory
            DESCRIPTION
                "Summary of the characters being received over the port."
        ::= { cdx6500PPSTPadPortEntry 6 }
          
        cdx6500padpStatCharOutTotal OBJECT-TYPE
            SYNTAX Counter
            ACCESS read-only
            STATUS mandatory
            DESCRIPTION
                "Summary of the characters being sent over the port."
        ::= { cdx6500PPSTPadPortEntry 7 }
          
        cdx6500padpStatCharsInPerSec OBJECT-TYPE
            SYNTAX INTEGER
            ACCESS read-only
            STATUS mandatory
            DESCRIPTION
                "Summary of the characters being received over the port."
        ::= { cdx6500PPSTPadPortEntry 8 }
          
        cdx6500padpStatCharsOutPerSec OBJECT-TYPE
            SYNTAX INTEGER
            ACCESS read-only
            STATUS mandatory
            DESCRIPTION
                "Summary of the characters being sent over the port."
        ::= { cdx6500PPSTPadPortEntry 9 }
          
        cdx6500padpStatPktInTotal OBJECT-TYPE
            SYNTAX Counter
            ACCESS read-only
            STATUS mandatory
            DESCRIPTION
                "Summary of the packets being sent over the port."
        ::= { cdx6500PPSTPadPortEntry 10 }
          
        cdx6500padpStatPktOutTotal OBJECT-TYPE
            SYNTAX Counter
            ACCESS read-only
            STATUS mandatory
            DESCRIPTION
                "Summary of the packets being sent over the port."
        ::= { cdx6500PPSTPadPortEntry 11 }
          
        cdx6500padpStatPktsInPerSec OBJECT-TYPE
            SYNTAX INTEGER
            ACCESS read-only
            STATUS mandatory
            DESCRIPTION
                "Summary of the packets being sent over the port."
        ::= { cdx6500PPSTPadPortEntry 12 }
          
        cdx6500padpStatPktsOutPerSec OBJECT-TYPE
            SYNTAX INTEGER
            ACCESS read-only
            STATUS mandatory
            DESCRIPTION
                "Summary of the packets being sent over the port."
        ::= { cdx6500PPSTPadPortEntry 13 }
          
        cdx6500padpStatPktsQueued OBJECT-TYPE
            SYNTAX INTEGER
            ACCESS read-only
            STATUS mandatory
            DESCRIPTION
                "Number of packets queued for output."
        ::= { cdx6500PPSTPadPortEntry 14}
          
        cdx6500padpStatOverrunErrors OBJECT-TYPE
            SYNTAX Counter16
            ACCESS read-only
            STATUS mandatory
            DESCRIPTION
                "Number of Overrun errors since the last reset."
        ::= { cdx6500PPSTPadPortEntry 15 }
          
        cdx6500padpStatParityErrors OBJECT-TYPE
            SYNTAX Counter16
            ACCESS read-only
            STATUS mandatory
            DESCRIPTION
                "Number of Parity errors since the last reset."
        ::= { cdx6500PPSTPadPortEntry 16 }
          
        cdx6500padpStatFramingErrors OBJECT-TYPE
            SYNTAX Counter16
            ACCESS read-only
            STATUS mandatory
            DESCRIPTION
                "Number of Framing errors since the last reset."
        ::= { cdx6500PPSTPadPortEntry 17 }
          
        cdx6500padpStatCurrentStatus OBJECT-TYPE
            SYNTAX DisplayString (SIZE(6..10))
            ACCESS read-only
            STATUS mandatory
            DESCRIPTION
                "Status of the call on the specific port (Disconnect,
                 Calling, Called, Clearing, Connected, Local Copy)"
        ::= { cdx6500PPSTPadPortEntry 18 }

        cdx6500padpStatPortState OBJECT-TYPE
            SYNTAX INTEGER {
                    pad       (0),
                    x28       (1),
                    account   (3),
                    password  (5),
                    newvalPad (50),
                    na        (100)
                    }
            ACCESS read-only
            STATUS mandatory
            DESCRIPTION
                "Current port state:
                 x28      : The port is in Command mode.
                 pad      : The port is in Data mode.
                 account  : The port is waiting for the account name.
                 password : The port is waiting for the password.
                 newvalPad: same functionality as 'pad', new enumeration
                            added for RFC1155 compatibility.
                 na       : Value not available."
        ::= { cdx6500PPSTPadPortEntry 19 }

        -- The Pad Prompt Configuration Table
          
        cdx6500CfgPadPromptTable OBJECT-TYPE
            SYNTAX SEQUENCE OF Cdx6500CfgPadPromptEntry
            ACCESS not-accessible
            STATUS mandatory
            DESCRIPTION
                "All of the configuration parameters relevant
                 to the PAD Prompt table.  "
        ::= { cdx6500CfgGeneralGroup 4 }
      
        cdx6500CfgPadPromptEntry OBJECT-TYPE
            SYNTAX Cdx6500CfgPadPromptEntry
            ACCESS not-accessible
            STATUS mandatory
            DESCRIPTION
                "A row of Pad Prompt table parameters"
            INDEX { cdx6500padpromptEntryNum }
        ::= { cdx6500CfgPadPromptTable 1 }
          
        Cdx6500CfgPadPromptEntry ::=
            SEQUENCE {
                cdx6500padpromptEntryNum
                    INTEGER,
                cdx6500padpromptPromptText
                    DisplayString
                }
          
        cdx6500padpromptEntryNum OBJECT-TYPE
            SYNTAX INTEGER (1..8)
            ACCESS read-only
            STATUS mandatory
            DESCRIPTION
                "This is not a configuration parameter. Instead, it 
                 identifies the particular PAD Prompt Table entry being 
                 configured by the other parameter in the record."
        ::= { cdx6500CfgPadPromptEntry 1 }
      
        cdx6500padpromptPromptText OBJECT-TYPE
            SYNTAX DisplayString (SIZE(0..1024))
            ACCESS read-only
            STATUS mandatory
            DESCRIPTION
                "Enter PAD prompt as an ASCII character string, terminated
                 by a carriage return. Use line feed (^j) to generate a new 
                 line. The prompt can have up to 1023 characters.  "
        ::= {  cdx6500CfgPadPromptEntry 2 }

        -- The Pad Profile Configuration Table
          
        cdx6500CfgPadProfileTable OBJECT-TYPE
            SYNTAX SEQUENCE OF Cdx6500CfgPadProfileEntry
            ACCESS not-accessible
            STATUS mandatory
            DESCRIPTION
                "All of the configuration parameters relevant
                 to the Pad Profile table.  "
        ::= { cdx6500CfgGeneralGroup 8 }
          
        cdx6500CfgPadProfileEntry OBJECT-TYPE
            SYNTAX Cdx6500CfgPadProfileEntry
            ACCESS not-accessible
            STATUS mandatory
            DESCRIPTION
                "A row of Pad Profile configuration parameters"
            INDEX { cdx6500padprofProfileNum }
        ::= { cdx6500CfgPadProfileTable 1 }
          
        Cdx6500CfgPadProfileEntry ::=
            SEQUENCE {
                cdx6500padprofProfileNum
                    INTEGER,
                cdx6500padprofProfileName
                    DisplayString,
                cdx6500padprofPar1
                    INTEGER,
                cdx6500padprofPar2
                    INTEGER,
                cdx6500padprofPar3
                    DisplayString,
                cdx6500padprofPar4
                    INTEGER,
                cdx6500padprofPar5
                    INTEGER,
                cdx6500padprofPar6
                    INTEGER,
                cdx6500padprofPar7
                    INTEGER,
                cdx6500padprofPar9
                    INTEGER,
                cdx6500padprofPar10
                    INTEGER,
                cdx6500padprofPar12
                    INTEGER,
                cdx6500padprofPar13
                    DisplayString,
                cdx6500padprofPar14
                    INTEGER,
                cdx6500padprofPar15
                    INTEGER,
                cdx6500padprofPar16
                    INTEGER,
                cdx6500padprofPar17
                    INTEGER,
                cdx6500padprofPar18
                    INTEGER,
                cdx6500padprofPar19
                    INTEGER,
                cdx6500padprofPar20
                    DisplayString,
                cdx6500padprofPar21
                    INTEGER,
                cdx6500padprofPar22
                    INTEGER,
                cdx6500padprofPar100
                    INTEGER,
                cdx6500padprofPar101
                    INTEGER,
                cdx6500padprofPar102
                    INTEGER,
                cdx6500padprofPar103
                    INTEGER,
                cdx6500padprofPar104
                    INTEGER,
                cdx6500padprofPar105
                    DisplayString,
                cdx6500padprofPar106
                    INTEGER,
                cdx6500padprofPar107
                    INTEGER,
                cdx6500padprofPar108
                    INTEGER,
                cdx6500padprofPar109
                    INTEGER,
                cdx6500padprofPar110
                    INTEGER,
                cdx6500padprofPar111
                    INTEGER,
                cdx6500padprofPar112
                    INTEGER,
                cdx6500padprofPar113
                    INTEGER,
                cdx6500padprofPar114
                    INTEGER,
                cdx6500padprofPar115
                    INTEGER,
                cdx6500padprofPar116
                    INTEGER,
                cdx6500padprofPar117
                    INTEGER,
                cdx6500padprofPar118
                    INTEGER,
                cdx6500padprofPar119
                    INTEGER
                }
          
        cdx6500padprofProfileNum OBJECT-TYPE
            SYNTAX INTEGER (1..16)
            ACCESS read-only
            STATUS mandatory
            DESCRIPTION
                "This is not a configuration parameter. Instead, it 
                 identifies the particular PAD Profile Table entry 
                 being configured by the other parameters in the record."
        ::= { cdx6500CfgPadProfileEntry 1 }
          
        cdx6500padprofProfileName OBJECT-TYPE
            SYNTAX DisplayString (SIZE(0..8))
            ACCESS read-only
            STATUS mandatory
            DESCRIPTION
                "Reference name for this PAD profile. Individual parameter 
                 prompt messages are prefixed with X.3 parameter number. 
                 Numbers greater than 100 indicate proprietary extensions."
        ::= { cdx6500CfgPadProfileEntry 2 }
          
        cdx6500padprofPar1 OBJECT-TYPE
            SYNTAX INTEGER (0..126)
            ACCESS read-only
            STATUS mandatory
            DESCRIPTION
                "#1, enables PAD recall to command mode during a call:
                 0      - PAD recall disabled
                 1      - PAD recall character = DLE = <^P>
                 32-126 - decimal value of character used for PAD recall"
        ::= { cdx6500CfgPadProfileEntry 3 }
          
        cdx6500padprofPar2 OBJECT-TYPE
            SYNTAX INTEGER (0..1)
            ACCESS read-only
            STATUS mandatory
            DESCRIPTION
                "#2, controls echo:
                 0 - echo disabled
                 1 - echo enabled."
        ::= { cdx6500CfgPadProfileEntry 4 }
          
        cdx6500padprofPar3 OBJECT-TYPE
            SYNTAX DisplayString (SIZE(1..18))
            ACCESS read-only
            STATUS mandatory
            DESCRIPTION
                "#3, selects the ASCII characters used for data forwarding:
                 0 - no data forwarding characters
                 1 - A-Z, a-z, 0-9
                 2 - CR
                 4 - ESC, BEL,ENQ, ACK
                 8 - DEL, CAN, DC2
                16 - EOT, ETX
                32 - HT, LF, VT, FF
                64 - all characters in columns 0 and 1 of the ASCII table
                     not mentioned above
               XXX - any combination of the above values."
        ::= { cdx6500CfgPadProfileEntry 5 }
      
        cdx6500padprofPar4 OBJECT-TYPE
            SYNTAX INTEGER (0..255)
            ACCESS read-only
            STATUS mandatory
            DESCRIPTION
                "#4, selects forwarding idle timer delay:
                 0        - idle timer disabled
                 1 to 255 - value of idle timer in 1/20 seconds."
        ::= { cdx6500CfgPadProfileEntry 6 }
      
        cdx6500padprofPar5 OBJECT-TYPE
            SYNTAX INTEGER (0..2)
            ACCESS read-only
            STATUS mandatory
            DESCRIPTION
                "#5, specifies whether the attached terminal is flow 
                 controlled (restrained from sending data) by the PAD port 
                 sending the XON, XOFF characters. Also called Data Restraint
                 Inbound (DRI) using in-band control:
                 0 - no control with XON, XOFF
                 1 - control inbound data from device
                 2 - control inbound data and PAD commands from device
                 For DRI control using V.24 connector control signals 
                 (CTS and pin 14), use parameter #105."
        ::= { cdx6500CfgPadProfileEntry 7 }
      
        cdx6500padprofPar6 OBJECT-TYPE
            SYNTAX INTEGER (0..13)
            ACCESS read-only
            STATUS mandatory
            DESCRIPTION
                "#6, controls PAD service signal messages to the attached 
                 device:
                 0 - no service signal is sent
                 1 - service signals, other than the prompt, are sent
                 4 - prompt service signal is sent
                 5 - all service signals are sent
                 9 - extended format service signals, other than prompt, 
                     are sent
                12 - extended format prompt service signal is sent
                13 - all service signals are sent in extended format."
        ::= { cdx6500CfgPadProfileEntry 8 }
      
        cdx6500padprofPar7 OBJECT-TYPE
            SYNTAX INTEGER (0..21)
            ACCESS read-only
            STATUS mandatory
            DESCRIPTION
                "#7, selects the PAD mode of operation on receipt of a break 
                 signal from the attached terminal:
                 0 - do nothing
                 1 - send Interrupt packet
                 2 - send Reset packet
                 4 - send Indication of Break packet
                 5 - send Interrupt packet and Indication of Break packet
                 8 - escape from data transfer state
                21 - discard output, send Interrupt packet,
                     and send Indication of Break Packet  "
        ::= { cdx6500CfgPadProfileEntry 9 }
      
        cdx6500padprofPar9 OBJECT-TYPE
            SYNTAX INTEGER (0..255)
            ACCESS read-only
            STATUS mandatory
            DESCRIPTION
                "#9, controls padding after carriage return (CR):
                 0        - no padding after CR.
                 1 to 255 - number of padding characters inserted after CR."
        ::= { cdx6500CfgPadProfileEntry 10 }
      
        cdx6500padprofPar10 OBJECT-TYPE
            SYNTAX INTEGER (0..255)
            ACCESS read-only
            STATUS mandatory
            DESCRIPTION
                "#10, controls line folding:
                 0        - no line folding.
                 1 to 255 - number of characters per line."
        ::= { cdx6500CfgPadProfileEntry 11 }
      
        cdx6500padprofPar12 OBJECT-TYPE
            SYNTAX INTEGER (0..1)
            ACCESS read-only
            STATUS mandatory
            DESCRIPTION
                "#12, specifies whether the PAD port is flow controlled
                 (restrained from sending data) by the attached terminal 
                 sending the XON, XOFF characters. Also called Data Restraint 
                 Outbound (DRO) using in-band control:
                 0 - no control with XON, XOFF
                 1 - allow flow control on outbound data and service signals
                 For DRO control using V.24 connector control signals 
                 (CTS and pin 14), use parameter #105."
        ::= { cdx6500CfgPadProfileEntry 12 }
      
        cdx6500padprofPar13 OBJECT-TYPE
            SYNTAX DisplayString (SIZE(1..7))
            ACCESS read-only
            STATUS mandatory
            DESCRIPTION
                "#13, controls line feed insertion after carriage return (CR) 
                 in data transfer state:
                 0 - no line feed insertion
                 1 - after CR in data sent to attached device
                 2 - after CR in data from the attached device
                 4 - after echo of CR to attached device
                 X - any combination of the above values."
        ::= { cdx6500CfgPadProfileEntry 13 }
      
        cdx6500padprofPar14 OBJECT-TYPE
            SYNTAX INTEGER (0..255)
            ACCESS read-only
            STATUS mandatory
            DESCRIPTION
                "#14, controls padding after line feed in the data transfer 
                 state:
                 0        - no padding after line feed
                 1 to 255 - number of padding characters inserted after 
                            line feed."
        ::= { cdx6500CfgPadProfileEntry 14 }
      
        cdx6500padprofPar15 OBJECT-TYPE
            SYNTAX INTEGER (0..1)
            ACCESS read-only
            STATUS mandatory
            DESCRIPTION
                "#15, controls local editing in data transfer state:
                 0 - no editing
                 1 - allow editing (idle timer data forwarding must be 
                     disabled, parameter #4 = 0)
                 Editing is limited to deleting single characters, deleting 
                 the entered line and displaying the entered line."
        ::= { cdx6500CfgPadProfileEntry 15 }
      
        cdx6500padprofPar16 OBJECT-TYPE
            SYNTAX INTEGER (0..127)
            ACCESS read-only
            STATUS mandatory
            DESCRIPTION
                "#16, decimal value of ASCII character used to delete a 
                 character if editing is enabled (parameter #15 = 1)."
        ::= { cdx6500CfgPadProfileEntry 16 }
      
        cdx6500padprofPar17 OBJECT-TYPE
            SYNTAX INTEGER (0..127)
            ACCESS read-only
            STATUS mandatory
            DESCRIPTION
                "#17, decimal value of ASCII character used to delete a line
                 if editing is enabled (parameter #15 = 1)."
        ::= { cdx6500CfgPadProfileEntry 17 }
      
        cdx6500padprofPar18 OBJECT-TYPE
            SYNTAX INTEGER (0..127)
            ACCESS read-only
            STATUS mandatory
            DESCRIPTION
                "#18, decimal value of ASCII character used to display a line
                 if editing is enabled (parameter #15 = 1)."
        ::= { cdx6500CfgPadProfileEntry 18 }
      
        cdx6500padprofPar19 OBJECT-TYPE
            SYNTAX INTEGER (0..126)
            ACCESS read-only
            STATUS mandatory
            DESCRIPTION
                "#19, specifies the type of character delete service signal 
                 sent by PAD:
                 0        - no service signal
                 1        - printing terminals (PAD sends \\ for each delete
                            character received from terminal)
                 2        - display terminals (PAD sends <BS><SP><BS> for
                            each delete character received from terminal)
                 8,32-126 - specifies the ASCII character used as the
                            editing service signal."
        ::= { cdx6500CfgPadProfileEntry 19 }
      
        cdx6500padprofPar20 OBJECT-TYPE
            SYNTAX DisplayString (SIZE(1..22))
            ACCESS read-only
            STATUS mandatory
            DESCRIPTION
                "#20, specifies the echo mask:
                  0 - no echo mask (all characters echoed)
                  1 - no echo of CR
                  2 - no echo of LF
                  4 - no echo of VT, HT, or FF
                  8 - no echo of BEL or BS
                 16 - no echo of ESC or ENQ
                 32 - no echo of ACK, NAK, STX, SOH, EOT, ETB, or ETX
                 64 - no echo of editing characters as designated by
                      parameters 16, 17 and 18
                128 - no echo of all other characters in columns 0 and 1
                      of the ASCII table not mentioned above and character DEL
                XXX - any combination of the above values."
        ::= { cdx6500CfgPadProfileEntry 20 }
      
        cdx6500padprofPar21 OBJECT-TYPE
            SYNTAX INTEGER (0..7)
            ACCESS read-only
            STATUS mandatory
            DESCRIPTION
                "#21, controls the parity treatment of characters received and
                 transmitted to the attached device.
                 0 - No parity checking or generation
                 1 - Parity checked on received characters
                 2 - Parity generated in transmitted characters
                 4 - Parity stripped from received characters
                 x - any combination of the above values."
        ::= { cdx6500CfgPadProfileEntry 21 }
      
        cdx6500padprofPar22 OBJECT-TYPE
            SYNTAX INTEGER (0..255)
            ACCESS read-only
            STATUS mandatory
            DESCRIPTION
                "#22, controls page wait:
                 0        - page wait disabled.
                 1 to 255 - number of line feed characters sent
                            by the PAD for the page wait function."
        ::= { cdx6500CfgPadProfileEntry 22 }
      
        cdx6500padprofPar100 OBJECT-TYPE
            SYNTAX INTEGER (0..127)
            ACCESS read-only
            STATUS mandatory
            DESCRIPTION
                "#100, specifies the ASCII character used to simulate break
                 for attached terminals that do not have a break key:
                 0        - no break character defined
                 1 to 127 - decimal value of the character used to simulate 
                            break."
        ::= { cdx6500CfgPadProfileEntry 23 }
      
        cdx6500padprofPar101 OBJECT-TYPE
            SYNTAX INTEGER (0..127)
            ACCESS read-only
            STATUS mandatory
            DESCRIPTION
                "#101, specifies the ASCII character used to toggle echo 
                 substitution of entered data. This function available only 
                 if parameter #2 = 1:
                 0        - no echo substitution function
                 1 to 127 - decimal value of character to use to toggle
                            on and off the echo substitution."
        ::= { cdx6500CfgPadProfileEntry 24 }
      
        cdx6500padprofPar102 OBJECT-TYPE
            SYNTAX INTEGER (0..127)
            ACCESS read-only
            STATUS mandatory
            DESCRIPTION
                "#102, specifies the ASCII character used to echo all 
                 characters entered by the attached device when echo 
                 substitution is toggled on:
                 0        - no echo when echo substitution toggled on
                 1 to 127 - decimal value of character used as echo, if 
                            echoing is enabled by parameter #2 and substitution 
                            is enabled by parameter #101."
        ::= { cdx6500CfgPadProfileEntry 25 }
      
        cdx6500padprofPar103 OBJECT-TYPE
            SYNTAX INTEGER (0..255)
            ACCESS read-only
            STATUS mandatory
            DESCRIPTION
                "#103, specifies the ASCII character used for the XON 
                 function:
                 0 to 255 - decimal value of the XON character  "
        ::= { cdx6500CfgPadProfileEntry 26 }
      
        cdx6500padprofPar104 OBJECT-TYPE
            SYNTAX INTEGER (0..255)
            ACCESS read-only
            STATUS mandatory
            DESCRIPTION
                "#104, specifies the ASCII character used for the XOFF 
                 function:
                 0 to 255 - decimal value of the XOFF character."
        ::= { cdx6500CfgPadProfileEntry 27 }
      
        cdx6500padprofPar105 OBJECT-TYPE
            SYNTAX DisplayString (SIZE(1..5))
            ACCESS read-only
            STATUS mandatory
            DESCRIPTION
                "#105, specifies whether both the PAD and the attached 
                 terminal are flow controlled (restrained from sending data) 
                 by the use of V.24 control signals, rather than XON, XOFF.
                 This type of control is called out-of-band flow control. 
                 The control applies to data, commands and responses to and 
                 from an attached device:
                 0 - none using connector control signals
                 1 - Data Restraint Outbound, attached device flow controls
                     PAD with connector pin 14
                 2 - Data Restraint Inbound, PAD flow controls attached device
                     with connector pin 5, CTS
                 X - any combination formed by summing (e.g. 1+2 or 3)
                 For DRO control using XON/XOFF, use parameters #5 and #12."
        ::= { cdx6500CfgPadProfileEntry 28 }
      
        cdx6500padprofPar106 OBJECT-TYPE
            SYNTAX INTEGER (0..4)
            ACCESS read-only
            STATUS mandatory
            DESCRIPTION
                "#106, specifies parity of data sent to the network by the PAD:
                 0 - transparent - pass data as received
                 1 - space
                 2 - mark
                 3 - even
                 4 - odd"
        ::= { cdx6500CfgPadProfileEntry 29 }
      
        cdx6500padprofPar107 OBJECT-TYPE
            SYNTAX INTEGER (0..255)
            ACCESS read-only
            STATUS mandatory
            DESCRIPTION
                "#107, is the elapsed time of no user data input after which 
                 a call on the port will be cleared:
                 0        - timer disabled
                 1 to 255 - timer value in minutes."
        ::= { cdx6500CfgPadProfileEntry 30 }
      
        cdx6500padprofPar108 OBJECT-TYPE
            SYNTAX INTEGER (0..127)
            ACCESS read-only
            STATUS mandatory
            DESCRIPTION
                "#108, specifies the ASCII character used to disconnect a call:
                 0        - no character disconnects the call.
                 1 to 127 - decimal value of call disconnect character."
        ::= { cdx6500CfgPadProfileEntry 31 }
      
        cdx6500padprofPar109 OBJECT-TYPE
            SYNTAX INTEGER (0..255)
            ACCESS read-only
            STATUS mandatory
            DESCRIPTION
                "#109, specifies the number of padding characters inserted 
                 in the data sent to the attached device after a form feed:
                 0        - no padding characters inserted.
                 1 to 255 - number of padding characters to insert after FF."
        ::= { cdx6500CfgPadProfileEntry 32 }
      
        cdx6500padprofPar110 OBJECT-TYPE
            SYNTAX INTEGER (0..255)
            ACCESS read-only
            STATUS mandatory
            DESCRIPTION
                "#110, Selects the data forwarding delay after ESC is detected
                 0        - timer disabled.
                 1 to 255 - timer value in 1/20 second."
        ::= { cdx6500CfgPadProfileEntry 33 }
      
        cdx6500padprofPar111 OBJECT-TYPE
            SYNTAX INTEGER (0..3)
            ACCESS read-only
            STATUS mandatory
            DESCRIPTION
                "#111, Controls how the pad handles the echo of data when echo,
                 parameter 2, is on.
                 0        - No Priority. Data is output and characters 
                            are echoed as they arrive.
                 1        - Input Priority. PAD holds output until input from
                            terminal is finished.
                 2        - Output Priority. PAD will reecho input after output.
                 3        - Formatted Screen. PAD will echo one block of data 
                            for each prompt sent from host."
        ::= { cdx6500CfgPadProfileEntry 34 }
      
        cdx6500padprofPar112 OBJECT-TYPE
            SYNTAX INTEGER (0..1)
            ACCESS read-only
            STATUS mandatory
            DESCRIPTION
                "#112, Setting this parameter causes the PAD port to 
                 dynamically forward data packets, as bandwidth becomes 
                 available on the network link. Settings for X.3 parameters 
                 1,2,3,4,15,16,17,18,19,20,100,101, 102,106,108,110,111 and 
                 13 value 2,3,6 or 7 are ignored if parameter 112 is set.
                 0        - Dynamic forwarding turned off.
                 1        - Dynamic forwarding turned on."
        ::= { cdx6500CfgPadProfileEntry 35 }
      
        cdx6500padprofPar113 OBJECT-TYPE
            SYNTAX INTEGER (0..4)
            ACCESS read-only
            STATUS mandatory
            DESCRIPTION
                "#113, Controls Hewlett-Packard flow control.
                 0        - No HP flow control.
                 1        - HP host enq/ack control.
                 2        - HP terminal enq/ack control.
                 3        - HP host xon/xoff control.
                 4        - HP terminal xon/xoff control."
        ::= { cdx6500CfgPadProfileEntry 36 }
      
        cdx6500padprofPar114 OBJECT-TYPE
            SYNTAX INTEGER (0..2)
            ACCESS read-only
            STATUS mandatory
            DESCRIPTION
                "#114, Selects PAD operational mode:
                 0        - Normal PAD.
                 1        - Transparent Polled Async Host PAD.
                 2        - Transparent Polled Async Remote PAD."
        ::= { cdx6500CfgPadProfileEntry 37 }
      
        cdx6500padprofPar115 OBJECT-TYPE
            SYNTAX INTEGER (0..2)
            ACCESS read-only
            STATUS mandatory
            DESCRIPTION
                "#115, Selects Data Forwarding Criteria for Polled Async
                 PADs:
                 0        - Normal.
                 1        - Short Timer.
                 2        - RTS Signal Drop."
        ::= { cdx6500CfgPadProfileEntry 38 }
      
        cdx6500padprofPar116 OBJECT-TYPE
            SYNTAX INTEGER (0..255)
            ACCESS read-only
            STATUS mandatory
            DESCRIPTION
                "#116, Selects forwarding Short Timer duration for Polled 
                 Async PADs:
                 0        - Short Timer disabled.
                 1 to 255 - Duration of Short Timer in milliseconds."
        ::= { cdx6500CfgPadProfileEntry 39 }
      
        cdx6500padprofPar117 OBJECT-TYPE
            SYNTAX INTEGER (0..1)
            ACCESS read-only
            STATUS mandatory
            DESCRIPTION
                "#117, Selects EIA Signalling Action for Polled Async PADs:
                 0        - None.
                 1        - Raise DCD before transmission and drop DCD
                            after transmission."
        ::= { cdx6500CfgPadProfileEntry 40 }
      
        cdx6500padprofPar118 OBJECT-TYPE
            SYNTAX INTEGER (0..1)
            ACCESS read-only
            STATUS mandatory
            DESCRIPTION
                "#118, Setting this parameter causes a Polled Async PAD to 
                 buffer complete async messages from the network before 
                 transmitting them to the attached device.
                 0        - Disabled.
                 1        - Enabled."
        ::= { cdx6500CfgPadProfileEntry 41 }

            cdx6500padprofPar119 OBJECT-TYPE
            SYNTAX INTEGER (0..255)
            ACCESS read-only
            STATUS mandatory
            DESCRIPTION
                "#119, This parameter specifies the amount of time that 
                 DCD is held high before data transmission to the attached 
                 device begins. This parameter is used when EIA Signalling 
                 Action (#117) is configured to 1.
                 0         - DCD to Data Timer disabled.
                 1 to 255  - Duration of DCD to Data Timer in milliseconds."
        ::= { cdx6500CfgPadProfileEntry 42 }

        -- The Remote Pad Parameter Configuration Table
      
        cdx6500CfgRemotePadTable OBJECT-TYPE
            SYNTAX SEQUENCE OF Cdx6500CfgRemotePadEntry
            ACCESS not-accessible
            STATUS mandatory
            DESCRIPTION
                "All of the configuration parameters relevant
                 to the Remote Pad Paramter table."
        ::= { cdx6500CfgGeneralGroup 9 }
      
        cdx6500CfgRemotePadEntry OBJECT-TYPE
            SYNTAX Cdx6500CfgRemotePadEntry
            ACCESS not-accessible
            STATUS mandatory
            DESCRIPTION
                "A row of Remote Pad configuration parameters"
            INDEX { cdx6500remotepadEntryNum }
        ::= { cdx6500CfgRemotePadTable 1 }
      
        Cdx6500CfgRemotePadEntry ::=
            SEQUENCE {
                cdx6500remotepadEntryNum
                    INTEGER,
                cdx6500remotepadParamNum1
                    INTEGER,
                cdx6500remotepadParamVal1
                    INTEGER,
                cdx6500remotepadParamNum2
                    INTEGER,
                cdx6500remotepadParamVal2
                    INTEGER,
                cdx6500remotepadParamNum3
                    INTEGER,
                cdx6500remotepadParamVal3
                    INTEGER,
                cdx6500remotepadParamNum4
                    INTEGER,
                cdx6500remotepadParamVal4
                    INTEGER,
                cdx6500remotepadParamNum5
                    INTEGER,
                cdx6500remotepadParamVal5
                    INTEGER,
                cdx6500remotepadParamNum6
                    INTEGER,
                cdx6500remotepadParamVal6
                    INTEGER,
                cdx6500remotepadParamNum7
                    INTEGER,
                cdx6500remotepadParamVal7
                    INTEGER,
                cdx6500remotepadParamNum8
                    INTEGER,
                cdx6500remotepadParamVal8
                    INTEGER,
                cdx6500remotepadParamNum9
                    INTEGER,
                cdx6500remotepadParamVal9
                    INTEGER,
                cdx6500remotepadParamNum10
                    INTEGER,
                cdx6500remotepadParamVal10
                    INTEGER,
                cdx6500remotepadParamNum11
                    INTEGER,
                cdx6500remotepadParamVal11
                    INTEGER,
                cdx6500remotepadParamNum12
                    INTEGER,
                cdx6500remotepadParamVal12
                    INTEGER,
                cdx6500remotepadParamNum13
                    INTEGER,
                cdx6500remotepadParamVal13
                    INTEGER,
                cdx6500remotepadParamNum14
                    INTEGER,
                cdx6500remotepadParamVal14
                    INTEGER,
                cdx6500remotepadParamNum15
                    INTEGER,
                cdx6500remotepadParamVal15
                    INTEGER,
                cdx6500remotepadParamNum16
                    INTEGER,
                cdx6500remotepadParamVal16
                    INTEGER,
                cdx6500remotepadParamNum17
                    INTEGER,
                cdx6500remotepadParamVal17
                    INTEGER,
                cdx6500remotepadParamNum18
                    INTEGER,
                cdx6500remotepadParamVal18
                    INTEGER,
                cdx6500remotepadParamNum19
                    INTEGER,
                cdx6500remotepadParamVal19
                    INTEGER,
                cdx6500remotepadParamNum20
                    INTEGER,
                cdx6500remotepadParamVal20
                    INTEGER,
                cdx6500remotepadParamNum21
                    INTEGER,
                cdx6500remotepadParamVal21
                    INTEGER,
                cdx6500remotepadParamNum22
                    INTEGER,
                cdx6500remotepadParamVal22
                    INTEGER
                }
      
        cdx6500remotepadEntryNum OBJECT-TYPE
            SYNTAX INTEGER (1..6)
            ACCESS read-only
            STATUS mandatory
            DESCRIPTION
                "This is not a configuration parameter. Instead, it 
                 identifies the particular PAD Parameter Table entry 
                 being configured by the other parameters in the record. 
                 This value is referenced by the parameter Remote PAD 
                 Parameter Number in the PAD Port Record."
        ::= { cdx6500CfgRemotePadEntry 1 }
      
        cdx6500remotepadParamNum1 OBJECT-TYPE
            SYNTAX INTEGER (0..127)
            ACCESS read-only
            STATUS mandatory
            DESCRIPTION
                "Reference number of X.3 parameter sent to remote PAD when 
                 a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 2 }
      
        cdx6500remotepadParamVal1 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 3 }
      
        cdx6500remotepadParamNum2 OBJECT-TYPE
            SYNTAX INTEGER (0..127)
            ACCESS read-only
            STATUS mandatory
            DESCRIPTION
                "Reference number of X.3 parameter sent to remote PAD when 
                 a connection is made to a PAD port in this node. Standard 
                 parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 4 }
      
        cdx6500remotepadParamVal2 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 5 }
      
        cdx6500remotepadParamNum3 OBJECT-TYPE
            SYNTAX INTEGER (0..127)
            ACCESS read-only
            STATUS mandatory
            DESCRIPTION
                "Reference number of X.3 parameter sent to remote PAD when 
                 a connection is made to a PAD port in this node. Standard 
                 parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 6 }
      
        cdx6500remotepadParamVal3 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 7 }
      
        cdx6500remotepadParamNum4 OBJECT-TYPE
            SYNTAX INTEGER (0..127)
            ACCESS read-only
            STATUS mandatory
            DESCRIPTION
                "Reference number of X.3 parameter sent to remote PAD when 
                 a connection is made to a PAD port in this node. Standard 
                 parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 8 }
      
        cdx6500remotepadParamVal4 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 9 }
      
        cdx6500remotepadParamNum5 OBJECT-TYPE
            SYNTAX INTEGER (0..127)
            ACCESS read-only
            STATUS mandatory
            DESCRIPTION
                "Reference number of X.3 parameter sent to remote PAD 
                 when a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 10 }
      
        cdx6500remotepadParamVal5 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 11 }
      
        cdx6500remotepadParamNum6 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 12 }
      
        cdx6500remotepadParamVal6 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 13 }
      
        cdx6500remotepadParamNum7 OBJECT-TYPE
            SYNTAX INTEGER (0..127)
            ACCESS read-only
            STATUS mandatory
            DESCRIPTION
                "Reference number of X.3 parameter sent to remote PAD 
                 when a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 14 }
      
        cdx6500remotepadParamVal7 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 15 }
      
        cdx6500remotepadParamNum8 OBJECT-TYPE
            SYNTAX INTEGER (0..127)
            ACCESS read-only
            STATUS mandatory
            DESCRIPTION
                "Reference number of X.3 parameter sent to remote PAD 
                 when a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 16 }
      
        cdx6500remotepadParamVal8 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 17 }
      
        cdx6500remotepadParamNum9 OBJECT-TYPE
            SYNTAX INTEGER (0..127)
            ACCESS read-only
            STATUS mandatory
            DESCRIPTION
                "Reference number of X.3 parameter sent to remote PAD 
                 when a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 18 }
      
        cdx6500remotepadParamVal9 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 19 }
      
        cdx6500remotepadParamNum10 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 20 }
      
        cdx6500remotepadParamVal10 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 21 }
      
        cdx6500remotepadParamNum11 OBJECT-TYPE
            SYNTAX INTEGER (0..127)
            ACCESS read-only
            STATUS mandatory
            DESCRIPTION
                "Reference number of X.3 parameter sent to remote PAD 
                 when a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 22 }
      
        cdx6500remotepadParamVal11 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 23 }
      
        cdx6500remotepadParamNum12 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 24 }
      
        cdx6500remotepadParamVal12 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 25 }
      
        cdx6500remotepadParamNum13 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 26 }
      
        cdx6500remotepadParamVal13 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 27 }
      
        cdx6500remotepadParamNum14 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 28 }
      
        cdx6500remotepadParamVal14 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 29 }
      
        cdx6500remotepadParamNum15 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 30 }
      
        cdx6500remotepadParamVal15 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 31 }
      
        cdx6500remotepadParamNum16 OBJECT-TYPE
            SYNTAX INTEGER (0..127)
            ACCESS read-only
            STATUS mandatory
            DESCRIPTION
                "Reference number of X.3 parameter sent to remote PAD 
                 when a connection is made to a PAD port in this node. 
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 32 }
      
        cdx6500remotepadParamVal16 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 33 }
      
        cdx6500remotepadParamNum17 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 34 }
      
        cdx6500remotepadParamVal17 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 35 }
      
        cdx6500remotepadParamNum18 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 36 }
      
        cdx6500remotepadParamVal18 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 37 }
      
        cdx6500remotepadParamNum19 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 38 }
      
        cdx6500remotepadParamVal19 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 39 }
      
        cdx6500remotepadParamNum20 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 40 }
      
        cdx6500remotepadParamVal20 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 41 }
      
        cdx6500remotepadParamNum21 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 42 }
      
        cdx6500remotepadParamVal21 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 43 }
      
        cdx6500remotepadParamNum22 OBJECT-TYPE
            SYNTAX INTEGER (0..127)
            ACCESS read-only
            STATUS mandatory
            DESCRIPTION
                "Reference number of X.3 parameter sent to remote PAD 
                 when a connection is made to a PAD port in this node.
                 Standard parameters and function are:
                 1 - PAD recall character    12 - data restraint out
                 2 - echo on/off             13 - <LF> insertion after <CR>
                 3 - forwarding, character   14 - <LF> padding
                 4 - forwarding, timer       15 - editing
                 5 - data restraint in       16 - character delete
                 6 - service signals         17 - line delete
                 7 - break handling          18 - line display
                 8 - discard output          19 - editing type
                 9 - <CR> padding            20 - echo mask
                10 - line folding            21 - parity treatment
                11 - speed                   22 - page wait  "
        ::= { cdx6500CfgRemotePadEntry 44 }
      
        cdx6500remotepadParamVal22 OBJECT-TYPE
            SYNTAX INTEGER (0..255)
            ACCESS read-only
            STATUS mandatory
            DESCRIPTION
                "Corresponding value of referenced X.3 parameter sent to 
                 remote PAD when connection is made. Valid range of parameter 
                 value depends on parameter."
        ::= { cdx6500CfgRemotePadEntry 45 }

             END
