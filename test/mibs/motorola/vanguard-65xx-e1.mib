-- Version 1.5, modified 02/12/98

        E1-OPT-MIB DEFINITIONS ::= BEGIN

        IMPORTS
            Counter, Gauge
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }
    cdx6500PCTT1E1PortTable OBJECT IDENTIFIER ::= { cdx6500PCTPortProtocolGroup 24 }
          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }
    cdx6500PSTT1E1PortTable OBJECT IDENTIFIER ::= { cdx6500PSTPortProtocolGroup 25 }

        -- Textual Conventions

        DisplayString ::= OCTET STRING
       
        PhysicalPortNumber ::= INTEGER (49..50)

        VirtualPortNumber ::= INTEGER (100..255)


        -- Configuration parameters and statistics used by the E1 ports. 

        cdx6500PCTE1PortTable OBJECT IDENTIFIER 
            ::= { cdx6500PCTT1E1PortTable 2 }

        -- E1 Physical Port Configuration Table

        cdx6500PPCTE1PortTable OBJECT-TYPE
            SYNTAX SEQUENCE OF Cdx6500PPCTE1PortEntry
            ACCESS not-accessible
            STATUS mandatory
            DESCRIPTION
                "This table contains the E1 (Physical) Port Configuration 
                 parameters."
        ::= { cdx6500PCTE1PortTable 1 }

        cdx6500PPCTE1PortEntry OBJECT-TYPE
            SYNTAX Cdx6500PPCTE1PortEntry
            ACCESS not-accessible
            STATUS mandatory
            DESCRIPTION
               "A E1 Port Configuration Table Entry. Each entry contains the 
                configuration parameters for a single E1 port."
            INDEX  { cdx6500E1CfgPortNumber }
        ::= { cdx6500PPCTE1PortTable 1 }

        Cdx6500PPCTE1PortEntry ::=
            SEQUENCE {
                cdx6500E1CfgPortNumber
                    PhysicalPortNumber,
                cdx6500E1CfgPortType
                    INTEGER,
                cdx6500E1CfgFormat
                    INTEGER,
                cdx6500E1CfgLineFramingType
                    INTEGER,
                cdx6500E1CfgLineCoding
                    INTEGER,
                cdx6500E1CfgLineImpedence
                    INTEGER,
                cdx6500E1CfgTransmitClock
                    INTEGER,
                cdx6500E1CfgThresholdValueLES
                    INTEGER,
                cdx6500E1CfgThresholdValueLCV
                    INTEGER,
                cdx6500E1CfgThresholdValuePCV
                    INTEGER,
                cdx6500E1CfgThresholdValueCSS
                    INTEGER,
                cdx6500E1CfgThresholdValueES
                    INTEGER,
                cdx6500E1CfgThresholdValueBES
                    INTEGER,
                cdx6500E1CfgThresholdValueSES
                    INTEGER,
                cdx6500E1CfgThresholdValueSEFS
                    INTEGER,
                cdx6500E1CfgThresholdValueUAS
                    INTEGER,
                cdx6500E1CfgThresholdValueDM
                    INTEGER,
                cdx6500E1CfgSwitchType
                    INTEGER,
                cdx6500E1CfgVariant
                    INTEGER,
                cdx6500E1CfgUserNetworkSide
                    INTEGER,
                cdx6500E1CfgCallingIdMsbState
                    INTEGER,
                cdx6500E1BchannelNumbering
                    INTEGER
                }

        cdx6500E1CfgPortNumber OBJECT-TYPE
            SYNTAX PhysicalPortNumber
            ACCESS read-only
            STATUS mandatory
            DESCRIPTION
                "Port number of the (physical) E1 port."
        ::= { cdx6500PPCTE1PortEntry 1 }

        cdx6500E1CfgPortType OBJECT-TYPE
            SYNTAX INTEGER {
                    e1      (45)
                    }
            ACCESS read-only
            STATUS mandatory
            DESCRIPTION
                "This is a digital port having interface type E1.
                 e1      :This is an E1 port."
        ::= { cdx6500PPCTE1PortEntry 2 }

        cdx6500E1CfgFormat OBJECT-TYPE
            SYNTAX INTEGER {
                    channelize (1),
                    isdn       (2),
                    nc         (100)
                    }
            ACCESS read-only
            STATUS mandatory
            DESCRIPTION
                "Specifies the format of the E1 interface.
                 channelize :  DS0 definition fixed, predefined
                               by the telco or the user.
                 isdn       :  DS0 definition defined by the
                               ISDN D channel.
                 nc         :  Skipped during configuration."
        ::= { cdx6500PPCTE1PortEntry 3 }

        cdx6500E1CfgLineFramingType OBJECT-TYPE
            SYNTAX INTEGER {
                    e1CcsFebe (1),
                    e1CcsCrc  (2),
                    e1Ccs     (3),
                    e1CasFebe (4),
                    e1CasCrc  (5),
                    e1Cas     (6),
                    nc        (100)
                    }
            ACCESS read-only
            STATUS mandatory
            DESCRIPTION
                "Indicates the type of framing used by the
                 DS1 circuit -
                 e1CcsFebe : Common Channel Signaling with CRC & Si = FEBE.
                 e1CcsCrc  : Common Channel Signaling with CRC & Si = 1.
                 e1Ccs     : Common Channel Signaling with no CRC & Si = 1.
                 e1CasFebe : Channel Associated Signalling with Si = FEBE.
                 e1CasCrc  : Channel Associated Signalling with CRC.
                 e1Cas     : Channel Associated Signalling.
                 nc        :  Skipped during configuration."
        ::= { cdx6500PPCTE1PortEntry 4 }

        cdx6500E1CfgLineCoding OBJECT-TYPE
            SYNTAX INTEGER {
                    hdb3 (1),
                    ami  (3),
                    nc   (100)
                    }
            ACCESS read-only
            STATUS mandatory
            DESCRIPTION
                "Selects the type of suppression used on the E1 link.
                 hdb3 : High Density Bipolar 3.
                 ami  : Alternate Mark Inversion.
                 nc   : Skipped during configuration."
        ::= { cdx6500PPCTE1PortEntry 5 }

        cdx6500E1CfgLineImpedence OBJECT-TYPE
            SYNTAX INTEGER {
                    li120 (1),
                    li75  (2),
                    nc    (100)
                    }
            ACCESS read-only
            STATUS mandatory
            DESCRIPTION
                "This parameter indicates the line impedence.
                 li120 :The line impedence is 120 ohms.
                 li75  :The line impedence is  75 ohms.
                 nc   : Skipped during configuration."
        ::= { cdx6500PPCTE1PortEntry 6 }

        cdx6500E1CfgTransmitClock OBJECT-TYPE
            SYNTAX INTEGER {
                    node (129),
                    rec  (130),
                    int  (131),
                    nc   (100)
                    }
            ACCESS read-only
            STATUS mandatory
            DESCRIPTION
                "This parameter selects the source of the transmit clock.
                 node : Node Timing (timing off another interface).
                 rec  : Received Timing.
                 int  : Internal Oscillator.
                 nc   : Skipped during configuration."
        ::= { cdx6500PPCTE1PortEntry 7 }

        cdx6500E1CfgThresholdValueLES OBJECT-TYPE
            SYNTAX INTEGER (1..255)
            ACCESS read-only
            STATUS mandatory
            DESCRIPTION
                "Threshold value of Line Errored Seconds (LESs)
                 to report alarms on CTP when exceeded."
        ::= { cdx6500PPCTE1PortEntry 8 }

        cdx6500E1CfgThresholdValueLCV OBJECT-TYPE
            SYNTAX INTEGER (1..255)
            ACCESS read-only
            STATUS mandatory
            DESCRIPTION
                "Threshold value of Line Code Violations (LCVs)
                 to report alarms on CTP when exceeded."
        ::= { cdx6500PPCTE1PortEntry 9 }

        cdx6500E1CfgThresholdValuePCV OBJECT-TYPE
            SYNTAX INTEGER (1..255)
            ACCESS read-only
            STATUS mandatory
            DESCRIPTION
                "Threshold value of Path Code Violations (PCVs)
                 to report alarms on CTP when exceeded."
        ::= { cdx6500PPCTE1PortEntry 10 }

        cdx6500E1CfgThresholdValueCSS OBJECT-TYPE
            SYNTAX INTEGER (1..255)
            ACCESS read-only
            STATUS mandatory
            DESCRIPTION
                "Threshold value of Controlled Slip Seconds (CSSs)
                 to report alarms on CTP when exceeded."
        ::= { cdx6500PPCTE1PortEntry 11 }

        cdx6500E1CfgThresholdValueES OBJECT-TYPE
            SYNTAX INTEGER (1..255)
            ACCESS read-only
            STATUS mandatory
            DESCRIPTION
                "Threshold value of Errored Seconds (ESs)
                 to report alarms on CTP when exceeded."
        ::= { cdx6500PPCTE1PortEntry 12 }

        cdx6500E1CfgThresholdValueBES OBJECT-TYPE
            SYNTAX INTEGER (1..255)
            ACCESS read-only
            STATUS mandatory
            DESCRIPTION
                "Threshold value of Bursty Errored Seconds (BESs)
                 to report alarms on CTP when exceeded."
        ::= { cdx6500PPCTE1PortEntry 13 }

        cdx6500E1CfgThresholdValueSES OBJECT-TYPE
            SYNTAX INTEGER (1..255)
            ACCESS read-only
            STATUS mandatory
            DESCRIPTION
                "Threshold value of Severely Errored Seconds (SESs)
                 to report alarms on CTP when exceeded."
        ::= { cdx6500PPCTE1PortEntry 14 }

        cdx6500E1CfgThresholdValueSEFS OBJECT-TYPE
            SYNTAX INTEGER (1..255)
            ACCESS read-only
            STATUS mandatory
            DESCRIPTION
                "Threshold value of Severely Errored Framing Seconds (SEFSs)
                 to report alarms on CTP when exceeded."
        ::= { cdx6500PPCTE1PortEntry 15 }

        cdx6500E1CfgThresholdValueUAS OBJECT-TYPE
            SYNTAX INTEGER (1..255)
            ACCESS read-only
            STATUS mandatory
            DESCRIPTION
                "Threshold value of Unavailable Seconds (UASs)
                 to report alarms on CTP when exceeded."
        ::= { cdx6500PPCTE1PortEntry 16 }

        cdx6500E1CfgThresholdValueDM OBJECT-TYPE
            SYNTAX INTEGER (1..255)
            ACCESS read-only
            STATUS mandatory
            DESCRIPTION
                "Threshold value of Degraded Minutes (DMs)
                 to report alarms on CTP when exceeded."
        ::= { cdx6500PPCTE1PortEntry 17 }
        
        cdx6500E1CfgSwitchType OBJECT-TYPE
            SYNTAX INTEGER {
                    att4ess  (1),
                    att5ess  (2),
                    ntDms100 (3),
                    ntDms250 (4),
                    md110Us  (5),
                    md110    (6),
                    siemens  (7),
                    ntt      (8),
                    general  (9),
                    nc       (100)
                    }
            ACCESS read-only
            STATUS mandatory
            DESCRIPTION
                "The ISDN switch type. This specifies the type of 
                 equipment to which this span is connected.
                 The possible choices are:
                 att4ess   :  AT&T 4ESS Switch 
                 att5ess   :  AT&T 5ESS Switch 
                 ntDms100  :  Northern Telecom DMS-100 Switch 
                 ntDms250  :  Northern Telecom DMS-250 Switch
                 md110Us   :  Ericsson MD-110 (North America)
                 md110     :  Ericsson MD-110 (International)
                 siemens   :  Siemens EWSD Switch (U.S.)
                 ntt       :  Nippon Telephone and Telegraph switch (Japan)
                 general   :  Any Switch Type that conforms to CCITT standards
                 nc        :  Skipped during configuration"
        ::= { cdx6500PPCTE1PortEntry 18 }

        cdx6500E1CfgVariant OBJECT-TYPE
            SYNTAX INTEGER {
                    att    (1),
                    nt     (2),
                    isdn2  (4),
                    jate   (5),
                    net5   (7),
                    oneTr6 (9),
                    vn3    (10),
                    ccitt  (11),
                    ts014  (14),
                    nc     (100)
                    }
            ACCESS read-only
            STATUS mandatory
            DESCRIPTION
                "Select the ISDN Switch variant. This parameter
                 depends upon the switch type configured.
                 att      :      AT&T Custom
                 nt       :      Northern Telecom
                 isdn2    :      Bellcore National ISDN-2
                 jate     :      JATE-compatible (Japan)
                 net5     :      NET-5 standard (Europe)
                 oneTr6   :      1TR6 standard for PRI (Germany)
                 vn3      :      VN3 standard (France)
                 ccitt    :      General CCITT Q.931 conformance
                 ts014    :      AUSTEL TS014 standard (Australia)
                 nc       :      Skipped during configuration"
        ::= { cdx6500PPCTE1PortEntry 19 }

        cdx6500E1CfgUserNetworkSide OBJECT-TYPE
            SYNTAX INTEGER {
                    user     (1),
                    network  (2),
                    nc       (100)
                    }
            ACCESS read-only
            STATUS mandatory
            DESCRIPTION
                "This parameter specifies whether the T1/E1 port 
                 is emulating the network or user side of the ISDN network.
                 user      :     The T1 or E1 port is emulating the user, 
                                 ex.  the T1 or E1 port is to be connected 
                                 to an ISDN network.
                 network   :     The T1 or E1 port is emulating the network, 
                                 ex. the T1 or E1 port is to be connected 
                                 to an ISDN PBX.
                 nc        :       Skipped during configuration"
        ::= { cdx6500PPCTE1PortEntry 20 }

        cdx6500E1CfgCallingIdMsbState OBJECT-TYPE
            SYNTAX INTEGER {
                    disabled (1),
                    enabled  (2),
                    nc       (100)
                    }
            ACCESS read-only
            STATUS mandatory
            DESCRIPTION
                "For DMS100/250 switches, this parameter defines if the MSB
                 is set or clear in the Calling ID IE.
                 disabled : The MSB in the calling ID IE is cleared.
                 enabled  : The MSB in the calling ID IE is set.
                 nc       : Skipped during configuration"
        ::= { cdx6500PPCTE1PortEntry 21 }

        cdx6500E1BchannelNumbering OBJECT-TYPE
            SYNTAX INTEGER {
                    oneTo31 (1),
                    oneTo30 (2),
                    nc      (100)
                    }
            ACCESS read-only
            STATUS mandatory
            DESCRIPTION
                "This parameter specifies the B-Channel numbering scheme 
                 used by the ISDN service provider.
                 oneTo31   : B-Channels are numbered 1 to 31. B-Channel
                             16 is an invalid number in this scheme.
                 oneTo30   : B-Channels are numbered 1 to 30. B-Channel
                             31 isan invalid number in this scheme.
                 nc        : Skipped during configuration."
        ::= { cdx6500PPCTE1PortEntry 22 }


        -- THE E1 PORT STATISTICS TABLE

        cdx6500PPSTE1PortTable OBJECT-TYPE
            SYNTAX SEQUENCE OF Cdx6500PPSTE1PortEntry
            ACCESS not-accessible
            STATUS mandatory
            DESCRIPTION
                "This table holds statistics information for E1 ports."
        ::= { cdx6500PSTT1E1PortTable 2 }
        
        cdx6500PPSTE1PortEntry OBJECT-TYPE
            SYNTAX Cdx6500PPSTE1PortEntry
            ACCESS not-accessible
            STATUS mandatory
            DESCRIPTION
               "Each entry contains statistics information for one E1 port."
            INDEX { cdx6500E1StatPortNumber }            
        ::= { cdx6500PPSTE1PortTable 1 }
        
        Cdx6500PPSTE1PortEntry ::=
            SEQUENCE {
                cdx6500E1StatPortNumber
                    PhysicalPortNumber,
                cdx6500E1StatPortType
                    INTEGER,
                cdx6500E1StatInterfaceType
                    INTEGER,
                cdx6500E1StatPortState
                    INTEGER,
                cdx6500E1StatAlarmState
                    INTEGER,
                cdx6500E1BoardHWRevAndPartNumber
                    DisplayString
                }

        cdx6500E1StatPortNumber OBJECT-TYPE
            SYNTAX PhysicalPortNumber
            ACCESS read-only
            STATUS mandatory
            DESCRIPTION
                "Port number of the (physical) E1 port."
        ::= { cdx6500PPSTE1PortEntry 1 }           

        cdx6500E1StatTimeSinceLastResetType OBJECT-TYPE
            SYNTAX DisplayString
            ACCESS read-only
            STATUS mandatory
            DESCRIPTION
                "Time since last reset has happened for the port."
        ::= { cdx6500PPSTE1PortEntry 2 }

        cdx6500E1StatPortType OBJECT-TYPE
            SYNTAX INTEGER {
                    e1 (45)
                    }
            ACCESS read-only
            STATUS mandatory
            DESCRIPTION
                "The configured value of the Port Type.
                 e1 : This is a digital port with interface type E1."
        ::= { cdx6500PPSTE1PortEntry 3 }
        
        cdx6500E1StatInterfaceType OBJECT-TYPE
            SYNTAX INTEGER {
                    it120 (1),
                    it75  (2),
                    na    (100)
                    }
            ACCESS read-only
            STATUS mandatory
            DESCRIPTION
                "This parameter indicates the interface type of this port.
                 it120 : Interface type is 120 ohms.
                 it75  : Interface type is 75 ohms.
                 na    : Value not available."
        ::= { cdx6500PPSTE1PortEntry 4 }
                    
        cdx6500E1StatPortState OBJECT-TYPE
            SYNTAX INTEGER {
                    disabled (1),
                    enabled  (2),
                    na       (100)
                    }
            ACCESS read-only
            STATUS mandatory
            DESCRIPTION
                "The current port state :
                 disabled : The port has been disabled.
                 enabled  : The port has been enabled.
                 na       : Value not available."
        ::= { cdx6500PPSTE1PortEntry 5 }
        
        cdx6500E1StatAlarmState OBJECT-TYPE
            SYNTAX INTEGER {
                    none (1),
                    rai  (2),
                    ais  (3),
                    los  (4),
                    fas  (5),
                    lof  (6),
                    na   (100)
                    }
            ACCESS read-only
            STATUS mandatory
            DESCRIPTION
                "The alarm state of the port :
                 none : No alarm (normal).
                 rai  : Remote Alarm Indication.
                 ais  : Alarm Indication Signal.
                 los  : Loss of Signal.
                 fas  : Frame Alignment Signal (FAS) High Error Rate.
                 lof  : Loss of Frame (LOF) Alignment.
                 na   : Value not available."
        ::= { cdx6500PPSTE1PortEntry 6 }
        
        cdx6500E1BoardHWRevAndPartNumber OBJECT-TYPE
            SYNTAX DisplayString
            ACCESS read-only
            STATUS mandatory
            DESCRIPTION
                "Hardware Revision and part number of the board."
        ::= { cdx6500PPSTE1PortEntry 7 }
        
        -- The DAILY HISTORY TABLE

        cdx6500E1StatDailyHistoryTable OBJECT-TYPE
            SYNTAX SEQUENCE OF Cdx6500E1StatDailyHistoryEntry
            ACCESS not-accessible
            STATUS mandatory
            DESCRIPTION
               "The E1 Daily History Table contains various statistics
                collected over the previous 24 hours which are broken
                into 96 completed 15 minute intervals."
        ::= { cdx6500PSTT1E1PortTable 4 }

        cdx6500E1StatDailyHistoryEntry OBJECT-TYPE
            SYNTAX Cdx6500E1StatDailyHistoryEntry
            ACCESS not-accessible
            STATUS mandatory
            DESCRIPTION
                "An entry in the E1 Daily History Table."
            INDEX { cdx6500E1StatDailyHistoryPortNumber,
                    cdx6500E1StatDailyHistoryInterval }
        ::= { cdx6500E1StatDailyHistoryTable 1 }

        Cdx6500E1StatDailyHistoryEntry ::=
            SEQUENCE {
                cdx6500E1StatDailyHistoryInterval
                    INTEGER,
                cdx6500E1StatDailyHistoryLES
                    Gauge,
                cdx6500E1StatDailyHistoryLCV
                    Gauge,
                cdx6500E1StatDailyHistoryPCV
                    Gauge,
                cdx6500E1StatDailyHistoryCSS
                    Gauge,
                cdx6500E1StatDailyHistoryES
                    Gauge,
                cdx6500E1StatDailyHistoryBES
                    Gauge,
                cdx6500E1StatDailyHistorySES
                    Gauge,
                cdx6500E1StatDailyHistorySEFS
                    Gauge,
                cdx6500E1StatDailyHistoryUAS
                    Gauge,
                cdx6500E1StatDailyHistoryDM
                    Gauge,
                cdx6500E1StatDailyHistoryPortNumber
                    PhysicalPortNumber
                }

        cdx6500E1StatDailyHistoryInterval OBJECT-TYPE
            SYNTAX INTEGER (1..96)
            ACCESS read-only
            STATUS mandatory
            DESCRIPTION
                "This gives the history at 15 minute intervals.Each 
                 block represents a 15 minute interval of the day, 
                 starting from 00:15 and ending at 24:00.Thus there 
                 are 96 such blocks possible.Therefore,
                 1  represents the history at 00:15 .
                 2  represents the history at 00:30 .
                 ..........
                 96 represents the history at 24:00 ."
        ::= { cdx6500E1StatDailyHistoryEntry 1 }

        cdx6500E1StatDailyHistoryLES OBJECT-TYPE
            SYNTAX Gauge
            ACCESS read-only
            STATUS mandatory
            DESCRIPTION
                "The number of Line Errored Seconds (LESs)
                 encountered by the E1 interface in one of 
                 the previous 96, individual 15 minute intervals."
        ::= { cdx6500E1StatDailyHistoryEntry 2 }

        cdx6500E1StatDailyHistoryLCV OBJECT-TYPE
            SYNTAX Gauge
            ACCESS read-only
            STATUS mandatory
            DESCRIPTION
                "The number of Line Code Violations (LCVs)
                 encountered by the E1 interface in one of
                 the previous 96, individual 15 minute intervals."
        ::= { cdx6500E1StatDailyHistoryEntry 3 }

        cdx6500E1StatDailyHistoryPCV OBJECT-TYPE
            SYNTAX Gauge
            ACCESS read-only
            STATUS mandatory
            DESCRIPTION
                "The number of Path Coding Violations (PCVs)
                 encountered by the E1 interface in one of 
                 the previous 96, individual 15 minute intervals."
        ::= { cdx6500E1StatDailyHistoryEntry 4 }

        cdx6500E1StatDailyHistoryCSS OBJECT-TYPE
            SYNTAX Gauge
            ACCESS read-only
            STATUS mandatory
            DESCRIPTION
                "The number of Controlled Slip Seconds (CSSs)
                 encountered by the E1 interface in one of 
                 the previous 96, individual 15 minute intervals."
        ::= { cdx6500E1StatDailyHistoryEntry 5 }

        cdx6500E1StatDailyHistoryES OBJECT-TYPE
            SYNTAX Gauge
            ACCESS read-only
            STATUS mandatory
            DESCRIPTION
                "The number of Errored Seconds (ESs)
                 encountered by the E1 interface in one of 
                 the previous 96, individual 15 minute intervals."
        ::= { cdx6500E1StatDailyHistoryEntry 6 }

        cdx6500E1StatDailyHistoryBES OBJECT-TYPE
            SYNTAX Gauge
            ACCESS read-only
            STATUS mandatory
            DESCRIPTION
                "The number of Bursty Errored Seconds (BESs)
                 encountered by the E1 interface in one of 
                 the previous 96, individual 15 minute intervals."
        ::= { cdx6500E1StatDailyHistoryEntry 7 }

        cdx6500E1StatDailyHistorySES OBJECT-TYPE
            SYNTAX Gauge
            ACCESS read-only
            STATUS mandatory
            DESCRIPTION
                "The number of Severely Errored Seconds (SESs)
                 encountered by the E1 interface in one of 
                 the previous 96, individual 15 minute intervals."
        ::= { cdx6500E1StatDailyHistoryEntry 8 }

        cdx6500E1StatDailyHistorySEFS OBJECT-TYPE
            SYNTAX Gauge
            ACCESS read-only
            STATUS mandatory
            DESCRIPTION
                "The number of Severely Errored Framing Seconds 
                 (SEFSs) encountered by the E1 interface in one of 
                 the previous 96, individual 15 minute intervals."
        ::= { cdx6500E1StatDailyHistoryEntry 9 }

        cdx6500E1StatDailyHistoryUAS OBJECT-TYPE
            SYNTAX Gauge
            ACCESS read-only
            STATUS mandatory
            DESCRIPTION
                "The number of Unavailable Seconds (UASs)
                 encountered by the E1 interface in one of 
                 the previous 96, individual 15 minute intervals."
        ::= { cdx6500E1StatDailyHistoryEntry 10 }

        cdx6500E1StatDailyHistoryDM OBJECT-TYPE
            SYNTAX Gauge
            ACCESS read-only
            STATUS mandatory
            DESCRIPTION
                "The number of Degraded Minutes (DMs)
                 encountered by the E1 interface in one of 
                 the previous 96, individual 15 minute intervals."
        ::= { cdx6500E1StatDailyHistoryEntry 11 }

        cdx6500E1StatDailyHistoryPortNumber OBJECT-TYPE
            SYNTAX PhysicalPortNumber
            ACCESS read-only
            STATUS mandatory
            DESCRIPTION
                "The port number of the E1 port."
        ::= { cdx6500E1StatDailyHistoryEntry 12 }

        -- ABCD STATE TABLE

        cdx6500E1StatABCDStateTable OBJECT-TYPE
            SYNTAX SEQUENCE OF Cdx6500E1StatABCDStateEntry
            ACCESS not-accessible
            STATUS mandatory
            DESCRIPTION
                "The ABCD State Table contains the current
                 TX / RX ABCD state of the Configured DS0 Channels."
        ::= { cdx6500PSTT1E1PortTable 6 } 

        cdx6500E1StatABCDStateEntry OBJECT-TYPE
            SYNTAX Cdx6500E1StatABCDStateEntry
            ACCESS not-accessible
            STATUS mandatory
            DESCRIPTION
                "An entry in the ABCD State Table."
            INDEX { cdx6500E1StatABCDStatePortNumber, 
                    cdx6500E1StatABCDStateDS0ChannelNumber }
        ::= { cdx6500E1StatABCDStateTable 1 }

        Cdx6500E1StatABCDStateEntry ::=
            SEQUENCE {
                cdx6500E1StatABCDStateDS0ChannelNumber
                    INTEGER,
                cdx6500E1StatABCDStateCurrentTxState
                    DisplayString,
                cdx6500E1StatABCDStateCurrentRxState
                    DisplayString,
                cdx6500E1StatABCDStatePortNumber
                    PhysicalPortNumber
                }

        cdx6500E1StatABCDStateDS0ChannelNumber OBJECT-TYPE
            SYNTAX INTEGER (1..24)
            ACCESS read-only
            STATUS mandatory
            DESCRIPTION
                "Channel number of the configured DS0 channel."
        ::= { cdx6500E1StatABCDStateEntry 1 }

        cdx6500E1StatABCDStateCurrentTxState OBJECT-TYPE
            SYNTAX DisplayString
            ACCESS read-only
            STATUS deprecated
            DESCRIPTION
               "Current TX ABCD state of the configured DS0 channels. This
                object is no longer supported."
        ::= { cdx6500E1StatABCDStateEntry 2 }

        cdx6500E1StatABCDStateCurrentRxState OBJECT-TYPE
            SYNTAX DisplayString
            ACCESS read-only
            STATUS mandatory
            DESCRIPTION
               "Current RX ABCD state of the configured DS0 channels."
        ::= { cdx6500E1StatABCDStateEntry 3 }   

        cdx6500E1StatABCDStatePortNumber OBJECT-TYPE
            SYNTAX PhysicalPortNumber
            ACCESS read-only
            STATUS mandatory
            DESCRIPTION
               "Port number of the E1 port."
        ::= { cdx6500E1StatABCDStateEntry 4 }

        -- ISDN Call Status

        cdx6500E1ISDNStatusTable OBJECT-TYPE
            SYNTAX SEQUENCE OF Cdx6500E1StatISDNStatusEntry
            ACCESS not-accessible
            STATUS mandatory
            DESCRIPTION
                "This table holds ISDN statistics information for E1 ports."
        ::= { cdx6500PSTT1E1PortTable 8 }
        
        cdx6500E1StatISDNStatusEntry OBJECT-TYPE
            SYNTAX Cdx6500E1StatISDNStatusEntry
            ACCESS not-accessible
            STATUS mandatory
            DESCRIPTION
                "Each entry contains statistics information for one E1 port."
            INDEX { cdx6500E1StatISDNStatusPortNumber }
        ::= { cdx6500E1ISDNStatusTable 1 }

        Cdx6500E1StatISDNStatusEntry ::=
            SEQUENCE {
                cdx6500E1StatISDNStatusPortNumber
                    PhysicalPortNumber,
                cdx6500E1StatNumRxCallsSinceLastReset
                    INTEGER,
                cdx6500E1StatNumRxCallsRejected
                    INTEGER,
                cdx6500E1StatRxLastCallFailureCause
                    INTEGER,
                cdx6500E1StatRxLastCalledNumber
                    DisplayString,
                cdx6500E1StatRxLastCallingNumber
                    DisplayString,
                cdx6500E1StatRxMinCallDuration
                    DisplayString,
                cdx6500E1StatRxMaxCallDuration
                    DisplayString,
                cdx6500E1StatRxAvgCallDuration
                    DisplayString,
                cdx6500E1StatNumTxCallsSinceLastReset
                    INTEGER,
                cdx6500E1StatNumTxCallsRejected
                    INTEGER,
                cdx6500E1StatTxLastCallFailureCause
                    INTEGER,                
                cdx6500E1StatTxLastCalledNumber
                    DisplayString,
                cdx6500E1StatTxLastCallingNumber
                    DisplayString,
                cdx6500E1StatTxMinCallDuration
                    DisplayString,
                cdx6500E1StatTxMaxCallDuration
                    DisplayString,
                cdx6500E1StatTxAvgCallDuration
                    DisplayString,
                cdx6500E1StatDchannelState
                    INTEGER
                }

        cdx6500E1StatISDNStatusPortNumber OBJECT-TYPE
            SYNTAX PhysicalPortNumber
            ACCESS read-only
            STATUS mandatory
            DESCRIPTION
               "The port number of the E1 port."
        ::= { cdx6500E1StatISDNStatusEntry 1 }

        cdx6500E1StatNumRxCallsSinceLastReset OBJECT-TYPE
            SYNTAX INTEGER
            ACCESS read-only
            STATUS mandatory
            DESCRIPTION
                "The number of inbound calls that were attempted
                 since the last statistics reset."
        ::= { cdx6500E1StatISDNStatusEntry 2 }

        cdx6500E1StatNumRxCallsRejected OBJECT-TYPE
            SYNTAX INTEGER
            ACCESS read-only
            STATUS mandatory
            DESCRIPTION
                "The number of inbound calls that were rejected
                 since the last statistics reset."
        ::= { cdx6500E1StatISDNStatusEntry 3 }

        cdx6500E1StatRxLastCallFailureCause OBJECT-TYPE
            SYNTAX INTEGER {
                    noFailureReported          (193),
                    noAvailableVirtualPort     (194),
                    securityViolation          (195),
                    noResourcesAvailable       (196),
                    callRejected               (197),
                    invalidPhoneNumber         (198),
                    outgoingCallRequestTimeout (199),
                    callCollision              (200),
                    virtualPortNotAvailable    (201),
                    invalidConfiguration       (202),
                    na                         (255)
                    }
            ACCESS read-only
            STATUS mandatory
            DESCRIPTION
               "The reason the last inbound call was rejected,
                since the last statistics reset.
                The posssible values are:
                noFailureReported          : No call failure
                noAvailableVirtualPort     : No Virtual Port available
                securityViolation          : Password/Calling ID security failed
                noResourcesAvailable       : No resources available
                callRejected               : Call failed by Xircom card
                invalidPhoneNumber         : Incorrect phone number
                outgoingCallRequestTimeout : Outgoing call request timed out
                callCollision              : A call collision occurred
                virtualPortNotAvailable    : Virtual port not available
                invalidConfiguration       : Invalid configuration
                na                         : Value not available"
        ::= { cdx6500E1StatISDNStatusEntry 4 }

        cdx6500E1StatRxLastCalledNumber OBJECT-TYPE
            SYNTAX DisplayString (SIZE (0..15))
            ACCESS read-only
            STATUS mandatory
            DESCRIPTION
                "The phone number of the virtual port of the last ISDN
                 call made into this node."
        ::= { cdx6500E1StatISDNStatusEntry 5 }

        cdx6500E1StatRxLastCallingNumber OBJECT-TYPE
            SYNTAX DisplayString (SIZE (0..15))
            ACCESS read-only
            STATUS mandatory
            DESCRIPTION
                "The phone number of last party to make an ISDN
                 call into this node."
        ::= { cdx6500E1StatISDNStatusEntry 6 }

        cdx6500E1StatRxMinCallDuration OBJECT-TYPE
            SYNTAX DisplayString
            ACCESS read-only
            STATUS mandatory
            DESCRIPTION
                "The minimum call duration of all inbound ISDN calls made
                 into this node, since the last statistics reset."
        ::= { cdx6500E1StatISDNStatusEntry 7 }

        cdx6500E1StatRxMaxCallDuration OBJECT-TYPE
            SYNTAX DisplayString
            ACCESS read-only
            STATUS mandatory
            DESCRIPTION
                "The maximum call duration of all inbound ISDN calls made
                 into this node, since the last statistics reset."
        ::= { cdx6500E1StatISDNStatusEntry 8 }

        cdx6500E1StatRxAvgCallDuration OBJECT-TYPE
            SYNTAX DisplayString
            ACCESS read-only
            STATUS mandatory
            DESCRIPTION
                "The average call duration of all inbound ISDN calls made
                 into this node, since the last statistics reset."
        ::= { cdx6500E1StatISDNStatusEntry 9 }

        cdx6500E1StatNumTxCallsSinceLastReset OBJECT-TYPE
            SYNTAX INTEGER
            ACCESS read-only
            STATUS mandatory
            DESCRIPTION
                "The number of outbound calls that were attempted
                 since the last statistics reset."
        ::= { cdx6500E1StatISDNStatusEntry 10 }

        cdx6500E1StatNumTxCallsRejected OBJECT-TYPE
            SYNTAX INTEGER
            ACCESS read-only
            STATUS mandatory
            DESCRIPTION
                "The number of outbound calls that were rejected
                 since the last statistics reset."
        ::= { cdx6500E1StatISDNStatusEntry 11 }

        cdx6500E1StatTxLastCallFailureCause OBJECT-TYPE
            SYNTAX INTEGER {
                    noFailureReported          (193),
                    noAvailableVirtualPort     (194),
                    securityViolation          (195),
                    noResourcesAvailable       (196),
                    callRejected               (197),
                    invalidPhoneNumber         (198),
                    outgoingCallRequestTimeout (199),
                    callCollision              (200),
                    virtualPortNotAvailable    (201),
                    invalidConfiguration       (202),
                    na                         (255)
                    }
            ACCESS read-only
            STATUS mandatory
            DESCRIPTION
                "The reason the last outbound call was rejected,
                 since the last statistics reset.
                 The posssible values are:
                 noFailureReported          : No call failure.
                 noAvailableVirtualPort     : No Virtual Port available.
                 securityViolation          : Password/Calling ID security 
                                              failed.
                 noResourcesAvailable       : No resources available.
                 callRejected               : Call failed by Xircom card.
                 invalidPhoneNumber         : Incorrect phone number.
                 outgoingCallRequestTimeout : Outgoing call request timed out.
                 callCollision              : A call collision occurred.
                 virtualPortNotAvailable    : Virtual port not available.
                 invalidConfiguration       : Invalid configuration.
                 na                         : Value not available."
        ::= { cdx6500E1StatISDNStatusEntry 12 }

        cdx6500E1StatTxLastCalledNumber OBJECT-TYPE
            SYNTAX DisplayString (SIZE (0..15))
            ACCESS read-only
            STATUS mandatory
            DESCRIPTION
                "The phone number of the last ISDN call made by a virtual 
                 port from this node."
        ::= { cdx6500E1StatISDNStatusEntry 13 }

        cdx6500E1StatTxLastCallingNumber OBJECT-TYPE
            SYNTAX DisplayString (SIZE (0..15))
            ACCESS read-only
            STATUS mandatory
            DESCRIPTION
                "The phone number of the virtual port that made the last 
                 ISDN call from this node."
        ::= { cdx6500E1StatISDNStatusEntry 14 }

        cdx6500E1StatTxMinCallDuration OBJECT-TYPE
            SYNTAX DisplayString
            ACCESS read-only
            STATUS mandatory
            DESCRIPTION
                "The minimum call duration of all outbound ISDN calls made
                 from this node, since the last statistics reset."
        ::= { cdx6500E1StatISDNStatusEntry 15 }

        cdx6500E1StatTxMaxCallDuration OBJECT-TYPE
            SYNTAX DisplayString
            ACCESS read-only
            STATUS mandatory
            DESCRIPTION
                "The maximum call duration of all outbound ISDN calls made
                 from this node, since the last statistics reset."
        ::= { cdx6500E1StatISDNStatusEntry 16 }

        cdx6500E1StatTxAvgCallDuration OBJECT-TYPE
            SYNTAX DisplayString
            ACCESS read-only
            STATUS mandatory
            DESCRIPTION
                "The average call duration of all outbound ISDN calls made
                 from this node, since the last statistics reset."
        ::= { cdx6500E1StatISDNStatusEntry 17 }

        cdx6500E1StatDchannelState OBJECT-TYPE
            SYNTAX INTEGER {
                    up    (1),
                    down  (2),
                    na    (100)
                    }
            ACCESS read-only
            STATUS mandatory
            DESCRIPTION
               "Specifies the status of the D Channel.
                up   : The D Channel is up.
                down : The D Channel is down.
                na   : Value not available."
        ::= { cdx6500E1StatISDNStatusEntry 18 }

        cdx6500E1StatISDNCallSummaryTable OBJECT-TYPE
            SYNTAX SEQUENCE OF Cdx6500E1StatISDNCallSummaryEntry
            ACCESS not-accessible
            STATUS mandatory
            DESCRIPTION
                "This table holds ISDN call summary information for E1 ports."
        ::= { cdx6500PSTT1E1PortTable 10  }

        cdx6500E1StatISDNCallSummaryEntry OBJECT-TYPE
            SYNTAX Cdx6500E1StatISDNCallSummaryEntry
            ACCESS not-accessible
            STATUS mandatory
            DESCRIPTION
                "An entry in the ISDN call summary table."
            INDEX { cdx6500E1StatISDNPortNumber,
                    cdx6500E1StatISDNBChannelNumber }
        ::= { cdx6500E1StatISDNCallSummaryTable 1 }

        Cdx6500E1StatISDNCallSummaryEntry ::=
            SEQUENCE {
                cdx6500E1StatISDNBChannelNumber
                    INTEGER,
                cdx6500E1StatISDNBChannelStatus
                    INTEGER,
                cdx6500E1StatISDNCallDirection
                    INTEGER,
                cdx6500E1StatISDNCallingNumber
                    DisplayString,
                cdx6500E1StatISDNCalledNumber
                    DisplayString,
                cdx6500E1StatISDNDS0Rate
                    INTEGER,
                cdx6500E1StatISDNVirtualPortNumber
                    INTEGER,
                cdx6500E1StatISDNTimeCallStarted
                    DisplayString,
                cdx6500E1StatISDNPortNumber
                    PhysicalPortNumber
                }

        cdx6500E1StatISDNBChannelNumber OBJECT-TYPE
            SYNTAX INTEGER (1..31)
            ACCESS read-only
            STATUS mandatory
            DESCRIPTION
                "B-Channel number of the ISDN Channel."
        ::= { cdx6500E1StatISDNCallSummaryEntry 1 }

        cdx6500E1StatISDNBChannelStatus OBJECT-TYPE
            SYNTAX INTEGER {
                    idle         (1),
                    ringing      (2),
                    connected    (3),
                    outOfService (4),
                    na           (100)
                    }
            ACCESS read-only
            STATUS mandatory
            DESCRIPTION
               "Status of the ISDN B-Channel.
                The posssible values are:
                idle         : The B-Channel is in the idle state.
                ringing      : The B-Channel is in the ringing state.
                connected    : The B-Channel is in the connected state.
                outOfService : The B-Channel is out of service.
                na           : Value not available."
        ::= { cdx6500E1StatISDNCallSummaryEntry 2 }
     
        cdx6500E1StatISDNCallDirection OBJECT-TYPE
            SYNTAX INTEGER {
                    inbound  (1),
                    outbound (2),
                    invalid  (3),
                    na       (100)
                    }
            ACCESS read-only
            STATUS mandatory
            DESCRIPTION
                "Direction of the ISDN call on the B-Channel.
                 The posssible values are:
                 inbound  : The current call is in the inbound direction.
                 outbound : The current call is in the outbound direction.
                 invalid  : There is no call present.
                 na       : Value not available."
        ::= { cdx6500E1StatISDNCallSummaryEntry 3 }

        cdx6500E1StatISDNCallingNumber OBJECT-TYPE
            SYNTAX DisplayString (SIZE (0..15))
            ACCESS read-only
            STATUS mandatory
            DESCRIPTION
                "This is the phone number of the party originating the 
                 ISDN call."
        ::= { cdx6500E1StatISDNCallSummaryEntry 4 }

        cdx6500E1StatISDNCalledNumber OBJECT-TYPE
            SYNTAX DisplayString (SIZE (0..15))
            ACCESS read-only
            STATUS mandatory
            DESCRIPTION
                "This is the phone number of the party at the destination 
                 end of the ISDN call."
        ::= { cdx6500E1StatISDNCallSummaryEntry 5 }

        cdx6500E1StatISDNDS0Rate OBJECT-TYPE
            SYNTAX INTEGER {
                    ds056k (1),
                    ds064k (2),
                    na     (100)
                    }
            ACCESS read-only
            STATUS mandatory
            DESCRIPTION
               "DS0 Rate of the ISDN B-Channel.
                The posssible values are:
                ds056k : The DS0 Rate is 56K.
                ds064k : The DS0 Rate is 64K.
                na     : Value not available."
        ::= { cdx6500E1StatISDNCallSummaryEntry 6 }

        cdx6500E1StatISDNVirtualPortNumber OBJECT-TYPE
            SYNTAX INTEGER
            ACCESS read-only
            STATUS mandatory
            DESCRIPTION
                "Virtual Port Number of the port using this B-Channel.
                 A value of 0 implies that no virtual port is
                 currently using the B-Channel."
        ::= { cdx6500E1StatISDNCallSummaryEntry 7 }

        cdx6500E1StatISDNTimeCallStarted OBJECT-TYPE
            SYNTAX DisplayString
            ACCESS read-only
            STATUS mandatory
            DESCRIPTION
                "This is the duration that the current call on this 
                 B-Channel has been connected."
        ::= { cdx6500E1StatISDNCallSummaryEntry 8 }

        cdx6500E1StatISDNPortNumber OBJECT-TYPE
            SYNTAX PhysicalPortNumber
            ACCESS read-only
            STATUS mandatory
            DESCRIPTION
                "Port number of the E1 port."
        ::= { cdx6500E1StatISDNCallSummaryEntry 9 }

        -- THE LAST 24 HOUR ERROR STATISTICS TABLE

        cdx6500E1StatLast24HoursReportTable OBJECT-TYPE
            SYNTAX SEQUENCE OF Cdx6500E1StatLast24HoursReportEntry
            ACCESS not-accessible
            STATUS mandatory
            DESCRIPTION
                "This table holds a report of the cumulative sum
                 of the statistics for the previous 24 hour interval."
        ::= { cdx6500PSTT1E1PortTable 12 }
        
        cdx6500E1StatLast24HoursReportEntry OBJECT-TYPE
            SYNTAX Cdx6500E1StatLast24HoursReportEntry
            ACCESS not-accessible
            STATUS mandatory
            DESCRIPTION
                "Each entry contains statistics information for one E1 port."
            INDEX { cdx6500E1StatLast24HoursReportPortNumber }
        ::= { cdx6500E1StatLast24HoursReportTable 1 }

        Cdx6500E1StatLast24HoursReportEntry ::=
            SEQUENCE {
                cdx6500E1StatLast24HoursReportPortNumber
                    PhysicalPortNumber,
                cdx6500E1StatLast24HoursReportLES
                    Gauge,
                cdx6500E1StatLast24HoursReportLCV
                    Gauge,
                cdx6500E1StatLast24HoursReportPCV
                    Gauge,
                cdx6500E1StatLast24HoursReportCSS
                    Gauge,
                cdx6500E1StatLast24HoursReportES
                    Gauge,
                cdx6500E1StatLast24HoursReportBES
                    Gauge,
                cdx6500E1StatLast24HoursReportSES
                    Gauge,
                cdx6500E1StatLast24HoursReportSEFS
                    Gauge,
                cdx6500E1StatLast24HoursReportUAS
                    Gauge
                }

        cdx6500E1StatLast24HoursReportPortNumber OBJECT-TYPE
            SYNTAX PhysicalPortNumber
            ACCESS read-only
            STATUS mandatory
            DESCRIPTION
                "Port number of the E1 port."
        ::= { cdx6500E1StatLast24HoursReportEntry 1 }

        cdx6500E1StatLast24HoursReportLES OBJECT-TYPE
            SYNTAX Gauge
            ACCESS read-only
            STATUS mandatory
            DESCRIPTION
                "The number of Line Errored Seconds (LESs) encountered 
                 by the E1 interface in the previous 24 hour interval. "
        ::= { cdx6500E1StatLast24HoursReportEntry 2 }

        cdx6500E1StatLast24HoursReportLCV OBJECT-TYPE
            SYNTAX Gauge
            ACCESS read-only
            STATUS mandatory
            DESCRIPTION
                "The number of Line Code Violations (LCVs) encountered 
                 by the E1 interface in the previous 24 hour interval."
        ::= { cdx6500E1StatLast24HoursReportEntry 3 }

        cdx6500E1StatLast24HoursReportPCV OBJECT-TYPE
            SYNTAX Gauge
            ACCESS read-only
            STATUS mandatory
            DESCRIPTION
                "The number of Path Coding  Violations (PCVs) encountered 
                 by the E1 interface in the previous 24 hour interval."
        ::= { cdx6500E1StatLast24HoursReportEntry 4 }

        cdx6500E1StatLast24HoursReportCSS OBJECT-TYPE
            SYNTAX Gauge
            ACCESS read-only
            STATUS mandatory
            DESCRIPTION
               "The number of Controlled Slip Seconds (CSSs) encountered 
                by the E1 interface in the previous 24 hour interval."
        ::= { cdx6500E1StatLast24HoursReportEntry 5 }

        cdx6500E1StatLast24HoursReportES OBJECT-TYPE
            SYNTAX Gauge
            ACCESS read-only
            STATUS mandatory
            DESCRIPTION
                "The number of Errored Seconds (ESs) encountered by 
                 the E1 interface in the previous 24 hour interval."
        ::= { cdx6500E1StatLast24HoursReportEntry 6 }

        cdx6500E1StatLast24HoursReportBES OBJECT-TYPE
            SYNTAX Gauge
            ACCESS read-only
            STATUS mandatory
            DESCRIPTION
                "The number of Bursty Errored Seconds (BESs) encountered 
                 by the E1 interface in the previous 24 hour interval."
        ::= { cdx6500E1StatLast24HoursReportEntry 7 }

        cdx6500E1StatLast24HoursReportSES OBJECT-TYPE
            SYNTAX Gauge
            ACCESS read-only
            STATUS mandatory
            DESCRIPTION
                "The number of Severely Errored Seconds (SESs) encountered 
                 by the E1 interface in the previous 24 hour interval."
        ::= { cdx6500E1StatLast24HoursReportEntry 8 }

        cdx6500E1StatLast24HoursReportSEFS OBJECT-TYPE
            SYNTAX Gauge
            ACCESS read-only
            STATUS mandatory
            DESCRIPTION
                "The number of Severely Errored Framing Seconds (SEFSs)
                 encountered by the E1 interface in the previous
                 24 hour interval."
        ::= { cdx6500E1StatLast24HoursReportEntry 9 }

        cdx6500E1StatLast24HoursReportUAS OBJECT-TYPE
            SYNTAX Gauge
            ACCESS read-only
            STATUS mandatory
            DESCRIPTION
                "The number of Unavailable Seconds (UASs) encountered 
                 by the E1 interface in the previous 24 hour interval."
        ::= { cdx6500E1StatLast24HoursReportEntry 10 }

        -- THE CURRENT 15 MINUTE INTERVAL ERROR STATISTICS TABLE

        cdx6500E1StatCurrent15MinutesReportTable OBJECT-TYPE
            SYNTAX SEQUENCE OF Cdx6500E1StatCurrent15MinutesReportEntry
            ACCESS not-accessible
            STATUS mandatory
            DESCRIPTION
                "This table holds a report of the statistics for the 
                 current 15 minutes interval."
        ::= { cdx6500PSTT1E1PortTable 14 }
        
        cdx6500E1StatCurrent15MinutesReportEntry OBJECT-TYPE
            SYNTAX Cdx6500E1StatCurrent15MinutesReportEntry
            ACCESS not-accessible
            STATUS mandatory
            DESCRIPTION
                "Each entry contains statistics information for one E1 port."
            INDEX { cdx6500E1StatCurrent15MinutesReportPortNumber }
        ::= { cdx6500E1StatCurrent15MinutesReportTable 1 }

        Cdx6500E1StatCurrent15MinutesReportEntry ::=
            SEQUENCE {
                cdx6500E1StatCurrent15MinutesReportPortNumber
                    PhysicalPortNumber,
                cdx6500E1StatCurrent15MinutesReportTimeElapsed
                    DisplayString,
                cdx6500E1StatCurrent15MinutesReportLES
                    Gauge,
                cdx6500E1StatCurrent15MinutesReportLCV
                    Gauge,
                cdx6500E1StatCurrent15MinutesReportPCV
                    Gauge,
                cdx6500E1StatCurrent15MinutesReportCSS
                    Gauge,
                cdx6500E1StatCurrent15MinutesReportES
                    Gauge,
                cdx6500E1StatCurrent15MinutesReportBES
                    Gauge,
                cdx6500E1StatCurrent15MinutesReportSES
                    Gauge,
                cdx6500E1StatCurrent15MinutesReportSEFS
                    Gauge,
                cdx6500E1StatCurrent15MinutesReportUAS
                    Gauge
                }                                               
         
        cdx6500E1StatCurrent15MinutesReportPortNumber OBJECT-TYPE
            SYNTAX PhysicalPortNumber
            ACCESS read-only
            STATUS mandatory
            DESCRIPTION
                "Port number of the E1 port."
        ::= { cdx6500E1StatCurrent15MinutesReportEntry 1 }

        cdx6500E1StatCurrent15MinutesReportTimeElapsed OBJECT-TYPE
            SYNTAX DisplayString
            ACCESS read-only
            STATUS mandatory
            DESCRIPTION
                "The time that has elapsed since the beginning 
                 of the current 15 minutes interval."
        ::= { cdx6500E1StatCurrent15MinutesReportEntry 2 }
                    
        cdx6500E1StatCurrent15MinutesReportLES OBJECT-TYPE
            SYNTAX Gauge
            ACCESS read-only
            STATUS mandatory
            DESCRIPTION
                "The number of Line Errored Seconds (LESs) encountered 
                 by the E1 interface in the current 15 minute interval."
        ::= { cdx6500E1StatCurrent15MinutesReportEntry 3 }

        cdx6500E1StatCurrent15MinutesReportLCV OBJECT-TYPE
            SYNTAX Gauge
            ACCESS read-only
            STATUS mandatory
            DESCRIPTION
                "The number of Line Code Violations (LCVs) encountered 
                 by the E1 interface in the current 15 minute interval."
        ::= { cdx6500E1StatCurrent15MinutesReportEntry 4 }

        cdx6500E1StatCurrent15MinutesReportPCV OBJECT-TYPE
            SYNTAX Gauge
            ACCESS read-only
            STATUS mandatory
            DESCRIPTION
                "The number of Path Coding  Violations (PCVs) encountered 
                 by the E1 interface in the current 15 minute interval."
        ::= { cdx6500E1StatCurrent15MinutesReportEntry 5 }

        cdx6500E1StatCurrent15MinutesReportCSS OBJECT-TYPE
            SYNTAX Gauge
            ACCESS read-only
            STATUS mandatory
            DESCRIPTION
                "The number of Controlled Slip Seconds (CSSs) encountered 
                 by the E1 interface in the current 15 minute interval."
        ::= { cdx6500E1StatCurrent15MinutesReportEntry 6 }

        cdx6500E1StatCurrent15MinutesReportES OBJECT-TYPE
            SYNTAX Gauge
            ACCESS read-only
            STATUS mandatory
            DESCRIPTION
                "The number of Errored Seconds (ESs) encountered by the 
                 E1 interface in the current 15 minute interval."
        ::= { cdx6500E1StatCurrent15MinutesReportEntry 7 }

        cdx6500E1StatCurrent15MinutesReportBES OBJECT-TYPE
            SYNTAX Gauge
            ACCESS read-only
            STATUS mandatory
            DESCRIPTION
                "The number of Bursty Errored Seconds (BESs) encountered 
                 by the E1 interface in the current 15 minute interval."
        ::= { cdx6500E1StatCurrent15MinutesReportEntry 8 }

        cdx6500E1StatCurrent15MinutesReportSES OBJECT-TYPE
            SYNTAX Gauge
            ACCESS read-only
            STATUS mandatory
            DESCRIPTION
                "The number of Severely Errored Seconds (SESs) encountered 
                 by the E1 interface in the current 15 minute interval."
        ::= { cdx6500E1StatCurrent15MinutesReportEntry 9 }

        cdx6500E1StatCurrent15MinutesReportSEFS OBJECT-TYPE
            SYNTAX Gauge
            ACCESS read-only
            STATUS mandatory
            DESCRIPTION
                "The number of Severely Errored Framing Seconds (SEFSs)
                 encountered by the E1 interface in the current
                 15 minute interval."
        ::= { cdx6500E1StatCurrent15MinutesReportEntry 10 }

        cdx6500E1StatCurrent15MinutesReportUAS OBJECT-TYPE
            SYNTAX Gauge
            ACCESS read-only
            STATUS mandatory
            DESCRIPTION
                "The number of Unavailable Seconds (UASs) encountered 
                 by the E1 interface in the current 15 minute interval."
        ::= { cdx6500E1StatCurrent15MinutesReportEntry 11 }

        END
