-- Version 1.4, modified 02/12/98

        NS-OPT-MIB DEFINITIONS ::= BEGIN

        IMPORTS
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

          cdx6500Statistics OBJECT IDENTIFIER ::= { cdx6500 3 }
 cdx6500StatOtherStatsGroup OBJECT IDENTIFIER ::= { cdx6500Statistics 2 }

            cdx6500Controls OBJECT IDENTIFIER ::= { cdx6500 4 }

        -- Textual Conventions

        DisplayString ::= OCTET STRING
        -- This data type is used to model textual information taken
        -- from the NVT ASCII character set.  By convention, objects
        -- with this syntax are declared as having SIZE (0..255)
        
        -- Config Objects for Network Services

        cdx6500NetServCfgTable OBJECT-TYPE
            SYNTAX SEQUENCE OF Cdx6500NetServCfgTableEntry
            ACCESS not-accessible
            STATUS mandatory
            DESCRIPTION
                "This table contains all the configuration objects 
                 for the Network Service Features."
        ::= { cdx6500CfgGeneralGroup 20 }

        cdx6500NetServCfgTableEntry OBJECT-TYPE
            SYNTAX Cdx6500NetServCfgTableEntry
            ACCESS not-accessible
            STATUS mandatory
            DESCRIPTION
                "Parameters in the Network Services Configuration Table."
            INDEX  { cdx6500NetServCfgEntryNumber }
        ::= { cdx6500NetServCfgTable 1 }

        Cdx6500NetServCfgTableEntry ::=
            SEQUENCE {
                cdx6500NetServCfgEntryNumber
                    INTEGER,
                cdx6500NetServCfgPortAndStnId
                    DisplayString,
                cdx6500NetServCfgFeaturesLevel
                    INTEGER
                }

        cdx6500NetServCfgEntryNumber OBJECT-TYPE
            SYNTAX INTEGER (1..128)
            ACCESS read-only
            STATUS mandatory
            DESCRIPTION
                "This is not a configurable parameter. 
                 This identifies the Network Services Configuration Table 
                 entry being configured by the other parameters in the record."
        ::= { cdx6500NetServCfgTableEntry 1 }

        cdx6500NetServCfgPortAndStnId OBJECT-TYPE
            SYNTAX DisplayString (SIZE(0..31))
            ACCESS read-only
            STATUS mandatory
            DESCRIPTION
                "This parameter identifies the port and station that 
                 the Network Services Data Compression feature will 
                 be enabled on. The wild card (match anything) character 
                 is * and can also be part of the entry. 
                 The following are the only valid port types:
                 X25-     (Examples: X25-1(16) or X25-1*)
                 FRA-     (Examples: FRA-3S1 or FRA-3*)
                 LCON-    (Examples: LCON-1 or LCON-*)
                 TCOP-    (Examples: TCOP-1 or TCOP-*)
                 TBOP-    (Examples: TBOP-1 or TBOP-*).
                 NOTE: The hyphen is required and there should be no 
                 leading spaces. The range is 0-31 alphanumeric characters,
                 the default value is blank."
        ::= { cdx6500NetServCfgTableEntry 2 }

        cdx6500NetServCfgFeaturesLevel OBJECT-TYPE
            SYNTAX INTEGER {
                    disable   (1),
                    negotiate (2),
                    required  (3),
                    forceOn  (4)
                    }
            ACCESS read-only
            STATUS mandatory
            DESCRIPTION
                "This parameter specifies the Network Services features level.
                 disable   - The feature is not requested.
                 negotiate - Negotiate for the feature. The feature is
                             desired, but if not available bring up the
                             virtual circuit anyway, without the feature.
                 required  - Required for call. Bring up the connection only
                             if the feature is available on both ends.
                 forceOn   - The feature is required for the circuit to 
                             come up."
        ::= { cdx6500NetServCfgTableEntry 3 }

        -- Statistics objects 

        cdx6500NetServStatTable OBJECT-TYPE
            SYNTAX SEQUENCE OF Cdx6500NetServStatTableEntry
            ACCESS not-accessible
            STATUS mandatory
            DESCRIPTION
                "The Network Services NS Channel Statistics Table."
        ::= { cdx6500StatOtherStatsGroup 11 } 

        cdx6500NetServStatTableEntry OBJECT-TYPE
            SYNTAX Cdx6500NetServStatTableEntry
            ACCESS not-accessible
            STATUS mandatory
            DESCRIPTION
                "Each entry in this table pertains to the Network 
                 Services (NS) Channel Statistics."
        ::= { cdx6500NetServStatTable 1 }

        Cdx6500NetServStatTableEntry ::=
            SEQUENCE {
                cdx6500NetServStatUsedChannels
                    INTEGER,
                cdx6500NetServStatMaxChannels
                    INTEGER,
                cdx6500NetServStatUnavailChannels
                    INTEGER
                }

        cdx6500NetServStatUsedChannels OBJECT-TYPE
            SYNTAX INTEGER
            ACCESS read-only
            STATUS mandatory
            DESCRIPTION
                 "The number of NS Channels in use."
        ::= { cdx6500NetServStatTableEntry 1 }

        cdx6500NetServStatMaxChannels OBJECT-TYPE
            SYNTAX INTEGER
            ACCESS read-only
            STATUS mandatory
            DESCRIPTION
                "The maximum number of NS Channels used."
        ::= { cdx6500NetServStatTableEntry 2 }

        cdx6500NetServStatUnavailChannels OBJECT-TYPE
            SYNTAX INTEGER
            ACCESS read-only
            STATUS mandatory
            DESCRIPTION
                "The number of NS Channels not available for allocation."
        ::= { cdx6500NetServStatTableEntry 3 }

        END
