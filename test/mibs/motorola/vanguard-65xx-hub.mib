-- Version 1.3, modified 02/12/98

        HUB-OPT-MIB DEFINITIONS ::= BEGIN

        IMPORTS
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Conventions

        DisplayString ::= OCTET STRING

        -- The HUB Port group contains the configuration parameters,
        -- statistics, and control objects used by the HUB
        -- ports.

        -- HUB Port Configuration Table

        cdx6500PPCTHUBPortTable OBJECT-TYPE
            SYNTAX SEQUENCE OF Cdx6500PPCTHUBPortEntry
            ACCESS not-accessible
            STATUS mandatory
            DESCRIPTION
                "A table of HUB Port configuration parameters."
        ::= { cdx6500PCTPortProtocolGroup 22 }

        cdx6500PPCTHUBPortEntry OBJECT-TYPE
            SYNTAX Cdx6500PPCTHUBPortEntry
            ACCESS not-accessible
            STATUS mandatory
            DESCRIPTION
                "A HUB Configuration Table entry. Each entry
                 contains the configuration parameters for a single
                 HUB port. "
            INDEX { cdx6500HUBCfgPortNumber }
        ::= { cdx6500PPCTHUBPortTable 1 }

        Cdx6500PPCTHUBPortEntry ::=
            SEQUENCE {
                cdx6500HUBCfgPortNumber 
                    INTEGER,    
                cdx6500HUBCfgPortLevel 
                    INTEGER
                }

        cdx6500HUBCfgPortNumber OBJECT-TYPE
            SYNTAX INTEGER (13..54)
            ACCESS read-only
            STATUS mandatory
            DESCRIPTION
                "The HUB port number described by this entry"
        ::= { cdx6500PPCTHUBPortEntry 1 }


        cdx6500HUBCfgPortLevel OBJECT-TYPE
            SYNTAX INTEGER {
                    normal  (1),
                    reduced (2)
                    }
            ACCESS read-only
            STATUS mandatory
            DESCRIPTION  
                "This is the level in which the port will run.
                 Select level on this HUB port as follows:
                 normal  - port operating at normal received squelch level.
                 reduced - port operating at reduced receive squelch level."
        ::= { cdx6500PPCTHUBPortEntry 2 }

        -- HUB Port Statistics

        cdx6500PPSTHUBPortStatTable  OBJECT-TYPE
            SYNTAX SEQUENCE OF Cdx6500HUBPortStatEntry
            ACCESS not-accessible
            STATUS mandatory
            DESCRIPTION
                "A table of HUB port statistics."
        ::= { cdx6500PSTPortProtocolGroup 23 }

        cdx6500HUBPortStatEntry OBJECT-TYPE
            SYNTAX Cdx6500HUBPortStatEntry
            ACCESS not-accessible
            STATUS mandatory
            DESCRIPTION
                "A HUB Port Statistic Table entry. Each entry
                 contains the statistics for a single HUB port."
            INDEX { cdx6500HUBStatPortNumber }
        ::= { cdx6500PPSTHUBPortStatTable 1 }

        Cdx6500HUBPortStatEntry ::=
            SEQUENCE {
                cdx6500HUBStatPortNumber
                    INTEGER,
                cdx6500HUBPortStatus
                    INTEGER,
                cdx6500HUBPortState
                    INTEGER,
                cdx6500HUBPortLevel
                    INTEGER,
                cdx6500HUBPortPolarity
                    INTEGER
                }

        cdx6500HUBStatPortNumber OBJECT-TYPE
            SYNTAX INTEGER (13..54)
            ACCESS read-only
            STATUS mandatory
            DESCRIPTION
                "The HUB port number described by this entry." 
        ::= { cdx6500HUBPortStatEntry 1 }

        cdx6500HUBPortStatus OBJECT-TYPE
            SYNTAX INTEGER {
                    up   (1),
                    down (2)
                    }
            ACCESS read-only
            STATUS mandatory
            DESCRIPTION
                "Port Status indicates whether or not the port
                 is switched on and is ready for operation. This value
                 may be one of :
                 up   - Port is up and running.
                 down - port is down."
        ::= { cdx6500HUBPortStatEntry 2 }

        cdx6500HUBPortState OBJECT-TYPE
            SYNTAX INTEGER {
                    enabled  (1),
                    disabled (2)
                    }
            ACCESS read-only
            STATUS mandatory
            DESCRIPTION
                "Port State indicates whether or not the port
                 is disabled. This value may be one of :
                 enable  - Port is enabled.
                 disable - port is disabled."
        ::= { cdx6500HUBPortStatEntry 3 }

        cdx6500HUBPortLevel OBJECT-TYPE
            SYNTAX INTEGER {
                    normal  (1),
                    reduced (2)
                    }
            ACCESS read-only
            STATUS mandatory
            DESCRIPTION
                "This is the level the port will be running.
                 normal - port operating at normal received squelch level.
                 reduced - port operating at reduced receive squelch level."
        ::= { cdx6500HUBPortStatEntry 4 }

        cdx6500HUBPortPolarity OBJECT-TYPE
            SYNTAX INTEGER {
                    nonInverted (1),
                    inverted    (2)
                    }
            ACCESS read-only
            STATUS mandatory
            DESCRIPTION
                "Port polarity :
                 nonInverted - port polarity in not inverted.
                 inverted    - port polarity is inverted."
        ::= { cdx6500HUBPortStatEntry 5 }

        END
