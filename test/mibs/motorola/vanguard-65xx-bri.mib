-- Version 1.4, modified 02/12/98
         
        BRI-OPT-MIB DEFINITIONS ::= BEGIN
         
        IMPORTS
            Counter, Gauge
                FROM RFC1155-SMI

            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

        -- This MIB is Branch Node (BN) specific.
         
        -- Textual conventions
        DisplayString ::= OCTET STRING

        cdx6500PPCTISDN OBJECT IDENTIFIER ::=
            { cdx6500PCTPortProtocolGroup 26 }
         
        cdx6500PPCTBRIConfig OBJECT IDENTIFIER ::= { cdx6500PPCTISDN 1 }

        cdx6500PPCTBRIPortTable OBJECT-TYPE
            SYNTAX SEQUENCE OF Cdx6500PPCTBRIPortEntry
            ACCESS not-accessible
            STATUS mandatory
            DESCRIPTION
                "This table contains BRI Port configuration parameters"
        ::= { cdx6500PPCTBRIConfig 1 }
         
        cdx6500PPCTBRIPortEntry OBJECT-TYPE
            SYNTAX Cdx6500PPCTBRIPortEntry
            ACCESS not-accessible
            STATUS mandatory
            DESCRIPTION
                "Each PortEntry contains the configuration
                 parameters for one BRI ISDN port."
            INDEX { cdx6500BRICfgPortNumber }
        ::= { cdx6500PPCTBRIPortTable 1 }
         
        Cdx6500PPCTBRIPortEntry  ::=
            SEQUENCE {
                cdx6500BRICfgPortNumber
                    INTEGER,
                cdx6500BRICfgPortType
                    INTEGER,
                cdx6500BRICfgSwitchType
                    DisplayString,
                cdx6500BRICfgVmebug
                    INTEGER,
                cdx6500BRICfgTEI
                    INTEGER
                }
         
        cdx6500BRICfgPortNumber OBJECT-TYPE
            SYNTAX INTEGER
            ACCESS read-only
            STATUS mandatory
            DESCRIPTION
                "Port number of the port."
        ::= { cdx6500PPCTBRIPortEntry 1 }
         
        cdx6500BRICfgPortType OBJECT-TYPE
            SYNTAX INTEGER {
                    bri  (40)
                    }
            ACCESS read-only
            STATUS mandatory
            DESCRIPTION
                "The Port Type of the port."
        ::= { cdx6500PPCTBRIPortEntry 2 }
         
        cdx6500BRICfgSwitchType OBJECT-TYPE
            SYNTAX DisplayString (SIZE (0..24))
            ACCESS read-only
            STATUS mandatory
            DESCRIPTION
                "Specifies switch type for the central office.
                 VN4    - French VN4 standard
                 1TR6   - German switch standard
                 BTNR   - UK Standard
                 ETSI   - Euro-ISDN
                 5ESS   - AT&T switch
                 NI-1   - National ISDN version 1."
        ::= { cdx6500PPCTBRIPortEntry 3 }
         
        cdx6500BRICfgVmebug OBJECT-TYPE
            SYNTAX INTEGER {
                    disabled (1),
                    enabled  (2)
                    }
            ACCESS read-only
            STATUS mandatory
            DESCRIPTION
                "Engineering use only.
                 Enable/disable the running of the OST VMEBUG debugger.
                 NOTE:  For this to work the flash must be loaded with
                 the dbg_vmebug file.  If the the dbg_vmebug file is not
                 in flash this parameter will have no effect."
        ::= { cdx6500PPCTBRIPortEntry 4 }
         
        cdx6500BRICfgTEI  OBJECT-TYPE
            SYNTAX INTEGER
            ACCESS read-only
            STATUS mandatory
            DESCRIPTION
                "The range is 0..63,127. The range 0..63  indicate a static
                 TEI provided by the Network subscribing.
                 127: TEI negotiated."
        ::= { cdx6500PPCTBRIPortEntry 5 }
         
        cdx6500PPCTBRIChan OBJECT IDENTIFIER ::= { cdx6500PPCTBRIConfig 2 }
         
        cdx6500PPCTBRIX25ChanTable OBJECT-TYPE
            SYNTAX SEQUENCE OF Cdx6500PPCTBRIX25ChanEntry
            ACCESS not-accessible
            STATUS mandatory
            DESCRIPTION
                "This table contains BRI Channel configuration parameters."
        ::= { cdx6500PPCTBRIChan 1 }
         
        cdx6500PPCTBRIX25ChanEntry OBJECT-TYPE
            SYNTAX Cdx6500PPCTBRIX25ChanEntry
            ACCESS not-accessible
            STATUS mandatory
            DESCRIPTION
                "Each ChanEntry contains the configuration
                 parameters for one BRI ISDN channel."
            INDEX { cdx6500BRIX25ChanCfgPortNumber,
                    cdx6500BRIX25ChanCfgChannelNum }
        ::= { cdx6500PPCTBRIX25ChanTable 1 }
         
        Cdx6500PPCTBRIX25ChanEntry ::=
            SEQUENCE {
                cdx6500BRIX25ChanCfgPortNumber
                    INTEGER,
                cdx6500BRIX25ChanCfgChannelNum
                    INTEGER,
                cdx6500BRIX25ChanCfgChannelType
                    INTEGER,
                cdx6500BRIX25ChanCfgAccessType
                    INTEGER,
                cdx6500BRIX25ChanCfgTimeslot
                    INTEGER,
                cdx6500BRIX25ChanCfgSPID
                    DisplayString,
                cdx6500BRIX25ChanCfgISDNCallAcc
                    INTEGER,
                cdx6500BRIX25ChanCfgLocalSubsAddr
                    DisplayString,
                cdx6500BRIX25ChanCfgLocalSubsSubAddr
                    DisplayString,
                cdx6500BRIX25ChanCfgRateAdaption
                    INTEGER,
                cdx6500BRIX25ChanCfgProtocolType
                    INTEGER,
                cdx6500BRIX25ChanCfgLinkAddr
                    INTEGER,
                cdx6500BRIX25ChanCfgNumPVCChannels
                    INTEGER,
                cdx6500BRIX25ChanCfgStartPVCChanNum
                    INTEGER,
                cdx6500BRIX25ChanCfgBNumSVCChannels
                    INTEGER,
                cdx6500BRIX25ChanCfgStartSVCChanNum
                    INTEGER,
                cdx6500BRIX25ChanCfgInitialFrame
                    INTEGER,
                cdx6500BRIX25ChanCfgT1TransRetryTimer
                    INTEGER,
                cdx6500BRIX25ChanCfgT4PollTimer
                    INTEGER,
                cdx6500BRIX25ChanCfgBN2TransTries
                    INTEGER,
                cdx6500BRIX25ChanCfgFrameSeqCount
                    INTEGER,
                cdx6500BRIX25ChanCfgBKFrameWindow
                    INTEGER,
                cdx6500BRIX25ChanCfgPktSeqCount
                    INTEGER,
                cdx6500BRIX25ChanCfgBWPktWindow
                    INTEGER,
                cdx6500BRIX25ChanCfgBPPktSize
                    INTEGER,
                cdx6500BRIX25ChanCfgMaxNegoPktSize
                    INTEGER,
                cdx6500BRIX25ChanCfgDataQUpperThres
                    INTEGER,
                cdx6500BRIX25ChanCfgDataQLowerThres
                    INTEGER,
                cdx6500BRIX25ChanCfgRestartTimer
                    INTEGER,
                cdx6500BRIX25ChanCfgResetTimer
                    INTEGER,
                cdx6500BRIX25ChanCfgCallTimer
                    INTEGER,
                cdx6500BRIX25ChanCfgClearTimer
                    INTEGER,
                cdx6500BRIX25ChanCfgFacToDelFromOutbCalls
                    DisplayString,
                cdx6500BRIX25ChanCfgFacToAddToOutbCalls
                    DisplayString,
                cdx6500BRIX25ChanCfgFacToBarInOutbCalls
                    DisplayString,
                cdx6500BRIX25ChanCfgFacToBarInInbCalls
                    DisplayString,
                cdx6500BRIX25ChanCfgX25Options
                    DisplayString,
                cdx6500BRIX25ChanCfgNumRoutDgtInCallUsrData
                    INTEGER,
                cdx6500BRIX25ChanCfgNumPreAddrDgstrpOutgCalls
                    INTEGER,
                cdx6500BRIX25ChanCfgInDigitsToStrip
                    INTEGER,
                cdx6500BRIX25ChanCfgRestrictedConnDest
                    DisplayString,
                cdx6500BRIX25ChanCfgPortAddress
                    DisplayString,
                cdx6500BRIX25ChanCfgCUGMembership
                    DisplayString,
                cdx6500BRIX25ChanCfgBillingRecords
                    INTEGER,
                cdx6500BRIX25ChanCfgSubAddrSize
                    INTEGER,
                cdx6500BRIX25ChanCfgCallSecurity
                    INTEGER,
                cdx6500BRIX25ChanCfgProtectionLevel
                    INTEGER,
                cdx6500BRIX25ChanCfgReconnTimeout
                    INTEGER,
                cdx6500BRIX25ChanCfgReconnTriesLt
                    INTEGER,
                cdx6500BRIX25ChanCfgFacSubsCtl
                    DisplayString,
                cdx6500BRIX25ChanCfgAlarmPriority
                    INTEGER,
                cdx6500BRIX25ChanCfgChanTEI
                    INTEGER,
                cdx6500BRIX25ChanCfgX25NetworkType
                    INTEGER,
                cdx6500BRIX25ChanCfgDNumSVCChannels
                    INTEGER,
                cdx6500BRIX25ChanCfgDWPktWindow
                    INTEGER,
                cdx6500BRIX25ChanCfgDPPktSize
                    INTEGER,
                cdx6500BRIX25ChanCfgDKFrameWindow
                    INTEGER,
                cdx6500BRIX25ChanCfgDN2TransTries
                    INTEGER,
                cdx6500BRIX25ChanCfgT1Timer
                    INTEGER,
                cdx6500BRIX25ChanCfgT2Timer
                    INTEGER,
                cdx6500BRIX25ChanCfgLinkType
                    INTEGER,
                cdx6500BRIX25ChanCfgAddrTrans
                    DisplayString
                }
         
        cdx6500BRIX25ChanCfgPortNumber OBJECT-TYPE
            SYNTAX INTEGER
            ACCESS read-only
            STATUS mandatory
            DESCRIPTION
                "The BRI port number."
        ::= { cdx6500PPCTBRIX25ChanEntry 1 }
         
        cdx6500BRIX25ChanCfgChannelNum OBJECT-TYPE
            SYNTAX INTEGER (1..3)
            ACCESS read-only
            STATUS mandatory
            DESCRIPTION
                "Configured ISDN Channel Number."
        ::= { cdx6500PPCTBRIX25ChanEntry 2 }
         
        cdx6500BRIX25ChanCfgChannelType OBJECT-TYPE
            SYNTAX INTEGER {
                    bChannel (3),
                    dChannel (4)
                    }
            ACCESS read-only
            STATUS mandatory
            DESCRIPTION
                "ISDN channel type.
                 bChannel - a full duplex, 56 or 64 Kbps
                            channel.
                 dChannel - a full duplex, 16 Kbps channel
                            configured only for packet mode."
        ::= { cdx6500PPCTBRIX25ChanEntry 3 }
         
        cdx6500BRIX25ChanCfgAccessType OBJECT-TYPE
            SYNTAX INTEGER {
                    permanent (1),
                    switched  (2)
                    }
            ACCESS read-only
            STATUS mandatory
            DESCRIPTION
                "permanent : Permanent BRI channels
                 switched  : Switched BRI channels."
        ::= { cdx6500PPCTBRIX25ChanEntry 4 }
        
        cdx6500BRIX25ChanCfgTimeslot OBJECT-TYPE
            SYNTAX INTEGER 
            ACCESS read-only
            STATUS mandatory
            DESCRIPTION
                "Physical channel number for permanent switch
                 type only."
        ::= { cdx6500PPCTBRIX25ChanEntry 5 }
         
        cdx6500BRIX25ChanCfgSPID OBJECT-TYPE
            SYNTAX DisplayString (SIZE(0..21))
            ACCESS read-only
            STATUS mandatory
            DESCRIPTION
                "Service Profile Identifiers (SPID) is to
                 define the services subscribed to by the
                 ISDN device that is accessing the ISDN
                 provider. This value is provided by your
                 service provider."
        ::= { cdx6500PPCTBRIX25ChanEntry 6 }
         
        cdx6500BRIX25ChanCfgISDNCallAcc OBJECT-TYPE
            SYNTAX INTEGER {
                    allCalls          (2),
                    addressOnly       (3),
                    addressSubaddress (5)
                   }
            ACCESS read-only
            STATUS mandatory
            DESCRIPTION
                "Specifies the ISDN routing for a setup
                 message coming from the network.
                 allCalls          :  ISDN routing for all setup message coming from the network.
                 addressOnly       :  ISDN routing for specified address only.
                 addressSubaddress :  ISDN routing for specified subaddress only. "
        ::= { cdx6500PPCTBRIX25ChanEntry 7 }
         
        cdx6500BRIX25ChanCfgLocalSubsAddr OBJECT-TYPE
            SYNTAX DisplayString (SIZE (0..36))
            ACCESS read-only
            STATUS mandatory
            DESCRIPTION
                "Specifies the local subscriber address
                 which is provided by the service provider."
        ::= { cdx6500PPCTBRIX25ChanEntry 8 }
         
        cdx6500BRIX25ChanCfgLocalSubsSubAddr OBJECT-TYPE
            SYNTAX DisplayString (SIZE (0..20))
            ACCESS read-only
            STATUS mandatory
            DESCRIPTION
                "Specifies the local subscriber subaddress
                 which is provided by the service provider."
        ::= { cdx6500PPCTBRIX25ChanEntry 9 }
         
        cdx6500BRIX25ChanCfgRateAdaption OBJECT-TYPE
            SYNTAX INTEGER {
                    rate56k (1),
                    rate64k (2)
                    }
            ACCESS read-only
            STATUS mandatory
            DESCRIPTION
                "Rate adaption parameter for this channel.
                 rate56k   :   Rate  of 56 K 
                 rate64k   :   Rate  of 64 K. " 
        ::= { cdx6500PPCTBRIX25ChanEntry 10 }
         
        cdx6500BRIX25ChanCfgProtocolType OBJECT-TYPE
            SYNTAX INTEGER {
                    x25 (2),
                    fri (3)
                    }
            ACCESS read-only
            STATUS mandatory
            DESCRIPTION
                "Specifies the protocol type run over ISDN B channel."
        ::= { cdx6500PPCTBRIX25ChanEntry 11 }
         
        cdx6500BRIX25ChanCfgLinkAddr OBJECT-TYPE
            SYNTAX INTEGER {
                    dte (1),
                    dce (2)
                    }
            ACCESS read-only
            STATUS mandatory
            DESCRIPTION
                "The logical link address must be set to complementary values
                 in devices at each end of the link:
                 dte - link to have logical DTE address (A)
                 dce - link to have logical DCE address (B)"
        ::= { cdx6500PPCTBRIX25ChanEntry 12 }
         
        cdx6500BRIX25ChanCfgNumPVCChannels OBJECT-TYPE
            SYNTAX INTEGER (0..128)
            ACCESS read-only
            STATUS mandatory
            DESCRIPTION
                "Number of logical channels used for Permanent Virtual 
                 Circuits. The total number of PVC and SVC channels on a 
                 link should be kept as small as possible and consistent 
                 with needs.
                 PVC connections must be configured in the PVC Table."
        ::= { cdx6500PPCTBRIX25ChanEntry 13 }
         
        cdx6500BRIX25ChanCfgStartPVCChanNum OBJECT-TYPE
            SYNTAX INTEGER (1..4095)
            ACCESS read-only
            STATUS mandatory
            DESCRIPTION
                "This is the starting logical channel number for the 
                 Permanent Virtual Circuits on this link. Not used if 
                 the number of PVCs = 0."
        ::= { cdx6500PPCTBRIX25ChanEntry 14 }
         
        cdx6500BRIX25ChanCfgBNumSVCChannels OBJECT-TYPE
            SYNTAX INTEGER (0..512)
            ACCESS read-only
            STATUS mandatory
            DESCRIPTION
                "Number of logical channels used in Switched Virtual Circuits.
                 The total number of PVC and SVC channels on a link should be
                 kept as small as possible and consistent with needs.
                 This is a B-channel object. "
        ::= { cdx6500PPCTBRIX25ChanEntry 15 }
         
        cdx6500BRIX25ChanCfgStartSVCChanNum OBJECT-TYPE
            SYNTAX INTEGER (0..4095)
            ACCESS read-only
            STATUS mandatory
            DESCRIPTION
                "This is the starting logical channel number for the 
                 Switched Virtual Circuits on this link. Not used if 
                 the number of SVCs = 0."
        ::= { cdx6500PPCTBRIX25ChanEntry 16 }
         
        cdx6500BRIX25ChanCfgInitialFrame OBJECT-TYPE
            SYNTAX INTEGER {
                    sabm (1),
                    disc (2),
                    none (3)
                    }
            ACCESS read-only
            STATUS mandatory
            DESCRIPTION
                "Specify the initial frame required by other end for link 
                 startup:
                 none - do nothing (other end initiates link-up)
                 sabm - send SABM
                 disc - send DISC, then SABM"
        ::= { cdx6500PPCTBRIX25ChanEntry 17 }
         
        cdx6500BRIX25ChanCfgT1TransRetryTimer OBJECT-TYPE
            SYNTAX INTEGER (1..254)
            ACCESS read-only
            STATUS mandatory
            DESCRIPTION
                "T1 link retry timer value in tenths of a second 
                 (e.g. 30 = 3.0 seconds)."
        ::= { cdx6500PPCTBRIX25ChanEntry 18 }
         
        cdx6500BRIX25ChanCfgT4PollTimer OBJECT-TYPE
            SYNTAX INTEGER
            ACCESS read-only
            STATUS mandatory
            DESCRIPTION
                "This sets the time an idle link is probed for assurance 
                 of connection to the remote device.
                 0 - disable the timer
                 X - X is in tenths of a second (e.g. 40 = 4.0 seconds)
                     and must be set greater than T1."
        ::= { cdx6500PPCTBRIX25ChanEntry 19 }
         
        cdx6500BRIX25ChanCfgBN2TransTries OBJECT-TYPE
            SYNTAX INTEGER (1..20)
            ACCESS read-only
            STATUS mandatory
            DESCRIPTION
                "The maximum number of attempts allowed to complete a 
                 transmission. This is a B channel object"
        ::= { cdx6500PPCTBRIX25ChanEntry 20 }
         
        cdx6500BRIX25ChanCfgFrameSeqCount OBJECT-TYPE
            SYNTAX INTEGER {
                    norm (1),
                    ext  (2)
                    }
            ACCESS read-only
            STATUS mandatory
            DESCRIPTION
                "Port uses normal or extended frame sequence numbering:
                 norm - normal sequencing  (modulo 8)
                 ext  - extended sequencing (modulo 128)"
        ::= { cdx6500PPCTBRIX25ChanEntry 21 }
         
        cdx6500BRIX25ChanCfgBKFrameWindow OBJECT-TYPE
            SYNTAX INTEGER (1..15)
            ACCESS read-only
            STATUS mandatory
            DESCRIPTION
                "Frame level window size must be set to the same value in
                 devices at each end of the link. This is a B-channel object."
        ::= { cdx6500PPCTBRIX25ChanEntry 22 }
         
        cdx6500BRIX25ChanCfgPktSeqCount OBJECT-TYPE
            SYNTAX INTEGER {
                    norm (1),
                    ext  (2)
                    }
            ACCESS read-only
            STATUS mandatory
            DESCRIPTION
                "Port uses normal or extended packet level sequence numbers
                 norm - normal sequencing (Modulo 8)
                 ext  - extended sequencing (Modulo 128)
                 The value must be the same in devices at each end of the link."
        ::= { cdx6500PPCTBRIX25ChanEntry 23 }
         
        cdx6500BRIX25ChanCfgBWPktWindow OBJECT-TYPE
            SYNTAX INTEGER (1..15)
            ACCESS read-only
            STATUS mandatory
            DESCRIPTION
                "Packet level window size must be set to the same value in
                 devices at each end of the link. This is a B-channel object."
        ::= { cdx6500PPCTBRIX25ChanEntry 24 }
         
        cdx6500BRIX25ChanCfgBPPktSize  OBJECT-TYPE
            SYNTAX INTEGER {
                    s128  (8),
                    s256  (9),
                    s512  (10),
                    s1024 (11)
                    }
            ACCESS read-only
            STATUS mandatory
            DESCRIPTION
                "This is the maximum packet size used on X.25 links. 
                 For proper operation, the size must be the same in devices 
                 at each end of the link. This is a B-channel object."
        ::= { cdx6500PPCTBRIX25ChanEntry 25 }
         
        cdx6500BRIX25ChanCfgMaxNegoPktSize OBJECT-TYPE
            SYNTAX INTEGER {
                    s128  (8),
                    s256  (9),
                    s512  (10),
                    s1024 (11)
                    }
            ACCESS read-only
            STATUS mandatory
            DESCRIPTION
                "This is the maximum negotiated packet size allowed for inbound
                 and outbound calls on this X.25 link."
        ::= { cdx6500PPCTBRIX25ChanEntry 26 }
         
        cdx6500BRIX25ChanCfgDataQUpperThres OBJECT-TYPE
            SYNTAX INTEGER (5..15)
            ACCESS read-only
            STATUS mandatory
            DESCRIPTION
                "This is the maximum number of data packets a channel on 
                 this port will queue for transmission before invoking flow 
                 control to the attached channel."
        ::= { cdx6500PPCTBRIX25ChanEntry 27 }
         
        cdx6500BRIX25ChanCfgDataQLowerThres OBJECT-TYPE
            SYNTAX INTEGER (0..4)
            ACCESS read-only
            STATUS mandatory
            DESCRIPTION
                "This is the number of data packets a channel on this port will
                 have queued for transmission when it releases flow control 
                 to the attached channel."
        ::= { cdx6500PPCTBRIX25ChanEntry 28 }
         
        cdx6500BRIX25ChanCfgRestartTimer OBJECT-TYPE
            SYNTAX INTEGER (5..255)
            ACCESS read-only
            STATUS mandatory
            DESCRIPTION
                "Restart-Request timeout timer in seconds. If timer expires,
                 request is sent again."
        ::= { cdx6500PPCTBRIX25ChanEntry 29 }
         
        cdx6500BRIX25ChanCfgResetTimer OBJECT-TYPE
            SYNTAX INTEGER (5..255)
            ACCESS read-only
            STATUS mandatory
            DESCRIPTION
                "Reset-Request timeout timer in seconds. If timer expires,
                 request is sent again."
        ::= { cdx6500PPCTBRIX25ChanEntry 30 }
         
        cdx6500BRIX25ChanCfgCallTimer OBJECT-TYPE
            SYNTAX INTEGER (5..255)
            ACCESS read-only
            STATUS mandatory
            DESCRIPTION
                "Call-Request timeout timer in seconds. If timer expires, 
                 call is cleared."
        ::= { cdx6500PPCTBRIX25ChanEntry 31 }
         
        cdx6500BRIX25ChanCfgClearTimer OBJECT-TYPE
            SYNTAX INTEGER (5..255)
            ACCESS read-only
            STATUS mandatory
            DESCRIPTION
                "Clear-Request timeout timer in seconds. If timer expires,
                 request is sent again."
        ::= { cdx6500PPCTBRIX25ChanEntry 32 }
         
        cdx6500BRIX25ChanCfgFacToDelFromOutbCalls OBJECT-TYPE
            SYNTAX DisplayString (SIZE(3..17))
            ACCESS read-only
            STATUS mandatory
            DESCRIPTION
                "Specify facilities deleted from an outbound call before it 
                 is forwarded:
                 NONE - no facilities deleted
                 THRO - delete throughput class negotiation
                 NUI  - delete network user identification
                 CUG  - delete closed user group
                 Any combination of above specified by summing
                 (e.g. THRO+NUI. . .)."
        ::= { cdx6500PPCTBRIX25ChanEntry 33 }
         
        cdx6500BRIX25ChanCfgFacToAddToOutbCalls OBJECT-TYPE
            SYNTAX DisplayString (SIZE(3..18))
            ACCESS read-only
            STATUS mandatory
            DESCRIPTION
                "Specify facilities added to an outbound call before it 
                 is forwarded:
                 NONE - no facilities added
                 REV  - add reverse charging
                 PACK - add packet size negotiation
                 WIND - add window size negotiation
                 Any combination of above specified by summing 
                 (e.g. PACK+WIND+. . .)."
        ::= { cdx6500PPCTBRIX25ChanEntry 34 }
         
        cdx6500BRIX25ChanCfgFacToBarInOutbCalls OBJECT-TYPE
            SYNTAX DisplayString (SIZE(3..24))
            ACCESS read-only
            STATUS mandatory
            DESCRIPTION
                "Specify facilities which, if present in an outbound call, 
                 will be blocked by the port:
                 NONE  - no facility blocked
                 REV   - bar reverse charging
                 FAST  - bar fast select
                 BCUG  - bar Bilateral Closed User Group
                 DGRAM - bar datagram
                 Any combination of above specified by summing (e.g. REV+FAST)."
        ::= { cdx6500PPCTBRIX25ChanEntry 35 }
          
        cdx6500BRIX25ChanCfgFacToBarInInbCalls OBJECT-TYPE
            SYNTAX DisplayString (SIZE(3..19))
            ACCESS read-only
            STATUS mandatory
            DESCRIPTION
                "Specify facilities which, if present in an inbound call, 
                 will be blocked by the port:
                 NONE  - no facility blocked
                 BCUG  - bar Bilateral Closed User Group
                 DGRAM - bar datagram 
                 REV   - bar Reverse Charging
                 Any combination of above specified by summing 
                 (e.g. DGRAM+BCUG)."
        ::= { cdx6500PPCTBRIX25ChanEntry 36 }
         
        cdx6500BRIX25ChanCfgX25Options OBJECT-TYPE
            SYNTAX DisplayString (SIZE(3..107))
            ACCESS read-only
            STATUS mandatory
            DESCRIPTION
                "Select X.25 options as follows:
                 NONE  - no option specified
                 1980  - use X.25 1980
                 NUI   - perform network user identification validation check
                 PDN   - connected to Public Data Network
                 CUD   - use call user data subaddressing
                 IBAR  - bar all calls coming in from X.25 port user
                 OBAR  - bar all calls going out to X.25 port user
                 CBCK  - allow routing inbound calls back out this port
                 CUG   - check closed user group; otherwise, CUG passes 
                         transparently
                 CAUSE - pass cause, diagnostic, code in outbound packets
                 HOLD  - hold calls over link restart
                 NRST  - do not send restart packet on link-up
                 BKUP  - this is a backup port to be activated if other ports
                         are down
                 INL   - inter-node link. Link goes to another 6500 device
                 INLA  - set with INL option when an X.25 link connection is to
                         a 6500 node using 2.12.04 or earlier
                 DELAY - Enable Delay and Path Trace on this link
                         (link must be connected to Rel. 4.xx node)
                 Any combination of above specified by summing 
                 (e.g. 1980+NUI+. . .)."
        ::= { cdx6500PPCTBRIX25ChanEntry 37 }
         
        cdx6500BRIX25ChanCfgNumRoutDgtInCallUsrData OBJECT-TYPE
            SYNTAX INTEGER (0..12)
            ACCESS read-only
            STATUS mandatory
            DESCRIPTION
                "This specifies the number of routing digits in the call user
                 data. It is used on X.25 links attached to a Public Data 
                 Network where the private network address is carried in the 
                 call user data."
        ::= { cdx6500PPCTBRIX25ChanEntry 38 }
         
        cdx6500BRIX25ChanCfgNumPreAddrDgstrpOutgCalls OBJECT-TYPE
            SYNTAX INTEGER (0..14)
            ACCESS read-only
            STATUS mandatory
            DESCRIPTION
                "For X.25 links connected to a Public Data Network, 
                 this parameter specifies the number of prefix digits to 
                 remove from the called address before forwarding the call 
                 to the PDN."
        ::= { cdx6500PPCTBRIX25ChanEntry 39 }
         
        cdx6500BRIX25ChanCfgInDigitsToStrip OBJECT-TYPE
            SYNTAX INTEGER (0..15)
            ACCESS read-only
            STATUS mandatory
            DESCRIPTION
                "For X.25 links connected to a Public Data Network, this 
                 parameter specifies the number of prefix digits to remove 
                 from the incoming calling address before forwarding the call 
                 from the PDN."
        ::= { cdx6500PPCTBRIX25ChanEntry 40 }
         
        cdx6500BRIX25ChanCfgRestrictedConnDest OBJECT-TYPE
            SYNTAX DisplayString (SIZE(0..32))
            ACCESS read-only
            STATUS mandatory
            DESCRIPTION
                "All calls entering this port will be routed to the destination
                 specified in this parameter, irrespective of route selection 
                 table entries. 
                 For example, to route all calls to X.25 port 3, use X25-3.
                 To route calls to SDLC port 2, station 4, use SDLC-2S4.
                 Function is disabled for blank field."
        ::= { cdx6500PPCTBRIX25ChanEntry 41 }
         
        cdx6500BRIX25ChanCfgPortAddress OBJECT-TYPE
            SYNTAX DisplayString (SIZE(0..15))
            ACCESS read-only
            STATUS mandatory
            DESCRIPTION
                "On X.25 links:
                 If the X.25 Option REGO, REGSO or REGI is selected, this 
                 address is inserted into the calling address field of the 
                 outbound or inbound call packet.
                 On MUX links:
                 When a MUX channel makes a call, the subaddress of the channel
                 is appended to this address and inserted into the calling 
                 address field of the call packet."
        ::= { cdx6500PPCTBRIX25ChanEntry 42 }
         
        cdx6500BRIX25ChanCfgCUGMembership OBJECT-TYPE
            SYNTAX DisplayString (SIZE(0..23))
            ACCESS read-only
            STATUS mandatory
            DESCRIPTION
                "The port may be a member of up to 8 different Closed User 
                 Groups (CUGs).
                 Each CUG membership must be a two digit number (except double
                 dash) and separated by a comma. ( e.g. 12,34,56,09,02,03 ).
                 --    - No CUG Membership
                 00-99 - CUG Membership"
        ::= { cdx6500PPCTBRIX25ChanEntry 43 }
         
        cdx6500BRIX25ChanCfgBillingRecords  OBJECT-TYPE
            SYNTAX INTEGER {
                    off (1),
                    on  (2)
                    }
            ACCESS read-only
            STATUS mandatory
            DESCRIPTION
                "This controls whether billing (accounting) records will 
                 be created for calls on this port."
        ::= { cdx6500PPCTBRIX25ChanEntry 44 }
         
        cdx6500BRIX25ChanCfgSubAddrSize OBJECT-TYPE
            SYNTAX INTEGER (0..3)
            ACCESS read-only
            STATUS mandatory
            DESCRIPTION
                "For ports connected to a Public Data Network, this parameter 
                 specifies the number of digits in the subaddress of an X.25 
                 address."
        ::= { cdx6500PPCTBRIX25ChanEntry 45 }
         
        cdx6500BRIX25ChanCfgCallSecurity OBJECT-TYPE
            SYNTAX INTEGER {
                    disable (1),
                    enable  (2)
                    }
            ACCESS read-only
            STATUS mandatory
            DESCRIPTION
                "For ports used as V.25 bis or SW56K backup, this parameter 
                 specifies the type of call security to use prior to the link 
                 being detected up.
                 disable - Disable will allow both incoming and outgoing calls.
                 enable  - Enable will allow ONLY outgoing calls. Incoming calls
                           will be immediately terminated."
        ::= { cdx6500PPCTBRIX25ChanEntry 46 }
         
        cdx6500BRIX25ChanCfgProtectionLevel OBJECT-TYPE
            SYNTAX INTEGER {
                    none    (1),
                    cpOnly  (2),
                    fullDcp (3)
                    }
            ACCESS read-only
            STATUS mandatory
            DESCRIPTION
                "This specifies the level of data or connection protection 
                 which will be applied to calls to or from this port.
                 The actual level for a call will be negotiated to the lesser 
                 of this level and the level configured for the other end of 
                 the call.
                 none    - No protection
                 cpOnly  - Connection protection only
                 fullDcp - Full data and connection protection"
        ::= { cdx6500PPCTBRIX25ChanEntry 47 }
         
        cdx6500BRIX25ChanCfgReconnTimeout OBJECT-TYPE
            SYNTAX INTEGER (1..128)
            ACCESS read-only
            STATUS mandatory
            DESCRIPTION
                "This specifies the number of seconds that DCP on the 
                 originating side will wait between reconnection attempts."
        ::= { cdx6500PPCTBRIX25ChanEntry 48 }
         
        cdx6500BRIX25ChanCfgReconnTriesLt OBJECT-TYPE
            SYNTAX INTEGER (0..127)
            ACCESS read-only
            STATUS mandatory
            DESCRIPTION
                "This specifies the number of times that DCP on the originating
                 side will attempt to reconnect before clearing the call.  For0,
                 it will not attempt to reconnect."
        ::= { cdx6500PPCTBRIX25ChanEntry 49 }
         
        cdx6500BRIX25ChanCfgFacSubsCtl OBJECT-TYPE
            SYNTAX DisplayString
            ACCESS read-only
            STATUS mandatory
            DESCRIPTION
                "NONE    - Subscription to facilities not enforced.
                 FCN_ON  - Flow Control Negotiation enabled.
                           Packet and Window size negotiation facilities in 
                           an inbound call will be allowed.
                           Packet and Window size facilities will always be 
                           included in outbound calls and call accepted/
                           connected when this parameter is set.
                 FCN_OFF - Flow Control Negotiation disabled.
                           Inbound calls containing Packet and Window size 
                           facilities will be cleared. Packet and Window size
                           facilities will not be present in outbound calls 
                           and call accepted/connected when this parameter is
                           set.
                 TCN_ON  - Throughput Class Negotiation enabled.
                           The throughput class negotiation facility in an 
                           inbound call will be allowed. The throughput class
                           negotiation facility will always be included in 
                           outbound calls and call accepted/connected when 
                           this parameter is set. The facility is passed onward
                           to the destination in the call packet transparently
                           and does not alter the handling of the
                           SVC data within the node.
                 TCN_OFF - Throughput Class Negotiation disabled.
                           Inbound calls containing the throughput class 
                           negotiation facility will be cleared. The throughput
                           class negotiation facility will not be present in 
                           outbound calls and call accepted/connected when this
                           parameter is set.
                 Some combinations of above options are allowed 
                 (e.g. FCNON+TCNON)"
        ::= { cdx6500PPCTBRIX25ChanEntry 50 }
         
        cdx6500BRIX25ChanCfgAlarmPriority OBJECT-TYPE
            SYNTAX INTEGER {
                    network (1),
                    access  (2)
                    }
            ACCESS read-only
            STATUS mandatory
            DESCRIPTION
                "Specify the severity level of LINK UP and LINK DOWN alarms:
                 network - Severity HIGH alarms will be generated
                 access  - Severity LOW alarms will be generated"
        ::= { cdx6500PPCTBRIX25ChanEntry 51 }
         
        cdx6500BRIX25ChanCfgChanTEI OBJECT-TYPE
            SYNTAX INTEGER (1..63)
            ACCESS read-only
            STATUS mandatory
            DESCRIPTION
                "Terminal Endpoint Identifier. Value is
                 provided by the service provider."
        ::= { cdx6500PPCTBRIX25ChanEntry 52 }
         
        cdx6500BRIX25ChanCfgX25NetworkType OBJECT-TYPE
            SYNTAX INTEGER {
                    transpac (1),
                    telenet  (2),
                    pss      (3),
                    datanet  (4)
                    }
            ACCESS read-only
            STATUS mandatory
            DESCRIPTION
                "Specifies the X.25 Network Type:
                 Transpac, PSS, Datanet, Telenet."
        ::= { cdx6500PPCTBRIX25ChanEntry 53 }
         
        cdx6500BRIX25ChanCfgDNumSVCChannels OBJECT-TYPE
            SYNTAX INTEGER (1..15)
            ACCESS read-only
            STATUS mandatory
            DESCRIPTION
                "Specifies the number of logical SVC channels on this 
                 port. This is a D-channel object."
        ::= { cdx6500PPCTBRIX25ChanEntry 54 }
         
        cdx6500BRIX25ChanCfgDWPktWindow OBJECT-TYPE
            SYNTAX INTEGER (1..7)
            ACCESS read-only
            STATUS mandatory
            DESCRIPTION
                "Specifies the default packet level window size when it is
                 not negotiated for the individual call. The value must be
                 the same for both ends of the link.
                 This is a D-channel object."
        ::= { cdx6500PPCTBRIX25ChanEntry 55 }
         
        cdx6500BRIX25ChanCfgDPPktSize OBJECT-TYPE
            SYNTAX INTEGER {
                    psize32  (6),
                    psize64  (7),
                    psize128 (8),
                    psize256 (9)
                    }
            ACCESS read-only
            STATUS mandatory
            DESCRIPTION
                "Specifies the maximum default packet size (in bytes) for 
                 inbound and outbound calls on the link. The
                 value must be the same for both ends of the link.
                 This is a D-channel object."
        ::= { cdx6500PPCTBRIX25ChanEntry 56 }
         
        cdx6500BRIX25ChanCfgDKFrameWindow OBJECT-TYPE
            SYNTAX INTEGER (1..7)
            ACCESS read-only
            STATUS mandatory
            DESCRIPTION
                "Specifies the number of unacknowledged frames that can be
                 outstanding. When there is a high link delay, set this
                 parameter to a high value to improve throughput. The setting
                 for this parameter should be the same for the devices on both
                 ends of the link. This is a D-channel object."
        ::= { cdx6500PPCTBRIX25ChanEntry 57 }
         
        cdx6500BRIX25ChanCfgDN2TransTries OBJECT-TYPE
            SYNTAX INTEGER (1..254)
            ACCESS read-only
            STATUS mandatory
            DESCRIPTION
                "Specifies the maximum number of times a frame is resent 
                 before disconnect. This is a D-channel object."
        ::= { cdx6500PPCTBRIX25ChanEntry 58 }
         
        cdx6500BRIX25ChanCfgT1Timer OBJECT-TYPE
            SYNTAX INTEGER (0..16383)
            ACCESS read-only
            STATUS mandatory
            DESCRIPTION
                "Sets the T1 Retry Timer. The values are in tenths of a second.
                 (30 = 3.0 seconds)"
        ::= { cdx6500PPCTBRIX25ChanEntry 59 }
         
        cdx6500BRIX25ChanCfgT2Timer OBJECT-TYPE
            SYNTAX INTEGER (0..16383)
            ACCESS read-only
            STATUS mandatory
            DESCRIPTION
                "Sets the T2 timer. The values are in tenths of a second.
                 (40 = 4.0 seconds)"
        ::= { cdx6500PPCTBRIX25ChanEntry 60 }
         
        cdx6500BRIX25ChanCfgLinkType OBJECT-TYPE
            SYNTAX INTEGER {
                    dChannel (1),
                    v24Dte   (2),
                    v24Dce   (3)
                    }
            ACCESS read-only
            STATUS mandatory
            DESCRIPTION
                "Engineering use only.
                 Sets the link type:
                 dChannel - Run over the D channel
                 v24Dte  - DTE on the V.24 port
                 v24Dce  - DCE on the V.24 port"
        ::= { cdx6500PPCTBRIX25ChanEntry 61 }
         
        cdx6500BRIX25ChanCfgAddrTrans OBJECT-TYPE
            SYNTAX DisplayString (SIZE(3..107))
            ACCESS read-only
            STATUS mandatory
            DESCRIPTION
                "Select any of the  following address translation options
                 NONE  - no option specified
                 Outbound Call Processing:
                 DEDO  - delete called address
                 DEGO  - delete calling address
                 REGO  - replace calling address with configured Port Address
                 REGSO - replace calling address with configured Port
                         Address plus Inbound Subaddress obtained from 
                         the Inbound Call Translation Table entry where
                         Private Network Address matches the entire
                         calling address
                 INGO  - replace calling address with configured Port 
                         Address and retain original calling subaddress
                 SAGO  - strip calling address, but retain subaddress
    
                 Inbound Call Processing:
                 INGI  - replace calling address with configured Port
                         Address and retain original calling subaddress
                 REGI  - replace calling address with configured Port Address
                 SRGI  - select route from the Calling Address 
                         Translation Table by replacing the called
                         address with the Private Network Address
                         where the Inbound Calling Address matches
                         the beginning of the calling address
   
                 Call Accept Processing:
                 DADA  - delete called address in inbound/outbound 
                         call accept
                 DAGA  - delete calling address in inbound/outbound 
                         call accept
                 IADD  - copy called and calling addresses from call
                         request into outbound call accepted/connected
                 Some of the options may be combined (e.g. DEDO + DEGO)."
        ::= { cdx6500PPCTBRIX25ChanEntry 62 }

        cdx6500BRIStats OBJECT IDENTIFIER ::= { cdx6500PSTPortProtocolGroup 27 }

        cdx6500BRIPStatsTable OBJECT-TYPE
            SYNTAX SEQUENCE OF Cdx6500BRIPStatsTableEntry
            ACCESS not-accessible
            STATUS mandatory
            DESCRIPTION
                "A table of BRI port statistics."
        ::=  {cdx6500BRIStats 1 }

        cdx6500BRIPStatsTableEntry OBJECT-TYPE
            SYNTAX Cdx6500BRIPStatsTableEntry
            ACCESS not-accessible
            STATUS mandatory
            DESCRIPTION
                "Each entry contains the statistics for a single BRI port."
            INDEX  { cdx6500BRIPStatPortNumber }
        ::= { cdx6500BRIPStatsTable 1 }

        Cdx6500BRIPStatsTableEntry ::=
            SEQUENCE {
                cdx6500BRIPStatPortNumber
                    INTEGER,
                cdx6500BRIPStatPortType
                    INTEGER,
                cdx6500BRIPStatPortStatus
                    DisplayString,
                cdx6500BRIPStatNumConfigChannels
                    INTEGER,
                cdx6500BRIPStatSwitchType
                    DisplayString,
                cdx6500BRIPStatTEI
                    INTEGER,
                cdx6500BRIPStatLastStatsReset
                    DisplayString,
                cdx6500BRIPStatCharsInTot
                    Counter,
                cdx6500BRIPStatCharsInPerSec
                    INTEGER,
                cdx6500BRIPStatCharsOutTot
                    Counter,
                cdx6500BRIPStatCharsOutPerSec
                    INTEGER,
                cdx6500BRIPStatFramesInTot
                    Counter,
                cdx6500BRIPStatFramesInPerSec
                    INTEGER,
                cdx6500BRIPStatFrameOutTot
                    Counter,
                cdx6500BRIPStatFrameOutPerSec
                    INTEGER,
                cdx6500BRIPStatAvFrameSzIn
                    INTEGER,
                cdx6500BRIPStatAvFrameSzOut
                    INTEGER,
                cdx6500BRIPStatPortUtilIn
                    INTEGER,
                cdx6500BRIPStatPortUtilOut
                    INTEGER,
                cdx6500BRIPStatPortUtilInMax
                    INTEGER,
                cdx6500BRIPStatPortUtilOutMax
                    INTEGER
                }

        cdx6500BRIPStatPortNumber OBJECT-TYPE
            SYNTAX INTEGER
            ACCESS read-only
            STATUS mandatory
            DESCRIPTION
                "The port number of the BRI port."
        ::= { cdx6500BRIPStatsTableEntry 1 }

        cdx6500BRIPStatPortType OBJECT-TYPE
            SYNTAX INTEGER {
                    bri (40)
                    }
            ACCESS read-only
            STATUS mandatory
            DESCRIPTION
                "The Port Type of the port."
        ::= { cdx6500BRIPStatsTableEntry 2 }

        cdx6500BRIPStatPortStatus OBJECT-TYPE
            SYNTAX DisplayString (SIZE(2..8))
            ACCESS read-only
            STATUS mandatory
            DESCRIPTION
                "Status of this port :
                 Enabled  - Port is enabled
                 Disabled - Port is disabled
                 Busyout  - Port has been busied out
                 Unknown  - Port not recognized
                 Init Failed - Port initialization failed."
        ::= { cdx6500BRIPStatsTableEntry 3 }

        cdx6500BRIPStatNumConfigChannels OBJECT-TYPE
            SYNTAX INTEGER (0..3)
            ACCESS read-only
            STATUS mandatory
            DESCRIPTION
                "The number of configured channels."
        ::= { cdx6500BRIPStatsTableEntry 4 }

        cdx6500BRIPStatSwitchType OBJECT-TYPE
            SYNTAX DisplayString (SIZE (0..23))
            ACCESS read-only
            STATUS mandatory
            DESCRIPTION
                "Specifies switch type for the central office.
                 VN4  : French VN4 standard
                 1TR6 : German switch standard
                 BTNR : UK Standard
                 ETSI : Euro-ISDN
                 5ESS : AT&T switch
                 NI-1 : National ISDN version 1 "
        ::= { cdx6500BRIPStatsTableEntry 5 }

        cdx6500BRIPStatTEI OBJECT-TYPE
            SYNTAX INTEGER 
            ACCESS read-only
            STATUS mandatory
            DESCRIPTION
                "Terminal Endpoint Identifier.
                 The range of values [0 - 63] indicate a static
                 TEI provided by the Network subscribing.
                 127: TEI negotiated"
        ::= { cdx6500BRIPStatsTableEntry 6 }

        cdx6500BRIPStatLastStatsReset OBJECT-TYPE
            SYNTAX DisplayString
            ACCESS read-only
            STATUS mandatory
            DESCRIPTION
                "Time when the statistics were last reset."
        ::= { cdx6500BRIPStatsTableEntry 7 }

        cdx6500BRIPStatCharsInTot OBJECT-TYPE
            SYNTAX Counter
            ACCESS read-only
            STATUS mandatory
            DESCRIPTION
                "Number of characters received since last node,
                 port or statistics reset."
        ::= { cdx6500BRIPStatsTableEntry 8 }

        cdx6500BRIPStatCharsInPerSec OBJECT-TYPE
            SYNTAX INTEGER
            ACCESS read-only
            STATUS mandatory
            DESCRIPTION
                "Average number of characters received per second
                 since last node, port or statistics reset."
        ::= { cdx6500BRIPStatsTableEntry 9 }

        cdx6500BRIPStatCharsOutTot OBJECT-TYPE
            SYNTAX Counter
            ACCESS read-only
            STATUS mandatory
            DESCRIPTION
                "Number of characters sent since last node,
                 port or statistics reset."
        ::= { cdx6500BRIPStatsTableEntry 10 }

        cdx6500BRIPStatCharsOutPerSec OBJECT-TYPE
            SYNTAX INTEGER
            ACCESS read-only
            STATUS mandatory
            DESCRIPTION
                "Average number of characters sent per second
                 since last node, port or statistics reset."
        ::= { cdx6500BRIPStatsTableEntry 11 }

        cdx6500BRIPStatFramesInTot OBJECT-TYPE
            SYNTAX Counter
            ACCESS read-only
            STATUS mandatory
            DESCRIPTION
                "Number of frames received since last node, 
                 port or statistics reset."
        ::= { cdx6500BRIPStatsTableEntry 12 }

        cdx6500BRIPStatFramesInPerSec OBJECT-TYPE
            SYNTAX INTEGER
            ACCESS read-only
            STATUS mandatory
            DESCRIPTION
                "Average number of Frames received per second
                 since last node, port or statistics reset."
        ::= { cdx6500BRIPStatsTableEntry 13 }

        cdx6500BRIPStatFrameOutTot OBJECT-TYPE
            SYNTAX Counter
            ACCESS read-only
            STATUS mandatory
            DESCRIPTION
                "Number of frames sent since last node,
                 port or statistics reset."
        ::= { cdx6500BRIPStatsTableEntry 14 }

        cdx6500BRIPStatFrameOutPerSec OBJECT-TYPE
            SYNTAX INTEGER
            ACCESS read-only
            STATUS mandatory
            DESCRIPTION
                "Average number of Frames sent per second
                 since last node, port or statistics reset."
        ::= { cdx6500BRIPStatsTableEntry 15 }

        cdx6500BRIPStatAvFrameSzIn OBJECT-TYPE
            SYNTAX INTEGER
            ACCESS read-only
            STATUS mandatory
            DESCRIPTION
                "Average size of the frames received."
        ::= { cdx6500BRIPStatsTableEntry 16 }

        cdx6500BRIPStatAvFrameSzOut OBJECT-TYPE
            SYNTAX INTEGER
            ACCESS read-only
            STATUS mandatory
            DESCRIPTION
                "Average size of the frames sent."
        ::= { cdx6500BRIPStatsTableEntry 17 }

        cdx6500BRIPStatPortUtilIn OBJECT-TYPE
            SYNTAX INTEGER
            ACCESS read-only
            STATUS mandatory
            DESCRIPTION
                "Current inbound port utilization."
        ::= { cdx6500BRIPStatsTableEntry 18 }

        cdx6500BRIPStatPortUtilOut OBJECT-TYPE
            SYNTAX INTEGER
            ACCESS read-only
            STATUS mandatory
            DESCRIPTION
                "Current outbound port utilization."
        ::= { cdx6500BRIPStatsTableEntry 19 }

        cdx6500BRIPStatPortUtilInMax  OBJECT-TYPE
            SYNTAX INTEGER
            ACCESS read-only
            STATUS mandatory
            DESCRIPTION
                "Maximum inbound port utilization."
        ::= { cdx6500BRIPStatsTableEntry 20 }

        cdx6500BRIPStatPortUtilOutMax OBJECT-TYPE
            SYNTAX INTEGER
            ACCESS read-only
            STATUS mandatory
            DESCRIPTION
                "Maximum outbound port utilization."
        ::= { cdx6500BRIPStatsTableEntry 21 }

        cdx6500BRIChanStatsTable OBJECT-TYPE
            SYNTAX SEQUENCE OF Cdx6500BRIChanStatsTableEntry
            ACCESS not-accessible
            STATUS mandatory
            DESCRIPTION
                "A table of BRI channel statistics."
        ::= { cdx6500BRIStats 2 }

        cdx6500BRIChanStatsTableEntry OBJECT-TYPE
            SYNTAX Cdx6500BRIChanStatsTableEntry
            ACCESS not-accessible
            STATUS mandatory
            DESCRIPTION
                "Each entry contains the statistics for a single channel."
            INDEX  { cdx6500BRICStatsPortNumber,
                     cdx6500BRICStatsChannelNum }
        ::= { cdx6500BRIChanStatsTable 1 }

        Cdx6500BRIChanStatsTableEntry ::=
            SEQUENCE {
                cdx6500BRICStatsPortNumber
                    INTEGER,
                cdx6500BRICStatsChannelNum
                    INTEGER,
                cdx6500BRICStatsChannelType
                    DisplayString,
                cdx6500BRICStatsAccessType
                    DisplayString,
                cdx6500BRICStatsProtocolType
                   DisplayString,
                cdx6500BRICStatsCallState
                    DisplayString,
                cdx6500BRICStatsChannelStatus
                    DisplayString,
                cdx6500BRICStatsInCurCallAddr
                    DisplayString,
                cdx6500BRICStatsInCurCallSubAddr
                    DisplayString,
                cdx6500BRICStatsInAvConnTm
                    DisplayString,
                cdx6500BRICStatsInCurConnTm
                    DisplayString,
                cdx6500BRICStatsInMinConnTm
                    DisplayString,
                cdx6500BRICStatsInMaxConnTm
                    DisplayString,
                cdx6500BRICStatsInNumSuccCalls
                    INTEGER,
                cdx6500BRICStatsInNumFailCalls
                    INTEGER,
                cdx6500BRICStatsOutCurCallAddr
                    DisplayString,
                cdx6500BRICStatsOutCurCallSubAddr
                    DisplayString,
                cdx6500BRICStatsOutAvConnTm
                    DisplayString,
                cdx6500BRICStatsOutCurConnTm
                    DisplayString,
                cdx6500BRICStatsOutMinConnTm
                    DisplayString,
                cdx6500BRICStatsOutMaxConnTm
                    DisplayString,
                cdx6500BRICStatsOutNumSuccCalls
                    INTEGER,
                cdx6500BRICStatsOutNumFailCalls
                    INTEGER,
                cdx6500BRICStatsMaxSVC
                    INTEGER,
                cdx6500BRICStatsMaxPVC
                    INTEGER,
                cdx6500BRICStatsCurSVC
                    INTEGER,
                cdx6500BRICStatsCurPVC
                    INTEGER,
                cdx6500BRICStatsLastRepReasonCodes
                    DisplayString,
                cdx6500BRICStatsLastStatsReset
                    DisplayString,
                cdx6500BRICStatsCharsInTot
                    Counter,
                cdx6500BRICStatsCharsOutTot
                    Counter,
                cdx6500BRICStatsCharsInPerSec
                    INTEGER,
                cdx6500BRICStatsCharsOutPerSec
                    INTEGER,
                cdx6500BRICStatsPktsInTot
                    Counter,
                cdx6500BRICStatsPktsOutTot
                    Counter,
                cdx6500BRICStatsPktsInPerSec
                    INTEGER,
                cdx6500BRICStatsPktsOutPerSec
                    INTEGER,
                cdx6500BRICStatsFramesInTot
                    Counter,
                cdx6500BRICStatsFramesOutTot
                    Counter,
                cdx6500BRICStatsFramesInPerSec
                    INTEGER,
                cdx6500BRICStatsFramesOutPerSec
                    INTEGER,
                cdx6500BRICStatsInfoFramesIn
                    Counter,
                cdx6500BRICStatsInfoFramesOut
                    Counter,
                cdx6500BRICStatsRNRFramesIn
                    Counter,
                cdx6500BRICStatsRNRFramesOut
                    Counter,
                cdx6500BRICStatsSABMFramesIn
                    Counter,
                cdx6500BRICStatsSABMFramesOut
                    Counter,
                cdx6500BRICStatsDMFramesIn
                    Counter,
                cdx6500BRICStatsDMFramesOut
                    Counter,
                cdx6500BRICStatsRRFramesIn
                    Counter,
                cdx6500BRICStatsRRFramesOut
                    Counter,
                cdx6500BRICStatsREJFramesIn
                    Counter,
                cdx6500BRICStatsREJFramesOut
                    Counter,
                cdx6500BRICStatsDISCFramesIn
                    Counter,
                cdx6500BRICStatsDISCFramesOut
                    Counter,
                cdx6500BRICStatsUAFramesIn
                    Counter,
                cdx6500BRICStatsUAFramesOut
                    Counter,
                cdx6500BRICStatsFRMRFramesIn
                    Counter,
                cdx6500BRICStatsFRMRFramesOut
                    Counter,
                cdx6500BRICStatsDataPktsIn
                    Counter,
                cdx6500BRICStatsDataPktsOut
                    Counter,
                cdx6500BRICStatsRRPktsIn
                    Counter,
                cdx6500BRICStatsRRPktsOut
                    Counter,
                cdx6500BRICStatsRNRPktsIn
                    Counter,
                cdx6500BRICStatsRNRPktsOut
                    Counter,
                cdx6500BRICStatsRejPktsIn
                    Counter,
                cdx6500BRICStatsRejPktsOut
                    Counter,
                cdx6500BRICStatsCallReqPktsIn
                    Counter,
                cdx6500BRICStatsCallReqPktsOut
                    Counter,
                cdx6500BRICStatsCallAccPktsIn
                    Counter,
                cdx6500BRICStatsCallAccPktsOut
                    Counter,
                cdx6500BRICStatsClrReqPktsIn
                    Counter,
                cdx6500BRICStatsClrReqPktsOut
                    Counter,
                cdx6500BRICStatsClrConfPktsIn
                    Counter,
                cdx6500BRICStatsClrConfPktsOut
                    Counter,
                cdx6500BRICStatsIntReqPktsIn
                    Counter,
                cdx6500BRICStatsIntReqPktsOut
                     Counter,
                cdx6500BRICStatsIntConfPktsIn
                    Counter,
                cdx6500BRICStatsIntConfPktsOut
                    Counter,
                cdx6500BRICStatsRstReqPktsIn
                    Counter,
                cdx6500BRICStatsRstReqPktsOut
                    Counter,
                cdx6500BRICStatsRstConfPktsIn
                    Counter,
                cdx6500BRICStatsRstConfPktsOut
                    Counter,
                cdx6500BRICStatsRestartReqPktsIn
                    Counter,
                cdx6500BRICStatsRestartReqPktsOut
                    Counter,
                cdx6500BRICStatsRestartConfPktsIn
                    Counter,
                cdx6500BRICStatsRestartConfPktsOut
                    Counter,
                cdx6500BRICStatsTEI
                    INTEGER,
                cdx6500BRICStatsSAPI
                    INTEGER,
                cdx6500BRICStatsNetworkType
                    DisplayString
                } 

        cdx6500BRICStatsPortNumber OBJECT-TYPE
            SYNTAX INTEGER
            ACCESS read-only
            STATUS mandatory
            DESCRIPTION
                "The BRI port number associated with the channels."
        ::= { cdx6500BRIChanStatsTableEntry 1 }

        cdx6500BRICStatsChannelNum OBJECT-TYPE
            SYNTAX INTEGER (1..3)
            ACCESS read-only
            STATUS mandatory
            DESCRIPTION
                "The ISDN channel Number."
        ::= { cdx6500BRIChanStatsTableEntry 2 }

        cdx6500BRICStatsChannelType OBJECT-TYPE
            SYNTAX DisplayString
            ACCESS read-only
            STATUS mandatory
            DESCRIPTION
                "ISDN channel type.
                 B Channel : a full duplex, 56 or 64 Kbps channel.
                 D Channel : a full duplex, 16 Kbps channel
                             configured only for packet mode.
                 Unknown   : unknown channel type ."
        ::= { cdx6500BRIChanStatsTableEntry 3 }

        cdx6500BRICStatsAccessType OBJECT-TYPE
            SYNTAX DisplayString
            ACCESS read-only
            STATUS mandatory
            DESCRIPTION
                "Switched BRI channel type.
                 Permanent channel type : not supported in this version
                 Unknown : unknown access type ."
        ::= { cdx6500BRIChanStatsTableEntry 4 }

        cdx6500BRICStatsProtocolType OBJECT-TYPE
            SYNTAX DisplayString
            ACCESS read-only
            STATUS mandatory
            DESCRIPTION
                "Specifies the protocol type such as X25, FRI.
                 `Unknown' indicates unknown protocol type." 
        ::= { cdx6500BRIChanStatsTableEntry 5 }

        cdx6500BRICStatsCallState OBJECT-TYPE
            SYNTAX DisplayString 
            ACCESS read-only
            STATUS mandatory
            DESCRIPTION
                "Call State:
                 Disconnected - Call in Idle state
                 Ringing      - Trying to establish connection
                 Connected    - Call connected
                 Disabled     - Call disabled
                 Congested    - not supported
                 Unknown      - unknown state ."
        ::= { cdx6500BRIChanStatsTableEntry 6 }

        cdx6500BRICStatsChannelStatus OBJECT-TYPE
            SYNTAX DisplayString
            ACCESS read-only
            STATUS mandatory
            DESCRIPTION
                "Disabled - Channel disabled.
                 Enabled  - Channel enabled.
                 Busyout  - Channel busyout
                 Unknown  - unknown status."
        ::= { cdx6500BRIChanStatsTableEntry 7 }

        cdx6500BRICStatsInCurCallAddr OBJECT-TYPE
            SYNTAX DisplayString
            ACCESS read-only
            STATUS mandatory
            DESCRIPTION
                "The address for the current inbound ISDN call."
        ::= { cdx6500BRIChanStatsTableEntry 8 }

        cdx6500BRICStatsInCurCallSubAddr OBJECT-TYPE
            SYNTAX DisplayString
            ACCESS read-only
            STATUS mandatory
            DESCRIPTION
                "The subaddress for the current ISDN call."
        ::= { cdx6500BRIChanStatsTableEntry 9 }

        cdx6500BRICStatsInAvConnTm OBJECT-TYPE
            SYNTAX DisplayString
            ACCESS read-only
            STATUS mandatory
            DESCRIPTION
                "Average connection time for an inbound ISDN call."
        ::= { cdx6500BRIChanStatsTableEntry 10 }

        cdx6500BRICStatsInCurConnTm OBJECT-TYPE
            SYNTAX DisplayString
            ACCESS read-only
            STATUS mandatory
            DESCRIPTION
                "Current connection time for an inbound ISDN call.
                 current time -  Time connection started."
        ::= { cdx6500BRIChanStatsTableEntry 11 }

        cdx6500BRICStatsInMinConnTm OBJECT-TYPE
            SYNTAX DisplayString
            ACCESS read-only
            STATUS mandatory
            DESCRIPTION
                "Minimum connection time for an inbound ISDN call."
        ::= { cdx6500BRIChanStatsTableEntry 12 }

        cdx6500BRICStatsInMaxConnTm OBJECT-TYPE
            SYNTAX DisplayString
            ACCESS read-only
            STATUS mandatory
            DESCRIPTION
                "Maximum connection time for an inbound ISDN call."
        ::= { cdx6500BRIChanStatsTableEntry 13 }

        cdx6500BRICStatsInNumSuccCalls OBJECT-TYPE
            SYNTAX INTEGER
            ACCESS read-only
            STATUS mandatory
            DESCRIPTION
                "Total number of successful inbound calls."
        ::= { cdx6500BRIChanStatsTableEntry 14 }

        cdx6500BRICStatsInNumFailCalls OBJECT-TYPE
            SYNTAX INTEGER
            ACCESS read-only
            STATUS mandatory
            DESCRIPTION
                "Total number of unsuccessful inbound calls."
        ::= { cdx6500BRIChanStatsTableEntry 15 }

        cdx6500BRICStatsOutCurCallAddr OBJECT-TYPE
            SYNTAX DisplayString
            ACCESS read-only
            STATUS mandatory
            DESCRIPTION
                "The address of the current ISDN outbound call."
        ::= { cdx6500BRIChanStatsTableEntry 16 }

        cdx6500BRICStatsOutCurCallSubAddr OBJECT-TYPE
            SYNTAX DisplayString
            ACCESS read-only
            STATUS mandatory
            DESCRIPTION
                "The subaddress of the current ISDN outbound call."
        ::= { cdx6500BRIChanStatsTableEntry 17 }

        cdx6500BRICStatsOutAvConnTm OBJECT-TYPE
            SYNTAX DisplayString
            ACCESS read-only
            STATUS mandatory
            DESCRIPTION
                "Average connection time for an outbound call."
        ::= { cdx6500BRIChanStatsTableEntry 18 }

        cdx6500BRICStatsOutCurConnTm OBJECT-TYPE
            SYNTAX DisplayString
            ACCESS read-only
            STATUS mandatory
            DESCRIPTION
                "Current connection time for an outbound call.
                 Current time - Time connection started."
        ::= { cdx6500BRIChanStatsTableEntry 19 }

        cdx6500BRICStatsOutMinConnTm OBJECT-TYPE
            SYNTAX DisplayString
            ACCESS read-only
            STATUS mandatory
            DESCRIPTION
                "Minimum connection time for an outbound call."
        ::= { cdx6500BRIChanStatsTableEntry 20 }

        cdx6500BRICStatsOutMaxConnTm OBJECT-TYPE
            SYNTAX DisplayString
            ACCESS read-only
            STATUS mandatory
            DESCRIPTION
                "Maximum connection time for an outbound call."
        ::= { cdx6500BRIChanStatsTableEntry 21 }

        cdx6500BRICStatsOutNumSuccCalls OBJECT-TYPE
            SYNTAX INTEGER
            ACCESS read-only
            STATUS mandatory
            DESCRIPTION
                "Total number of successful outbound calls."
        ::= { cdx6500BRIChanStatsTableEntry 22 }

        cdx6500BRICStatsOutNumFailCalls OBJECT-TYPE
            SYNTAX INTEGER
            ACCESS read-only
            STATUS mandatory
            DESCRIPTION
                "Total number of unsuccessful outbound calls."
        ::= { cdx6500BRIChanStatsTableEntry 23 }

        cdx6500BRICStatsMaxSVC OBJECT-TYPE
            SYNTAX INTEGER
            ACCESS read-only
            STATUS mandatory
            DESCRIPTION
                "Maximum number of async Switched Virtual Circuit channels."
        ::= { cdx6500BRIChanStatsTableEntry 24 }

        cdx6500BRICStatsMaxPVC OBJECT-TYPE
            SYNTAX INTEGER
            ACCESS read-only
            STATUS mandatory
            DESCRIPTION
                "Maximum number of async Permanent Virtual Circuit channels."
        ::= { cdx6500BRIChanStatsTableEntry 25 }

        cdx6500BRICStatsCurSVC OBJECT-TYPE
            SYNTAX INTEGER
            ACCESS read-only
            STATUS mandatory
            DESCRIPTION
                "Current number of async Switched Virtual Circuit channels."
        ::= { cdx6500BRIChanStatsTableEntry 26 }

        cdx6500BRICStatsCurPVC OBJECT-TYPE
            SYNTAX INTEGER
            ACCESS read-only
            STATUS mandatory
            DESCRIPTION
                "Current number of async Permament Virtual Circuit channels."
        ::= { cdx6500BRIChanStatsTableEntry 27 }

        cdx6500BRICStatsLastRepReasonCodes OBJECT-TYPE
            SYNTAX DisplayString
            ACCESS read-only
            STATUS mandatory
            DESCRIPTION
                "Last Reason codes returned from the network and 
                 Last Return code from Transparent."
        ::= { cdx6500BRIChanStatsTableEntry 28 }

        cdx6500BRICStatsLastStatsReset OBJECT-TYPE
            SYNTAX DisplayString
            ACCESS read-only
            STATUS mandatory
            DESCRIPTION
                "Time when the node restarted or the stats reset by CTP 
                 command ."
        ::= { cdx6500BRIChanStatsTableEntry 29 }

        cdx6500BRICStatsCharsInTot OBJECT-TYPE
            SYNTAX Counter
            ACCESS read-only
            STATUS mandatory
            DESCRIPTION
                "Number of characters received."
        ::= { cdx6500BRIChanStatsTableEntry 30 }

        cdx6500BRICStatsCharsOutTot OBJECT-TYPE
            SYNTAX Counter
            ACCESS read-only
            STATUS mandatory
            DESCRIPTION
                "Number of characters sent."
        ::= { cdx6500BRIChanStatsTableEntry 31 }

        cdx6500BRICStatsCharsInPerSec OBJECT-TYPE
            SYNTAX INTEGER
            ACCESS read-only
            STATUS mandatory
            DESCRIPTION
                "Average number of characters received per second."
        ::= { cdx6500BRIChanStatsTableEntry 32 }

        cdx6500BRICStatsCharsOutPerSec OBJECT-TYPE
            SYNTAX INTEGER
            ACCESS read-only
            STATUS mandatory
            DESCRIPTION
                "Average number of characters sent per second."
        ::= { cdx6500BRIChanStatsTableEntry 33 }

        cdx6500BRICStatsPktsInTot OBJECT-TYPE
            SYNTAX Counter
            ACCESS read-only
            STATUS mandatory
            DESCRIPTION
                "Number of packets received."
        ::= { cdx6500BRIChanStatsTableEntry 34 }

        cdx6500BRICStatsPktsOutTot OBJECT-TYPE
            SYNTAX Counter
            ACCESS read-only
            STATUS mandatory
            DESCRIPTION
                  "Number of packets sent."
        ::= { cdx6500BRIChanStatsTableEntry 35 }

        cdx6500BRICStatsPktsInPerSec OBJECT-TYPE
            SYNTAX INTEGER
            ACCESS read-only
            STATUS mandatory
            DESCRIPTION
                "Average number of packets received per second."
        ::= { cdx6500BRIChanStatsTableEntry 36 }

        cdx6500BRICStatsPktsOutPerSec OBJECT-TYPE
            SYNTAX INTEGER
            ACCESS read-only
            STATUS mandatory
            DESCRIPTION
                "Average number of packets sent per second."
        ::= { cdx6500BRIChanStatsTableEntry 37 }

        cdx6500BRICStatsFramesInTot OBJECT-TYPE
            SYNTAX Counter
            ACCESS read-only
            STATUS mandatory
            DESCRIPTION
                "Total number of frames received."
        ::= { cdx6500BRIChanStatsTableEntry 38 }

        cdx6500BRICStatsFramesOutTot OBJECT-TYPE
            SYNTAX Counter
            ACCESS read-only
            STATUS mandatory
            DESCRIPTION
                "Total number of frames sent."
        ::= { cdx6500BRIChanStatsTableEntry 39 }

        cdx6500BRICStatsFramesInPerSec OBJECT-TYPE
            SYNTAX INTEGER
            ACCESS read-only
            STATUS mandatory
            DESCRIPTION
                "Average number of frames received per second."
        ::= { cdx6500BRIChanStatsTableEntry 40 }

        cdx6500BRICStatsFramesOutPerSec OBJECT-TYPE
            SYNTAX INTEGER
            ACCESS read-only
            STATUS mandatory
            DESCRIPTION
                "Average number of frames sent per second."
        ::= { cdx6500BRIChanStatsTableEntry 41 }

        cdx6500BRICStatsInfoFramesIn OBJECT-TYPE
           SYNTAX Counter
           ACCESS read-only
           STATUS mandatory
           DESCRIPTION
               "Number of Information  frames received."
        ::= { cdx6500BRIChanStatsTableEntry 42 }

        cdx6500BRICStatsInfoFramesOut OBJECT-TYPE
            SYNTAX Counter
            ACCESS read-only
            STATUS mandatory
            DESCRIPTION
                "Number of Information frames sent."
        ::= { cdx6500BRIChanStatsTableEntry 43 }

        cdx6500BRICStatsRNRFramesIn OBJECT-TYPE
            SYNTAX Counter
            ACCESS read-only
            STATUS mandatory
            DESCRIPTION
                "Number of Receiver Not Ready (RNR) frames received."
        ::= { cdx6500BRIChanStatsTableEntry 44 }

        cdx6500BRICStatsRNRFramesOut OBJECT-TYPE
            SYNTAX Counter
            ACCESS read-only
            STATUS mandatory
            DESCRIPTION
                "Number of Receiver Not Ready (RNR) frames sent."
        ::= { cdx6500BRIChanStatsTableEntry 45 }

        cdx6500BRICStatsSABMFramesIn OBJECT-TYPE
            SYNTAX Counter
            ACCESS read-only
            STATUS mandatory
            DESCRIPTION
                "Number of Set Asynchronous Balanced Mode (SABM) frames 
                 received."
        ::= { cdx6500BRIChanStatsTableEntry 46 }

        cdx6500BRICStatsSABMFramesOut OBJECT-TYPE
            SYNTAX Counter
            ACCESS read-only
            STATUS mandatory
            DESCRIPTION
                "Number of Set Asynchronous Balanced Mode (SABM) frames sent."
        ::= { cdx6500BRIChanStatsTableEntry 47 }

        cdx6500BRICStatsDMFramesIn OBJECT-TYPE
            SYNTAX Counter
            ACCESS read-only
            STATUS mandatory
            DESCRIPTION
                "Number of Disconnect Mode (DM) frames received."
        ::= { cdx6500BRIChanStatsTableEntry 48 }

        cdx6500BRICStatsDMFramesOut OBJECT-TYPE
            SYNTAX Counter
            ACCESS read-only
            STATUS mandatory
            DESCRIPTION
                "Number of Disconnect Mode (DM) frames sent."
        ::= { cdx6500BRIChanStatsTableEntry 49 }

        cdx6500BRICStatsRRFramesIn OBJECT-TYPE
            SYNTAX Counter
            ACCESS read-only
            STATUS mandatory
            DESCRIPTION
                "Number of Receiver Ready (RR) frames received."
        ::= { cdx6500BRIChanStatsTableEntry 50 }

        cdx6500BRICStatsRRFramesOut OBJECT-TYPE
            SYNTAX Counter
            ACCESS read-only
            STATUS mandatory
            DESCRIPTION
                "Number of Receiver Ready (RR) frames sent."
        ::= { cdx6500BRIChanStatsTableEntry 51 }

        cdx6500BRICStatsREJFramesIn OBJECT-TYPE
            SYNTAX Counter
            ACCESS read-only
            STATUS mandatory
            DESCRIPTION
                "Number of Reject (REJ) frames received."
        ::= { cdx6500BRIChanStatsTableEntry 52 }

        cdx6500BRICStatsREJFramesOut OBJECT-TYPE
            SYNTAX Counter
            ACCESS read-only
            STATUS mandatory
            DESCRIPTION
                "Number of Reject (REJ) frames sent."
        ::= { cdx6500BRIChanStatsTableEntry 53 }

        cdx6500BRICStatsDISCFramesIn OBJECT-TYPE
            SYNTAX Counter
            ACCESS read-only
            STATUS mandatory
            DESCRIPTION
                "Number of Disconnect (DISC) frames received."
        ::= { cdx6500BRIChanStatsTableEntry 54 }

        cdx6500BRICStatsDISCFramesOut OBJECT-TYPE
            SYNTAX Counter
            ACCESS read-only
            STATUS mandatory
            DESCRIPTION
                "Number of Disconnect (DISC) frames sent."
        ::= { cdx6500BRIChanStatsTableEntry 55 }

        cdx6500BRICStatsUAFramesIn OBJECT-TYPE
            SYNTAX Counter
            ACCESS read-only
            STATUS mandatory
            DESCRIPTION
                "Number of Unnumbered Acknowledgement (UA) frames received."
        ::= { cdx6500BRIChanStatsTableEntry 56 }

        cdx6500BRICStatsUAFramesOut OBJECT-TYPE
            SYNTAX Counter
            ACCESS read-only
            STATUS mandatory
            DESCRIPTION
                "Number of Unnumbered Acknowledgement (UA) frames sent."
        ::= { cdx6500BRIChanStatsTableEntry 57 }

        cdx6500BRICStatsFRMRFramesIn OBJECT-TYPE
            SYNTAX Counter
            ACCESS read-only
            STATUS mandatory
            DESCRIPTION
                "Number of Frame Reject (FRMR) frames received."
        ::= { cdx6500BRIChanStatsTableEntry 58 }

        cdx6500BRICStatsFRMRFramesOut OBJECT-TYPE
            SYNTAX Counter
            ACCESS read-only
            STATUS mandatory
            DESCRIPTION
                "Number of Frame Reject (FRMR) frames sent."
        ::= { cdx6500BRIChanStatsTableEntry 59 }

        cdx6500BRICStatsDataPktsIn OBJECT-TYPE
            SYNTAX Counter
            ACCESS read-only
            STATUS mandatory
            DESCRIPTION
                "Total Number of Data packets received."
        ::= { cdx6500BRIChanStatsTableEntry 60 }

        cdx6500BRICStatsDataPktsOut OBJECT-TYPE
            SYNTAX Counter
            ACCESS read-only
            STATUS mandatory
            DESCRIPTION
                "Total Number of Data packets sent."
        ::= { cdx6500BRIChanStatsTableEntry 61 }

        cdx6500BRICStatsRRPktsIn OBJECT-TYPE
            SYNTAX Counter
            ACCESS read-only
            STATUS mandatory
            DESCRIPTION
                "Total Number of Receiver Ready (RR) packets received."
        ::= { cdx6500BRIChanStatsTableEntry 62 }

        cdx6500BRICStatsRRPktsOut OBJECT-TYPE
            SYNTAX Counter
            ACCESS read-only
            STATUS mandatory
            DESCRIPTION
                "Total Number of Receiver Ready (RR) packets sent."
        ::= { cdx6500BRIChanStatsTableEntry 63 }

        cdx6500BRICStatsRNRPktsIn OBJECT-TYPE
            SYNTAX Counter
            ACCESS read-only
            STATUS mandatory
            DESCRIPTION
                "Total Number of Receiver Not Ready (RNR) packets received."
        ::= { cdx6500BRIChanStatsTableEntry 64 }

        cdx6500BRICStatsRNRPktsOut OBJECT-TYPE
            SYNTAX Counter
            ACCESS read-only
            STATUS mandatory
            DESCRIPTION
                "Total Number of Receiver Not Ready (RNR) packets sent."
        ::= { cdx6500BRIChanStatsTableEntry 65 }

        cdx6500BRICStatsRejPktsIn OBJECT-TYPE
            SYNTAX Counter
            ACCESS read-only
            STATUS mandatory
            DESCRIPTION
                "Total Number of Reject packets received."
        ::= { cdx6500BRIChanStatsTableEntry 66 }

        cdx6500BRICStatsRejPktsOut OBJECT-TYPE
            SYNTAX Counter
            ACCESS read-only
            STATUS mandatory
            DESCRIPTION
                "Total Number of Reject packets sent."
        ::= { cdx6500BRIChanStatsTableEntry 67 }

        cdx6500BRICStatsCallReqPktsIn OBJECT-TYPE
            SYNTAX Counter
            ACCESS read-only
            STATUS mandatory
            DESCRIPTION
                "Total Number of Call Request packets received."
        ::= { cdx6500BRIChanStatsTableEntry 68 }

        cdx6500BRICStatsCallReqPktsOut OBJECT-TYPE
            SYNTAX Counter
            ACCESS read-only
            STATUS mandatory
            DESCRIPTION
                "Total Number of Call Request packets sent."
        ::= { cdx6500BRIChanStatsTableEntry 69 }

        cdx6500BRICStatsCallAccPktsIn OBJECT-TYPE
            SYNTAX Counter
            ACCESS read-only
            STATUS mandatory
            DESCRIPTION
                "Total Number of Call Accept packets received."
        ::= { cdx6500BRIChanStatsTableEntry 70 }

        cdx6500BRICStatsCallAccPktsOut OBJECT-TYPE
            SYNTAX Counter
            ACCESS read-only
            STATUS mandatory
            DESCRIPTION
                "Total Number of Call Acceptt packets sent."
        ::= { cdx6500BRIChanStatsTableEntry 71 }

        cdx6500BRICStatsClrReqPktsIn OBJECT-TYPE
            SYNTAX Counter
            ACCESS read-only
            STATUS mandatory
            DESCRIPTION
                "Total Number of Clear Request packets received."
        ::= { cdx6500BRIChanStatsTableEntry 72 }

        cdx6500BRICStatsClrReqPktsOut OBJECT-TYPE
            SYNTAX Counter
            ACCESS read-only
            STATUS mandatory
            DESCRIPTION
                "Total Number of Clear Request packets sent."
        ::= { cdx6500BRIChanStatsTableEntry 73 }

        cdx6500BRICStatsClrConfPktsIn OBJECT-TYPE
            SYNTAX Counter
            ACCESS read-only
            STATUS mandatory
            DESCRIPTION
                "Total Number of Clear Confirmation packets received."
        ::= { cdx6500BRIChanStatsTableEntry 74 }

        cdx6500BRICStatsClrConfPktsOut OBJECT-TYPE
            SYNTAX Counter
            ACCESS read-only
            STATUS mandatory
            DESCRIPTION
                "Total Number of Clear Confirmation packets sent."
        ::= { cdx6500BRIChanStatsTableEntry 75 }

        cdx6500BRICStatsIntReqPktsIn OBJECT-TYPE
            SYNTAX Counter
            ACCESS read-only
            STATUS mandatory
            DESCRIPTION
                "Total Number of Interrupt Request packets received."
        ::= { cdx6500BRIChanStatsTableEntry 76 }

        cdx6500BRICStatsIntReqPktsOut OBJECT-TYPE
            SYNTAX Counter
            ACCESS read-only
            STATUS mandatory
            DESCRIPTION
                "Total Number of Interrupt Request packets sent."
        ::= { cdx6500BRIChanStatsTableEntry 77 }

        cdx6500BRICStatsIntConfPktsIn OBJECT-TYPE
            SYNTAX Counter
            ACCESS read-only
            STATUS mandatory
            DESCRIPTION
                "Total Number of Interrupt Confirmation packets received."
        ::= { cdx6500BRIChanStatsTableEntry 78 }

        cdx6500BRICStatsIntConfPktsOut OBJECT-TYPE
            SYNTAX Counter
            ACCESS read-only
            STATUS mandatory
            DESCRIPTION
                "Total Number of Interrupt Confirmation packets sent."
        ::= { cdx6500BRIChanStatsTableEntry 79 }

        cdx6500BRICStatsRstReqPktsIn OBJECT-TYPE
            SYNTAX Counter
            ACCESS read-only
            STATUS mandatory
            DESCRIPTION
                "Total Number of Reset Request packets received."
        ::= { cdx6500BRIChanStatsTableEntry 80 }

        cdx6500BRICStatsRstReqPktsOut OBJECT-TYPE
            SYNTAX Counter
            ACCESS read-only
            STATUS mandatory
            DESCRIPTION
                "Total Number of Reset Request packets sent."
        ::= { cdx6500BRIChanStatsTableEntry 81 }

        cdx6500BRICStatsRstConfPktsIn OBJECT-TYPE
            SYNTAX Counter
            ACCESS read-only
            STATUS mandatory
            DESCRIPTION
                "Total Number of Reset Confirmation packets received."
        ::= { cdx6500BRIChanStatsTableEntry 82 }

        cdx6500BRICStatsRstConfPktsOut OBJECT-TYPE
            SYNTAX Counter
            ACCESS read-only
            STATUS mandatory
            DESCRIPTION
                "Total Number of Reset Confirmation packets sent."
        ::= { cdx6500BRIChanStatsTableEntry 83 }

        cdx6500BRICStatsRestartReqPktsIn OBJECT-TYPE
            SYNTAX Counter
            ACCESS read-only
            STATUS mandatory
            DESCRIPTION
                "Total Number of Restart Request packets received."
        ::= { cdx6500BRIChanStatsTableEntry 84 }

        cdx6500BRICStatsRestartReqPktsOut OBJECT-TYPE
            SYNTAX Counter
            ACCESS read-only
            STATUS mandatory
            DESCRIPTION
                "Total Number of Restart Request packets sent."
        ::= { cdx6500BRIChanStatsTableEntry 85 }

        cdx6500BRICStatsRestartConfPktsIn OBJECT-TYPE
            SYNTAX Counter
            ACCESS read-only
            STATUS mandatory
            DESCRIPTION
                "Total Number of Restart Confirmation packets received."
        ::= { cdx6500BRIChanStatsTableEntry 86 }

        cdx6500BRICStatsRestartConfPktsOut OBJECT-TYPE
            SYNTAX Counter
            ACCESS read-only
            STATUS mandatory
            DESCRIPTION
                "Total Number of Restart Confirmation packets sent."
        ::= { cdx6500BRIChanStatsTableEntry 87 }

        cdx6500BRICStatsTEI OBJECT-TYPE
            SYNTAX INTEGER
            ACCESS read-only
            STATUS mandatory
            DESCRIPTION
                "Terminal Endpoint Identifier provided by the Network 
                 subscribing."
        ::= { cdx6500BRIChanStatsTableEntry 88 }

        cdx6500BRICStatsSAPI OBJECT-TYPE
            SYNTAX INTEGER
            ACCESS read-only
            STATUS mandatory
            DESCRIPTION
                "Service Access Point Identifier.
                 A value of 16 is reserved for Packet-mode communication on 
                 the D-channel using X.25 level 3."
        ::= { cdx6500BRIChanStatsTableEntry 89 }

        cdx6500BRICStatsNetworkType OBJECT-TYPE
            SYNTAX DisplayString
            ACCESS read-only
            STATUS mandatory
            DESCRIPTION
                "Specifies the X.25 Network Type:
                 Transpac, PSS, Datanet, Telenet, Unknown ."
        ::= { cdx6500BRIChanStatsTableEntry 90 }

        END
