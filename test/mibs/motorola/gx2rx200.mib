OMNI-gx2RX200-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Rx200
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"4" Jan 20, 2003
		   --DESCRIPTION
		   --			Added revision and description comment section

		--    OMNISTAR Return Path Receiver Module  MIB MODULE

	-- This MIB module defines information for management of HFC networks
		-- 
		-- The MIB module assumes that all generic (static) network element
		-- information is defined in a different module such as the HFC module
		-- The MIB consists of two groups:
		-- the device type descriptor subgroup and 
		-- gx2Rx200 Network Elements subgroup.
		-- The device type descriptor subgroup is used to define 
		-- parameters specific to gx2Rx200 device type.
		-- These parameters are common across all network elements
		-- from gx2Rx200 device type.
		--
		-- The gx2Rx200 Network Elements subgroup is
		-- a list of gx2Rx200 type elements in the
		-- current network topology with nominal
		-- and current parameter values for the
		-- individual network elements; the individual
		-- network elements are identified by  
		-- index from hfcCommonTable.
		-- That implies what hfcCommonTableIndex and
		-- gx2Rx200TableIndex are equal for each individual
		-- network element.
		-- This table is an extension of the hfcCommonTable
		-- for all elements of gx2Rx200 type.
		--
		-- Both groups are mandatory for management of gx2Rx200 devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2Rx200 Device Descriptor subgroup.

		-- The device type descriptor subgroup is used to define 
		-- parameters specific to gx2Rx200 device type.
		-- These parameters are common across all network elements
		-- from gx2Rx200 device type.


		gx2Rx200Descriptor OBJECT IDENTIFIER ::= {gx2Rx200 1}



--*****************************************************************************
		--              gx2Rx200 Table
		
		-- Contains a list of all gx2Rx200 type devices in
		-- the network. Each device is characterized with
		-- current network topology information, with nominal
		-- and current parameter values for the
		-- individual network elements;
		--
		-- The individual network elements indentified by  
		-- index from hfcCommonTable.
		-- That implies what hfcCommonTableIndex and
		-- gx2Rx200TableIndex are equal for each individual
		-- nettwork element.
		-- This table should be used as an extension of the hfcCommonTable
		-- for all elements of gx2Rx200 type.


	       gx2Rx200AnalogTable                    OBJECT-TYPE
			 SYNTAX             SEQUENCE OF Gx2Rx200AnalogEntry
			 ACCESS             not-accessible
			 STATUS             mandatory
			 DESCRIPTION
			 "This table contains gx2Rx200 specific parameters with
			  nominal and current values."
			 ::= { gx2Rx200 2 }


	       gx2Rx200AnalogEntry               OBJECT-TYPE
			 SYNTAX             Gx2Rx200AnalogEntry
			 ACCESS             not-accessible
			 STATUS             mandatory
			 DESCRIPTION
			 "This list contains digital product class and the
			  associated RF channel parameters and descriptions."
			 INDEX { rxgx2Rx200AnalogTableIndex }
			 ::= { gx2Rx200AnalogTable  1}

--***********************************************************************
	       gx2Rx200DigitalTable                    OBJECT-TYPE
			 SYNTAX             SEQUENCE OF Gx2Rx200DigitalEntry
			 ACCESS             not-accessible
			 STATUS             mandatory
			 DESCRIPTION
			 "This table contains gx2Rx200 specific parameters with
			  nominal and current values."
			 ::= { gx2Rx200 3 }

	       gx2Rx200DigitalEntry               OBJECT-TYPE
			 SYNTAX             Gx2Rx200DigitalEntry
			 ACCESS             not-accessible
			 STATUS             mandatory
			 DESCRIPTION
			 "This list contains digital product class and the
			  associated RF channel parameters and descriptions."
			 INDEX { rxgx2Rx200DigitalTableIndex }
			 ::= { gx2Rx200DigitalTable  2}

--***********************************************************************
	       gx2Rx200StatusTable                    OBJECT-TYPE
			 SYNTAX             SEQUENCE OF Gx2Rx200StatusEntry
			 ACCESS             not-accessible
			 STATUS             mandatory
			 DESCRIPTION
			 "This table contains gx2Rx200 specific parameters with
			  nominal and current values."
			 ::= { gx2Rx200 4 }

	       gx2Rx200StatusEntry               OBJECT-TYPE
			 SYNTAX             Gx2Rx200StatusEntry
			 ACCESS             not-accessible
			 STATUS             mandatory
			 DESCRIPTION
			 "This list contains digital product class and the
			  associated RF channel parameters and descriptions."
			 INDEX { rxgx2Rx200StatusTableIndex }
			 ::= { gx2Rx200StatusTable  3}

--***********************************************************************
	       gx2Rx200FactoryTable                    OBJECT-TYPE
			 SYNTAX             SEQUENCE OF Gx2Rx200FactoryEntry
			 ACCESS             not-accessible
			 STATUS             mandatory
			 DESCRIPTION
			 "This table contains gx2Rx200 specific parameters with
			  nominal and current values."
			 ::= { gx2Rx200 5 }

	       gx2Rx200FactoryEntry               OBJECT-TYPE
			 SYNTAX             Gx2Rx200FactoryEntry
			 ACCESS             not-accessible
			 STATUS             mandatory
			 DESCRIPTION
			 "This list contains digital product class and the
			  associated RF channel parameters and descriptions."
			 INDEX { rxgx2Rx200FactoryTableIndex }
			 ::= { gx2Rx200FactoryTable  4}

--***********************************************************************
	      Gx2Rx200AnalogEntry    ::= SEQUENCE  
	       {
		rxgx2Rx200AnalogTableIndex         INTEGER,   
		
		--           Analog Parameters

		rxlabelModTemp			DisplayString (SIZE (0..80)),
		rxuomModTemp				DisplayString (SIZE (0..80)),
		rxmajorHighModTemp			Float, 
		rxmajorLowModTemp			Float, 
		rxminorHighModTemp			Float,
		rxminorLowModTemp			Float, 
		rxcurrentValueModTemp		Float, 
		rxstateFlagModTemp			INTEGER,
		rxminValueModTemp			Float,
		rxmaxValueModTemp			Float,
		rxalarmStateModTemp			INTEGER,

		rxlabelFanCurrent			DisplayString (SIZE (0..80)),
		rxuomFanCurrent			DisplayString (SIZE (0..80)),
		rxmajorHighFanCurrent		Float, 
		rxmajorLowFanCurrent		Float, 
		rxminorHighFanCurrent		Float,
		rxminorLowFanCurrent		Float, 
		rxcurrentValueFanCurrent		Float, 
		rxstateFlagFanCurrent		INTEGER,
		rxminValueFanCurrent		Float,
		rxmaxValueFanCurrent 		Float,
		rxalarmStateFanCurrent		INTEGER,

		rxlabel12Volt				DisplayString (SIZE (0..80)),
		rxuom12Volt				DisplayString (SIZE (0..80)),
		rxmajorHigh12Volt			Float, 
		rxmajorLow12Volt			Float, 
		rxminorHigh12Volt			Float,
		rxminorLow12Volt			Float, 
		rxcurrentValue12Volt		Float, 
		rxstateFlag12Volt			INTEGER,
		rxminValue12Volt			Float,
		rxmaxValue12Volt			Float,
		rxalarmState12Volt			INTEGER,

		rxlabelOptPower			DisplayString (SIZE (0..80)),
		rxuomOptPower				DisplayString (SIZE (0..80)),
		rxmajorHighOptPower			Float, 
		rxmajorLowOptPower			Float, 
		rxminorHighOptPower			Float,
		rxminorLowOptPower			Float, 
		rxcurrentValueOptPower		Float, 
		rxstateFlagOptPower			INTEGER,
		rxminValueOptPower			Float,
		rxmaxValueOptPower 			Float,
		rxalarmStateOptPower		INTEGER
		}

		-- ****************  Digital Parameters ***********************
	      Gx2Rx200DigitalEntry    ::= SEQUENCE  
	       {
		rxgx2Rx200DigitalTableIndex         INTEGER,   

		rxlabelMode	 			DisplayString (SIZE (0..80)),
		rxvalueMode				INTEGER,
		rxenumMode				DisplayString (SIZE (0..80)),
		rxstateFlagMode     	    	INTEGER,

		rxlabelWavelength	 		DisplayString (SIZE (0..80)),
		rxvalueWavelength			INTEGER,
		rxenumWavelength			DisplayString (SIZE (0..80)),
		rxstateFlagWavelength         	INTEGER,

		rxlabelAttnSetting	 		DisplayString (SIZE (0..80)),
		rxvalueAttnSetting			INTEGER,
		rxenumAttnSetting			DisplayString (SIZE (0..80)),
		rxstateFlagAttnSetting        	INTEGER,

		rxlabelSwModeSetting		DisplayString (SIZE (0..80)),
		rxvalueSwModeSetting		INTEGER,
		rxenumSwModeSetting			DisplayString (SIZE (0..80)),
		rxstateFlagSwModeSetting     	INTEGER,

		rxlabelSwModeThreshold	 	DisplayString (SIZE (0..80)),
		rxvalueSwModeThreshold		INTEGER,
		rxenumSwModeThreshold		DisplayString (SIZE (0..80)),
		rxstateFlagSwModeThreshold     	INTEGER,

		rxlabelFactoryDefault		DisplayString (SIZE (0..80)),
		rxvalueFactoryDefault		INTEGER,
		rxenumFactoryDefault		DisplayString (SIZE (0..80)),
		rxstateFlagFactoryDefault   	INTEGER

		}
		-- ****************  Status Parameters ************************************
	      Gx2Rx200StatusEntry    ::= SEQUENCE  
	       {

		rxgx2Rx200StatusTableIndex         INTEGER,   
		rxlabelBoot				DisplayString (SIZE (0..80)),
		rxvalueBoot				INTEGER,
		rxstateflagBoot			INTEGER,
		
		rxlabelFlash				DisplayString (SIZE (0..80)),
		rxvalueFlash				INTEGER,
		rxstateflagFlash			INTEGER,

		rxlabelFactoryDataCRC 		DisplayString (SIZE (0..80)),
		rxvalueFactoryDataCRC		INTEGER,
		rxstateflagFactoryDataCRC		INTEGER,

		rxlabelAlarmDataCRC 		DisplayString (SIZE (0..80)),
		rxvalueAlarmDataCRC			INTEGER,
		rxstateflagAlarmDataCRC		INTEGER,

		rxlabelCalibrationDataCRC		DisplayString (SIZE (0..80)),
		rxvalueCalibrationDataCRC		INTEGER,
		rxstateflagCalibrationDataCRC	INTEGER,

		rxlabelThermalCompCRC		DisplayString (SIZE (0..80)),
		rxvalueThermalCompCRC		INTEGER,
		rxstateflagThermalCompCRC	INTEGER,

		rxlabelHW					DisplayString (SIZE (0..80)),
		rxvalueHW					INTEGER,
		rxstateflagHW				INTEGER,

		rxlabelOptSig				DisplayString (SIZE (0..80)),
		rxvalueOptSig				INTEGER,
		rxstateflagOptSig			INTEGER

}
		

		-- ****************  Factory Parameters *************************************
	      Gx2Rx200FactoryEntry    ::= SEQUENCE  
	       {
		rxgx2Rx200FactoryTableIndex         INTEGER,   
		rxbootControlByte  			INTEGER,
		rxbootStatusByte   			INTEGER,
		rxbank0CRC    			INTEGER,
		rxbank1CRC    			INTEGER,
		rxprgEEPROMByte    			INTEGER,
		rxfactoryCRC    			INTEGER,
		rxcalculateCRC    			INTEGER,
		rxhourMeter    			INTEGER,
		rxflashPrgCntA    			INTEGER,
		rxflashPrgCntB    			INTEGER,
		rxfwRev0	    			DisplayString (SIZE (0..80)),
		rxfwRev1	    			DisplayString (SIZE (0..80))
		}


        -- ************** Analog Parameters ****************************
		rxgx2Rx200AnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200AnalogEntry 1}

-- New Parameter

		rxlabelModTemp              OBJECT-TYPE
			   SYNTAX           DisplayString (SIZE (0..80))
			   ACCESS           read-only
			   STATUS           optional
			   DESCRIPTION
			   "The value of this object provides the label of the
			    Module Temperature Analog parameter."
			   ::= { gx2Rx200AnalogEntry 2}

		rxuomModTemp                OBJECT-TYPE
			   SYNTAX           DisplayString (SIZE (0..80))
			   ACCESS           read-only
			   STATUS           optional
			   DESCRIPTION
			   "The value of this object provides the Unit of Measure of the
			    Module Temperature Analog parameter."
			   ::= { gx2Rx200AnalogEntry 3}

		rxmajorHighModTemp          OBJECT-TYPE
			   SYNTAX           Float 
			   ACCESS           read-only
			   STATUS           mandatory
			   DESCRIPTION
			   "The value of this object provides the Major High alarm value
			          of the Module Temperature Analog parameter. This value is a floating 
			    point number that is represented as an IEEE 32 bit number."
			   ::= { gx2Rx200AnalogEntry 4}


		rxmajorLowModTemp           OBJECT-TYPE
			   SYNTAX           Float 
			   ACCESS           read-only
			   STATUS           mandatory
			   DESCRIPTION
			   "The value of this object provides the Major Low alarm value
			          of the Module Temperature Analog parameter. This value is a floating 
			    point number that is represented as an IEEE 32 bit number."
			   ::= { gx2Rx200AnalogEntry 5}

		rxminorHighModTemp          OBJECT-TYPE
			   SYNTAX           Float
			   ACCESS           read-only
			   STATUS           mandatory
			   DESCRIPTION
			   "The value of this object provides the Minor High alarm value
			          of the Module Temperature Analog parameter. This value is a floating 
			    point number that is represented as an IEEE 32 bit number."
			   ::= { gx2Rx200AnalogEntry 6}

		rxminorLowModTemp           OBJECT-TYPE
			   SYNTAX           Float 
			   ACCESS           read-only
			   STATUS           mandatory
			   DESCRIPTION
			   "The value of this object provides the Minor Low alarm value
			          of the Module Temperature Analog parameter. This value is a floating 
			    point number that is represented as an IEEE 32 bit number."
			   ::= { gx2Rx200AnalogEntry 7}

		rxcurrentValueModTemp       OBJECT-TYPE
			   SYNTAX           Float 
			   ACCESS           read-only
			   STATUS           mandatory
			   DESCRIPTION
			   "The value of this object provides the Current value
			          of the Module Temperature Analog parameter. This value is a floating 
			    point number that is represented as an IEEE 32 bit number."
			   ::= { gx2Rx200AnalogEntry 8}

		rxstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2Rx200AnalogEntry 9}

		rxminValueModTemp           OBJECT-TYPE
			   SYNTAX           Float
			   ACCESS           read-only
			   STATUS           mandatory
			   DESCRIPTION
			   "The value of this object provides the minimum value
			          of the Module Temperature Analog parameter. This value is a floating 
			    point number that is represented as an IEEE 32 bit number."
			   ::= { gx2Rx200AnalogEntry 10}

		rxmaxValueModTemp           OBJECT-TYPE
			   SYNTAX           Float
			   ACCESS           read-only
			   STATUS           mandatory
			   DESCRIPTION
			   "The value of this object provides the maximum value
			          of the Module Temperature Analog parameter. This value is a floating 
			    point number that is represented as an IEEE 32 bit number."
			   ::= { gx2Rx200AnalogEntry 11}

		rxalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Rx200AnalogEntry 12}
-- New Parameter

		rxlabelFanCurrent           OBJECT-TYPE
			   SYNTAX           DisplayString (SIZE (0..80))
			   ACCESS           read-only
			   STATUS           optional
			   DESCRIPTION
			   "The value of this object provides the label of the
			    Fan Current Analog parameter."
			   ::= { gx2Rx200AnalogEntry 13}

		rxuomFanCurrent             OBJECT-TYPE
			   SYNTAX           DisplayString (SIZE (0..80))
			   ACCESS           read-only
			   STATUS           optional
			   DESCRIPTION
			   "The value of this object provides the Unit of Measure of the
			    Fan Current Analog parameter."
			   ::= { gx2Rx200AnalogEntry 14}

		rxmajorHighFanCurrent       OBJECT-TYPE
			   SYNTAX           Float 
			   ACCESS           read-only
			   STATUS           mandatory
			   DESCRIPTION
			   "The value of this object provides the Major High alarm value
			          of the Fan Current Analog parameter. This value is a floating 
			    point number that is represented as an IEEE 32 bit number."
			   ::= { gx2Rx200AnalogEntry 15}


		rxmajorLowFanCurrent        OBJECT-TYPE
			   SYNTAX           Float 
			   ACCESS           read-only
			   STATUS           mandatory
			   DESCRIPTION
			   "The value of this object provides the Major Low alarm value
			          of the Fan Current Analog parameter. This value is a floating 
			    point number that is represented as an IEEE 32 bit number."
			   ::= { gx2Rx200AnalogEntry 16}

		rxminorHighFanCurrent       OBJECT-TYPE
			   SYNTAX           Float
			   ACCESS           read-only
			   STATUS           mandatory
			   DESCRIPTION
			   "The value of this object provides the Minor High alarm value
			          of the Fan Current Analog parameter. This value is a floating 
			    point number that is represented as an IEEE 32 bit number."
			   ::= { gx2Rx200AnalogEntry 17}

		rxminorLowFanCurrent        OBJECT-TYPE
			   SYNTAX           Float 
			   ACCESS           read-only
			   STATUS           mandatory
			   DESCRIPTION
			   "The value of this object provides the Minor Low alarm value
			          of the Fan Current Analog parameter. This value is a floating 
			    point number that is represented as an IEEE 32 bit number."
			   ::= { gx2Rx200AnalogEntry 18}

		rxcurrentValueFanCurrent    OBJECT-TYPE
			   SYNTAX           Float 
			   ACCESS           read-only
			   STATUS           mandatory
			   DESCRIPTION
			   "The value of this object provides the Current value
			          of the Fan Current Analog parameter. This value is a floating 
			    point number that is represented as an IEEE 32 bit number."
			   ::= { gx2Rx200AnalogEntry 19}

		rxstateFlagFanCurrent       OBJECT-TYPE
			   SYNTAX           INTEGER
								{
								hidden(1),
								read-only(2),
								updateable(3)
								}

			   ACCESS           read-only
			   STATUS           mandatory
			   DESCRIPTION
			   "The value of this object provides the state
			    of the Fan Current Analog parameter. (0-Hidden	
			          1-Read-Only, 2-Updateable)."
			   ::= { gx2Rx200AnalogEntry 20}

		rxminValueFanCurrent        OBJECT-TYPE
			   SYNTAX           Float
			   ACCESS           read-only
			   STATUS           mandatory
			   DESCRIPTION
			   "The value of this object provides the minimum value
			          of the Fan Current Analog parameter. This value is a floating 
			    point number that is represented as an IEEE 32 bit number."
			   ::= { gx2Rx200AnalogEntry 21}

		rxmaxValueFanCurrent        OBJECT-TYPE
			   SYNTAX           Float
			   ACCESS           read-only
			   STATUS           mandatory
			   DESCRIPTION
			   "The value of this object provides the maximum value
			          of the Fan Current Analog parameter. This value is a floating 
			    point number that is represented as an IEEE 32 bit number."
			   ::= { gx2Rx200AnalogEntry 22}

		rxalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Rx200AnalogEntry 23}
-- New Parameter

		rxlabel12Volt               OBJECT-TYPE
			   SYNTAX           DisplayString (SIZE (0..80))
			   ACCESS           read-only
			   STATUS           optional
			   DESCRIPTION
			   "The value of this object provides the label of the
			    12v Current Analog parameter."
			   ::= { gx2Rx200AnalogEntry 24}

		rxuom12Volt                 OBJECT-TYPE
			   SYNTAX           DisplayString (SIZE (0..80))
			   ACCESS           read-only
			   STATUS           optional
			   DESCRIPTION
			   "The value of this object provides the Unit of Measure of the
			    12v Current Analog parameter."
			   ::= { gx2Rx200AnalogEntry 25}

		rxmajorHigh12Volt           OBJECT-TYPE
			   SYNTAX           Float 
			   ACCESS           read-only
			   STATUS           mandatory
			   DESCRIPTION
			   "The value of this object provides the Major High alarm value
			          of the 12 Volt Current Analog parameter. This value is a floating 
			    point number that is represented as an IEEE 32 bit number."
			   ::= { gx2Rx200AnalogEntry 26}


		rxmajorLow12Volt            OBJECT-TYPE
			   SYNTAX           Float 
			   ACCESS           read-only
			   STATUS           mandatory
			   DESCRIPTION
			   "The value of this object provides the Major Low alarm value
			          of the 12 Volt Current Analog parameter. This value is a floating 
			    point number that is represented as an IEEE 32 bit number."
			   ::= { gx2Rx200AnalogEntry 27}

		rxminorHigh12Volt           OBJECT-TYPE
			   SYNTAX           Float
			   ACCESS           read-only
			   STATUS           mandatory
			   DESCRIPTION
			   "The value of this object provides the Minor High alarm value
			          of the 12 Volt Current Analog parameter. This value is a floating 
			    point number that is represented as an IEEE 32 bit number."
			   ::= { gx2Rx200AnalogEntry 28}

		rxminorLow12Volt            OBJECT-TYPE
			   SYNTAX           Float 
			   ACCESS           read-only
			   STATUS           mandatory
			   DESCRIPTION
			   "The value of this object provides the Minor Low alarm value
			          of the 12 Volt Current Analog parameter. This value is a floating 
			    point number that is represented as an IEEE 32 bit number."
			   ::= { gx2Rx200AnalogEntry 29}

		rxcurrentValue12Volt        OBJECT-TYPE
			   SYNTAX           Float 
			   ACCESS           read-only
			   STATUS           mandatory
			   DESCRIPTION
			   "The value of this object provides the Current value
			          of the 12 Volt Current Analog parameter. This value is a floating 
			    point number that is represented as an IEEE 32 bit number."
			   ::= { gx2Rx200AnalogEntry 30}

		rxstateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2Rx200AnalogEntry 31}

		rxminValue12Volt            OBJECT-TYPE
			   SYNTAX           Float
			   ACCESS           read-only
			   STATUS           mandatory
			   DESCRIPTION
			   "The value of this object provides the minimum value
			          of the 12 Volt Current Analog parameter. This value is a floating 
			    point number that is represented as an IEEE 32 bit number."
			   ::= { gx2Rx200AnalogEntry 32}

		rxmaxValue12Volt            OBJECT-TYPE
			   SYNTAX           Float
			   ACCESS           read-only
			   STATUS           mandatory
			   DESCRIPTION
			   "The value of this object provides the maximum value
			          of the 12 Volt Current Analog parameter. This value is a floating 
			    point number that is represented as an IEEE 32 bit number."
			   ::= { gx2Rx200AnalogEntry 33}

		rxalarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2Rx200AnalogEntry 34}

-- New Parameter

		rxlabelOptPower             OBJECT-TYPE
			   SYNTAX           DisplayString (SIZE (0..80))
			   ACCESS           read-only
			   STATUS           optional
			   DESCRIPTION
			   "The value of this object provides the label of the
			    Optical Power Analog parameter."
			   ::= { gx2Rx200AnalogEntry 35}

		rxuomOptPower               OBJECT-TYPE
			   SYNTAX           DisplayString (SIZE (0..80))
			   ACCESS           read-only
			   STATUS           optional
			   DESCRIPTION
			   "The value of this object provides the Unit of Measure of the
			    Optical Power Analog parameter."
			   ::= { gx2Rx200AnalogEntry 36}

		rxmajorHighOptPower         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx200AnalogEntry 37}


		rxmajorLowOptPower          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx200AnalogEntry 38}

		rxminorHighOptPower         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx200AnalogEntry 39}

		rxminorLowOptPower          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx200AnalogEntry 40}

		rxcurrentValueOptPower      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx200AnalogEntry 41}

		rxstateFlagOptPower         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx200AnalogEntry 42}

		rxminValueOptPower          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx200AnalogEntry 43}

		rxmaxValueOptPower          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx200AnalogEntry 44}

		rxalarmStateOptPower        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx200AnalogEntry 45}

-- ************************ Digital parameters **********************************
		rxgx2Rx200DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200DigitalEntry 1}

-- New parameter
		rxlabelMode	             	OBJECT-TYPE
			   SYNTAX         	DisplayString (SIZE (0..80))         
			   ACCESS           	read-only
			   STATUS           	optional
			   DESCRIPTION
			   "The value of this object provides the label of the
			    RX200's Mode  Digital parameter."
			   ::= { gx2Rx200DigitalEntry 2}

		rxenumMode	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200DigitalEntry 3}

		rxvalueMode	                OBJECT-TYPE
			   SYNTAX       		INTEGER
					    		{
							off(1),
							normal(2)
					    		}
			   ACCESS           	read-write
			   STATUS           	mandatory
			   DESCRIPTION
			   "The value of this object is the current value of the parameter."
			   ::= { gx2Rx200DigitalEntry 4}

		rxstateFlagMode	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200DigitalEntry 5}
-- New parameter
		rxlabelWavelength             	OBJECT-TYPE
			   SYNTAX         	DisplayString (SIZE (0..80))         
			   ACCESS           	read-only
			   STATUS           	optional
			   DESCRIPTION
			   "The value of this object provides the label of the
			    RX200's Wavelength  Digital parameter."
			   ::= { gx2Rx200DigitalEntry 6}

		rxenumWavelength               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200DigitalEntry 7}

		rxvalueWavelength               OBJECT-TYPE
			   SYNTAX       		INTEGER
					    		{
							nM1310(1),
							nM1550(2)
					    		}
			   ACCESS           	read-write
			   STATUS           	mandatory
			   DESCRIPTION
			   "The value of this object is the current value of the parameter."
			   ::= { gx2Rx200DigitalEntry 8}

		rxstateFlagWavelength	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200DigitalEntry 9}
-- New parameter
		rxlabelAttnSetting	          	OBJECT-TYPE
			   SYNTAX         	DisplayString (SIZE (0..80))         
			   ACCESS           	read-only
			   STATUS           	optional
			   DESCRIPTION
			   "The value of this object provides the label of the
			    RX200's AttnSetting  Digital parameter."
			   ::= { gx2Rx200DigitalEntry 10}

		rxenumAttnSetting	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200DigitalEntry 11}

		rxvalueAttnSetting	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx200DigitalEntry 12}

		rxstateFlagAttnSetting	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200DigitalEntry 13}
-- New parameter
		rxlabelSwModeSetting	     	OBJECT-TYPE
			   SYNTAX         	DisplayString (SIZE (0..80))         
			   ACCESS           	read-only
			   STATUS           	optional
			   DESCRIPTION
			   "The value of this object provides the label of the
			    RX200's Switch Mode Setting  Digital parameter."
			   ::= { gx2Rx200DigitalEntry 14}

		rxenumSwModeSetting	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx200DigitalEntry 15}

		rxvalueSwModeSetting	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx200DigitalEntry 16}

		rxstateFlagSwModeSetting	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200DigitalEntry 17}
-- New parameter
		rxlabelSwModeThreshold	      OBJECT-TYPE
			   SYNTAX         	DisplayString (SIZE (0..80))         
			   ACCESS           	read-only
			   STATUS           	optional
			   DESCRIPTION
			   "The value of this object provides the label of the
			    RX200's Switch Mode Threshold  Digital parameter."
			   ::= { gx2Rx200DigitalEntry 18}

		rxenumSwModeThreshold		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200DigitalEntry 19}

		rxvalueSwModeThreshold	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx200DigitalEntry 20}

		rxstateFlagSwModeThreshold	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200DigitalEntry 21}

-- New parameter
		rxlabelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2Rx200DigitalEntry 22}

		rxenumFactoryDefault          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200DigitalEntry 23}

		rxvalueFactoryDefault         	OBJECT-TYPE
			   SYNTAX       		INTEGER
					    		{
							off(1),
							on(2)
					    		}
			   ACCESS           	read-write
			   STATUS           	mandatory
			   DESCRIPTION
			   "The value of this object is the current value of the parameter."
			   ::= { gx2Rx200DigitalEntry 24}

		rxstateFlagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200DigitalEntry 25}


		--*********** STATUS *****************
		rxgx2Rx200StatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200StatusEntry 1}

--New Parameter
		rxlabelBoot               	OBJECT-TYPE
			   SYNTAX       		DisplayString (SIZE (0..80))         
			   ACCESS           	read-only
			   STATUS           	optional
			   DESCRIPTION
			   "The value of this object provides the label of the
			    Boot Status  Status parameter."
			   ::= { gx2Rx200StatusEntry 2}

		rxvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 3}

		rxstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry  4}


--New Parameter
		rxlabelFlash               	OBJECT-TYPE
			   SYNTAX       		DisplayString (SIZE (0..80))         
			   ACCESS           	read-only
			   STATUS           	optional
			   DESCRIPTION
			   "The value of this object provides the label of the
			    Flash Status  Status parameter."
			   ::= { gx2Rx200StatusEntry 5}

		rxvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 6}

		rxstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 7}


--New Parameter
		rxlabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Rx200StatusEntry 8}

		rxvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 9}

		rxstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 10}


--New Parameter
		rxlabelAlarmDataCRC             OBJECT-TYPE
			   SYNTAX       		DisplayString (SIZE (0..80))         
			   ACCESS           	read-only
			   STATUS           	optional
			   DESCRIPTION
			   "The value of this object provides the label of the
			    Alarm Data CRC Status parameter."
			   ::= { gx2Rx200StatusEntry 11}

		rxvalueAlarmDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 12}

		rxstateflagAlarmDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 13}


--New Parameter
		rxlabelCalibrationDataCRC       OBJECT-TYPE
			   SYNTAX       		DisplayString (SIZE (0..80))         
			   ACCESS           	read-only
			   STATUS           	optional
			   DESCRIPTION
			   "The value of this object provides the label of the
			    Calibration Data CRC Status parameter."
			   ::= { gx2Rx200StatusEntry 14}

		rxvalueCalibrationDataCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 15}

		rxstateflagCalibrationDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 16}


--New Parameter


		rxlabelThermalCompCRC       OBJECT-TYPE
			   SYNTAX       		DisplayString (SIZE (0..80))         
			   ACCESS           	read-only
			   STATUS           	optional
			   DESCRIPTION
			   "The value of this object provides the label of the
			    Calibration Data CRC Status parameter."
			   ::= { gx2Rx200StatusEntry 17}

		rxvalueThermalCompCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 18}

		rxstateflagThermalCompCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 19}


--New Parameter
		rxlabelHW               	      OBJECT-TYPE
			   SYNTAX       		DisplayString (SIZE (0..80))         
			   ACCESS           	read-only
			   STATUS           	optional
			   DESCRIPTION
			   "The value of this object provides the label of the
			    Hardware Status parameter."
			   ::= { gx2Rx200StatusEntry 20}

		rxvalueHW              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 21}

		rxstateflagHW     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 22}


--New Parameter
		rxlabelOptSig               	      OBJECT-TYPE
			   SYNTAX       		DisplayString (SIZE (0..80))         
			   ACCESS           	read-only
			   STATUS           	optional
			   DESCRIPTION
			   "The value of this object provides the label of the
			    Optical Signal Status parameter."
			   ::= { gx2Rx200StatusEntry 23}

		rxvalueOptSig              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200StatusEntry 24}

		rxstateflagOptSig     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200StatusEntry 25}

            -- ************ FACTORY DATA ****************
		rxgx2Rx200FactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200FactoryEntry 1}

		rxbootControlByte          	OBJECT-TYPE
			   SYNTAX       		INTEGER
			   ACCESS           	read-only
			   STATUS           	mandatory
			   DESCRIPTION
			   "The value of this object indicates which bank the firmware
			    is currently being boot from."
			   ::= { gx2Rx200FactoryEntry 2}

		rxbootStatusByte          	OBJECT-TYPE
			   SYNTAX       		INTEGER
			   ACCESS           	read-only
			   STATUS           	mandatory
			   DESCRIPTION
			   "This object indicates the status of the last boot"
			   ::= { gx2Rx200FactoryEntry 3}

		rxbank0CRC          		OBJECT-TYPE
			   SYNTAX       		INTEGER
			   ACCESS           	read-only
			   STATUS           	mandatory
			   DESCRIPTION
			   "This object provides the CRC code of bank 0."
			   ::= { gx2Rx200FactoryEntry 4}

		rxbank1CRC          		OBJECT-TYPE
			   SYNTAX       		INTEGER
			   ACCESS           	read-only
			   STATUS           	mandatory
			   DESCRIPTION
			   "This object provides the CRC code of bank 1."
			   ::= { gx2Rx200FactoryEntry 5}

		rxprgEEPROMByte          		OBJECT-TYPE
			   SYNTAX       		INTEGER
			   ACCESS           	read-only
			   STATUS           	mandatory
			   DESCRIPTION
			   "This object indicates if the EEPROM has been programmed"
			   ::= { gx2Rx200FactoryEntry 6}

		rxfactoryCRC          		OBJECT-TYPE
			   SYNTAX       		INTEGER
			   ACCESS           	read-only
			   STATUS           	mandatory
			   DESCRIPTION
			   "This object provides the CRC code for the Factory data."
			   ::= { gx2Rx200FactoryEntry 7}

		rxcalculateCRC          		OBJECT-TYPE
			   SYNTAX       		INTEGER
					    		{
							factory(1),
							calibration(2),
							alarm(3),
							tempComp(4)
					    		}
			   ACCESS           	read-only
			   STATUS           	mandatory
			   DESCRIPTION
			   "This object indicates which of the Emnums will have the CRC calculated."
			   ::= { gx2Rx200FactoryEntry 8}

		rxhourMeter          		OBJECT-TYPE
			   SYNTAX       		INTEGER
			   ACCESS           	read-only
			   STATUS           	mandatory
			   DESCRIPTION
			   "This object provides the hour meter reading of the module."
			   ::= { gx2Rx200FactoryEntry 9}

		rxflashPrgCntA          		OBJECT-TYPE
			   SYNTAX       		INTEGER
			   ACCESS           	read-only
			   STATUS           	mandatory
			   DESCRIPTION
			   "This object provides the number of times the flash has been 
                      programmed on side A."
			   ::= { gx2Rx200FactoryEntry 10}

		rxflashPrgCntB          		OBJECT-TYPE
			   SYNTAX       		INTEGER
			   ACCESS           	read-only
			   STATUS           	mandatory
			   DESCRIPTION
			   "This object provides the number of times the flash has been 
                      programmed on side B."
			   ::= { gx2Rx200FactoryEntry 11}

		rxfwRev0     		     		OBJECT-TYPE
			   SYNTAX       		DisplayString (SIZE (0..80))
			   ACCESS           	read-only
			   STATUS           	mandatory
			   DESCRIPTION
			   "This object provides the Revision of the firmware stores in bank 0."
			   ::= { gx2Rx200FactoryEntry 12}

		rxfwRev1     		     		OBJECT-TYPE
			   SYNTAX       		DisplayString (SIZE (0..80))
			   ACCESS           	read-only
			   STATUS           	mandatory
			   DESCRIPTION
			   "This object provides the Revision of the firmware stores in bank 1."
			   ::= { gx2Rx200FactoryEntry 13}


-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                              RX200 Module traps
-- **************************************************************************
   trapRX200ConfigChangeInteger TRAP-TYPE
       ENTERPRISE gx2Rx200
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapRX200ConfigChangeDisplayString TRAP-TYPE
       ENTERPRISE gx2Rx200
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
  
  trapRX200OpticalPowerAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Laser Modules Optical Power parameter 
	 goes out of range.
	 trapAdditionalInfoInteger variable contains current reading of 
	 the this parameter."
  ::= 3

  trapRX200ModuleTemperatureAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RX200 Modules Temperature goes out of range.
	 trapAdditionalInfoInteger variable contains current reading of 
	 the this parameter."
  ::= 4

  trapRX200FanCurrentAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RX200 Modules Fan Currrent parameter 
	 goes out of range. trapAdditionalInfoInteger variable contains current reading of 
	 the this parameter."
  ::= 5

  trapRX200Plus12CurrentAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RX200 Modules positive 12 volt current parameter 
	 goes out of range. trapAdditionalInfoInteger variable contains current reading of 
	 the this parameter."
  ::= 6

  trapRX200Boot0Alarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RX200 Modules Bank 0 Boot sequence has detected an error.
       trapAdditionalInfoInteger variable contains current reading of 
	 the this parameter."
  ::= 7

  trapRX200Boot1Alarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RX200 Modules Bank 1 Boot sequence has detected an error.
       trapAdditionalInfoInteger variable contains current reading of 
	 the this parameter."
  ::= 8

  trapRX200FlashAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the RX200 Modules boot or flash programming sequence has 
       detected a Flash error. trapAdditionalInfoInteger variable contains current reading of 
	 the this parameter."
  ::= 9

  trapRX200AlarmDataCRCAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RX200 Module detects an error calculating the alarm limit CRC.
       trapAdditionalInfoInteger variable contains current reading of the this parameter."
  ::= 10

  trapRX200FactoryDataCRCAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RX200 Module detects an error calculating the Factory data CRC.
       trapAdditionalInfoInteger variable contains current reading of the this parameter."
  ::= 11

  trapRX200CalDataCRCAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RX200 Module detects an error calculating the Calibration data CRC.
       trapAdditionalInfoInteger variable contains current reading of the this parameter."
  ::= 12

  trapRX200DefaultAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RX200 Module is reset to it's factory default state.
       trapAdditionalInfoInteger variable contains current reading of the this parameter."
  ::= 13

  trapRX200ModeAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RX200 Modules mode is changed from normal to off or off to normal.
       trapAdditionalInfoInteger variable contains current reading of the this parameter."
  ::= 14

  trapRX200OutputSwitchedAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the RX200 Module's output to the RF Switch Module changes state 
       from good to bad or bad to good. trapAdditionalInfoInteger variable contains current reading 
       of the this parameter."
  ::= 15

  trapRX200SideStatusAlarm TRAP-TYPE
	ENTERPRISE gx2Rx200
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when one of the RX200 Module's outputs are turned on or off."
  ::= 16


  END
