-- Version 1.6, modified 06/01/98

        X25-OPT-MIB DEFINITIONS ::= BEGIN

        IMPORTS
            Counter, Gauge
                FROM RFC1155-SMI

            OBJECT-TYPE
                FROM RFC-1212;

        -- Codex MIB Group definitions

                      codex OBJECT IDENTIFIER ::= { enterprises 449 }
         cdxProductSpecific OBJECT IDENTIFIER ::= { codex 2 }
                  cdx6500 OBJECT IDENTIFIER ::= { cdxProductSpecific 1 }

      cdx6500Configuration  OBJECT IDENTIFIER ::= { cdx6500 2 }
    cdx6500CfgProtocolGroup OBJECT IDENTIFIER ::= { cdx6500Configuration 1 }
     cdx6500CfgGeneralGroup OBJECT IDENTIFIER ::= { cdx6500Configuration 2 }
cdx6500PCTPortProtocolGroup OBJECT IDENTIFIER ::= { cdx6500CfgProtocolGroup 1 }

        cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

          cdx6500Controls OBJECT IDENTIFIER ::= { cdx6500 4 }

        -- Textual Conventions

        DisplayString ::= OCTET STRING
        -- This data type is used to model textual information taken
        -- from the NVT ASCII character set.  By convention, objects
        -- with this syntax are declared as having SIZE (0..255)


        Counter16 ::= INTEGER (0..65535)
        -- X.25 Port Objects

        -- The 6500 X.25 Port Configuration Sub-group
        -- This sub-group belongs to the 6500 Port Protocol Configuration
        -- sub-group. It holds configuration parameters peculiar to the 6500
        -- implementation of the X.25 protocol
  
        cdx6500PPCTX25PortTable OBJECT-TYPE
            SYNTAX SEQUENCE OF Cdx6500PPCTX25PortEntry
            ACCESS not-accessible
            STATUS mandatory
            DESCRIPTION
                "A table of X.25 Port configuration entries."
        ::= { cdx6500PCTPortProtocolGroup 2 }

        cdx6500PPCTX25PortEntry OBJECT-TYPE
            SYNTAX Cdx6500PPCTX25PortEntry
            ACCESS not-accessible
            STATUS mandatory
            DESCRIPTION
                "An X.25 Configuration Table entry. Each entry
                 contains the configuration parameters for a single
                 X.25 port."
            INDEX { cdx6500X25CfgPortNumber }
        ::= { cdx6500PPCTX25PortTable 1 }

        Cdx6500PPCTX25PortEntry ::=
            SEQUENCE {
                cdx6500X25CfgPortNumber
                    INTEGER,
                cdx6500X25CfgConnType
                    INTEGER,
                cdx6500X25CfgPortCont
                    DisplayString,
                cdx6500X25CfgClockSource
                    INTEGER,
                cdx6500X25CfgClockSpeed
                    INTEGER,
                cdx6500X25CfgAdmnInterfaceMode
                    INTEGER,
                cdx6500X25CfgAdmnNumberPVCs
                    INTEGER,
                cdx6500X25CfgStartPVCChanNum
                    INTEGER,
                cdx6500X25CfgNumberSVCs
                    INTEGER,
                cdx6500X25CfgStartSVCChanNum
                    INTEGER,
                cdx6500X25CfgInitFrame
                    DisplayString,
                cdx6500X25CfgT1RetryTimer
                    INTEGER,
                cdx6500X25CfgT4PollTimer
                    INTEGER,
                cdx6500X25CfgN2TransTries
                    INTEGER,
                cdx6500X25CfgFrameSeqCounting
                    INTEGER,
                cdx6500X25CfgKFrameWindow
                    INTEGER,
                cdx6500X25CfgAdmnPacketSequencing
                    INTEGER,
                cdx6500X25CfgWPacketWindow
                    INTEGER,
                cdx6500X25CfgPPacketSize
                    INTEGER,
                cdx6500X25CfgMaxNegotPacketSize
                    INTEGER,
                cdx6500X25CfgDataQueueUpper
                    INTEGER,
                cdx6500X25CfgDataQueueLower
                    INTEGER,
                cdx6500X25CfgAdmnRestartTimer
                    INTEGER,
                cdx6500X25CfgAdmnResetTimer
                    INTEGER,
                cdx6500X25CfgAdmnCallTimer
                    INTEGER,
                cdx6500X25CfgAdmnClearTimer
                    INTEGER,
                cdx6500X25CfgOutDelFacilities
                    DisplayString,
                cdx6500X25CfgOutAddFacilities
                    DisplayString,
                cdx6500X25CfgOutBarFacilities
                    DisplayString,
                cdx6500X25CfgInBarFacilities
                    DisplayString,
                cdx6500X25CfgOptions
                    DisplayString,
                cdx6500X25CfgNumRoutDigits
                    INTEGER,
                cdx6500X25CfgPortDigitsToStrip
                    INTEGER,
                cdx6500X25CfgInDigitsToStrip
                    INTEGER,
                cdx6500X25CfgRestrictConn
                    DisplayString,
                cdx6500X25CfgPortAddress
                    DisplayString,
                cdx6500X25CfgCUGMember
                    DisplayString,
                cdx6500X25CfgBillRec
                    INTEGER,
                cdx6500X25CfgSubAddrSize
                    INTEGER,
                cdx6500X25CfgIdleDiscTimer
                    INTEGER,
                cdx6500X25CfgCallSecurity
                    INTEGER,
                cdx6500X25CfgProtectLevel
                    INTEGER,
                cdx6500X25CfgReconnTimeout
                    INTEGER,
                cdx6500X25CfgReconnTriesLimit
                    INTEGER,
                cdx6500X25CfgFacilSubscripCont
                    DisplayString,
                cdx6500X25CfgAlarmPriority
                    INTEGER,
                cdx6500X25CfgAddrTrans
                    DisplayString
                }

        cdx6500X25CfgPortNumber OBJECT-TYPE
            SYNTAX INTEGER (1..255)
            ACCESS read-only
            STATUS mandatory
            DESCRIPTION
                "Port number for this X.25 port."
        ::= { cdx6500PPCTX25PortEntry 1 }

        cdx6500X25CfgConnType OBJECT-TYPE
            SYNTAX INTEGER {
                    simp  (1),
                    dtr   (2),
                    dtrd  (3),
                    emri  (4),
                    emdc  (5),
                    dimo  (6),
                    dimoa (7),
                    dimob (8),
                    dimov (11),
                    simpv (12),
                    simpb (21)
                    }
            ACCESS read-only
            STATUS mandatory
            DESCRIPTION
                "Specify the control signal handshake and clocking
                 required for a connection to be made to this port:
                 simp  - simple, no control signals required.
                 dtr   - dedicated, require the data terminal ready
                         signal (DTR).
                 dtrd  - same as DTR, except data set ready (DSR)
                         drops between calls.
                 dimo  - port handshakes with attached dial modem
                 dimoa - same as DIMO except DSR never raised on
                         incoming call from modem.
                 dimob - same as DIMO except DSR follows DTR on
                         incoming call from modem.
                 dimov - port handshakes with attached V.25 bis
                         dial modem.
                 emri  - port emulates a dial modem with ring
                         indicator (RI).
                 emdc  - port emulates a dial modem with data carrier
                         detect (DCD).
                 simpv - SIMP/DIMOv, modem will switch from Leased
                         to Dial-only mode when leased line goes down
                         (used with Link Backup only).
                 simpb - simple, no control signals required for data 
                         transmission and reception. By default output 
                         leads will be low."
        ::= { cdx6500PPCTX25PortEntry 2 }

        cdx6500X25CfgPortCont OBJECT-TYPE
            SYNTAX DisplayString (SIZE(2..7))
            ACCESS read-only
            STATUS mandatory
            DESCRIPTION
                "Specify any of the following port control options:
                 NONE  - no option specified.
                 MB    - raise Pin 22 when the port becomes disabled."
        ::= { cdx6500PPCTX25PortEntry 3 }

        cdx6500X25CfgClockSource OBJECT-TYPE
            SYNTAX INTEGER {
                    int    (1),
                    ext    (2),
                    extint (3),
                    extlp  (4)
                    }
            ACCESS read-only
            STATUS mandatory
            DESCRIPTION
                "int    - internal clock source.
                 ext    - external clock source.
                 extint - internal receive and external transmit 
                          clock source (DCE only).
                 extlp  - external receive and loopback transmit 
                          clock source (DTE only). extlp must be 
                          configured in conjunction with extint."
        ::= { cdx6500PPCTX25PortEntry 4 }

        cdx6500X25CfgClockSpeed OBJECT-TYPE
            SYNTAX INTEGER (1200..384000)
            ACCESS read-only
            STATUS mandatory
            DESCRIPTION
                 "This is the speed of the port in bits per second, when
                  using internal clocking.  The highest available speed
                  is dependant on the card type, and on the interface type.
                  See the 6500 Series Configuration and Administration
                  Manual for proper values."
        ::= { cdx6500PPCTX25PortEntry 5 }

        cdx6500X25CfgAdmnInterfaceMode OBJECT-TYPE
            SYNTAX INTEGER {
                    dte       (1),
                    dce       (2),
                    negotiate (3)
                    }
            ACCESS read-only
            STATUS mandatory
            DESCRIPTION
                "The logical link address must be set to complementary 
                 values in devices at each end of the link:
                 dte       - link to have logical DTE address (A).
                 dce       - link to have logical DCE address (B).
                 negotiate - link ends will negotiate which 
                             end is DCE address (B). This option is available
                             only if the correct CSK is enabled."
        ::= { cdx6500PPCTX25PortEntry 6 }

        cdx6500X25CfgAdmnNumberPVCs OBJECT-TYPE
            SYNTAX INTEGER (0..128)
            ACCESS read-only
            STATUS mandatory
            DESCRIPTION
                "Number of logical channels used for Permanent Virtual
                 Circuits. The total number of PVC and SVC channels on
                 a link should be kept as small as possible and consistent
                 with needs. PVC connections must be configured in the
                 PVC Table."
        ::= { cdx6500PPCTX25PortEntry 7 }

        cdx6500X25CfgStartPVCChanNum OBJECT-TYPE
            SYNTAX INTEGER (0..4095)
            ACCESS read-only
            STATUS mandatory
            DESCRIPTION
                "This is the starting logical channel number for the
                 Permanent Virtual Circuits on this link. Not used
                 if the number of PVCs = 0."
        ::= { cdx6500PPCTX25PortEntry 8 }

        cdx6500X25CfgNumberSVCs OBJECT-TYPE
            SYNTAX INTEGER (0..512)
            ACCESS read-only
            STATUS mandatory
            DESCRIPTION
                "Number of logical channels used in Switched Virtual
                 Circuits. The total number of PVC and SVC channels
                 on a link should be kept as small as possible and
                 consistent with needs."
        ::= { cdx6500PPCTX25PortEntry 9 }


        cdx6500X25CfgStartSVCChanNum OBJECT-TYPE
            SYNTAX INTEGER (0..4095)
            ACCESS read-only
            STATUS mandatory
            DESCRIPTION
                "This is the starting logical channel number for the
                 Switched Virtual Circuits on this link. Not used if
                 the number of SVCs = 0."
        ::= { cdx6500PPCTX25PortEntry 10 }

        cdx6500X25CfgInitFrame OBJECT-TYPE
            SYNTAX INTEGER {
                    sabm (1),
                    disc (2),
                    none (3)
                    }
            ACCESS read-only
            STATUS mandatory
            DESCRIPTION
                "Specify the initial frame required by other end for link
                 startup:
                 none - do nothing (other end initiates link-up).
                 sabm - send SABM.
                 disc - send DISC, then SABM."
        ::= { cdx6500PPCTX25PortEntry 11 }

        cdx6500X25CfgT1RetryTimer OBJECT-TYPE
            SYNTAX INTEGER (1..254)
            ACCESS read-only
            STATUS mandatory
            DESCRIPTION
                "T1 link retry timer value in tenths of a second
                 (e.g. 30 = 3.0 seconds)."
        ::= { cdx6500PPCTX25PortEntry 12 }

        cdx6500X25CfgT4PollTimer OBJECT-TYPE
            SYNTAX INTEGER (0..255)
            ACCESS read-only
            STATUS mandatory
            DESCRIPTION
                "This sets the time an idle link is probed for assurance
                 of connection to the remote device. 
                 0 - disable the timer
                 X - X is in tenths of a second (e.g. 40 = 4.0 seconds)
                 and must be set greater than T1."
        ::= { cdx6500PPCTX25PortEntry 13 }

        cdx6500X25CfgN2TransTries OBJECT-TYPE
            SYNTAX INTEGER (1..20) 
            ACCESS read-only
            STATUS mandatory
            DESCRIPTION
                "The maximum number of attempts allowed to complete a
                 transmission."
        ::= { cdx6500PPCTX25PortEntry 14 }

        cdx6500X25CfgFrameSeqCounting OBJECT-TYPE
            SYNTAX INTEGER {
                    norm (1),
                    ext  (2)
                    }
            ACCESS read-only
            STATUS mandatory
            DESCRIPTION
                "Port uses normal or extended frame sequence numbering
                 norm - normal sequence counting (Modulo 8).
                 ext  - extended sequencing (Modulo 128)."
        ::= { cdx6500PPCTX25PortEntry 15 }

        cdx6500X25CfgKFrameWindow OBJECT-TYPE
            SYNTAX INTEGER (1..15)
            ACCESS read-only
            STATUS mandatory
            DESCRIPTION
                "Frame level window size must be set to the same value in
                 devices at each end of the link."
        ::= { cdx6500PPCTX25PortEntry 16 }

        cdx6500X25CfgAdmnPacketSequencing OBJECT-TYPE
            SYNTAX INTEGER {
                    norm (1),
                    ext  (2)
                    }
            ACCESS read-only
            STATUS mandatory
            DESCRIPTION
                "Port uses normal or extended packet level sequence
                 numbers :
                 norm - normal sequencing (Modulo 8).
                 ext  - extended sequencing (Modulo 128).
                 The value must be the same in devices at each end of the
                 link."
        ::= { cdx6500PPCTX25PortEntry 17 }

        cdx6500X25CfgWPacketWindow OBJECT-TYPE
            SYNTAX INTEGER (1..15)
            ACCESS read-only
            STATUS mandatory
            DESCRIPTION
                "Packet level window size must be set to the same value in
                 devices at each end of the link."
        ::= { cdx6500PPCTX25PortEntry 18 }

        cdx6500X25CfgPPacketSize OBJECT-TYPE
            SYNTAX INTEGER {
                    bytes128  (7),
                    bytes256  (8),
                    bytes512  (9),
                    bytes1024 (10)
                    }
            ACCESS read-only
            STATUS mandatory
            DESCRIPTION
                "This is the maximum packet size used on X.25 links. For
                 proper operation, the size must be the same in devices
                 at each end of the link."
        ::= { cdx6500PPCTX25PortEntry 19 }

        cdx6500X25CfgMaxNegotPacketSize OBJECT-TYPE
            SYNTAX INTEGER {
                    bytes128  (7),
                    bytes256  (8),
                    bytes512  (9),
                    bytes1024 (10)
                    }
            ACCESS read-only
            STATUS mandatory
            DESCRIPTION
                "This is the maximum negotiated packet size allowed for
                 inbound and outbound calls on this X.25 link."
        ::= { cdx6500PPCTX25PortEntry 20 }

        cdx6500X25CfgDataQueueUpper OBJECT-TYPE
            SYNTAX INTEGER (5..15)
            ACCESS read-only
            STATUS mandatory
            DESCRIPTION
                "This is the maximum number of data packets a channel on
                 this port will queue for transmission before invoking
                 flow control to the attached channel"
        ::= { cdx6500PPCTX25PortEntry 21 }

        cdx6500X25CfgDataQueueLower OBJECT-TYPE
            SYNTAX INTEGER (0..14)
            ACCESS read-only
            STATUS mandatory
            DESCRIPTION
                "This is the number of data packets a channel on this port
                 will have queued for transmission when it releases flow
                 control to the attached channel"
        ::= { cdx6500PPCTX25PortEntry 22 }

        cdx6500X25CfgAdmnRestartTimer OBJECT-TYPE
            SYNTAX INTEGER (5..255)
            ACCESS read-only
            STATUS mandatory
            DESCRIPTION
                "Restart-Request timeout timer in seconds. If timer
                 expires, request is sent again."
        ::= { cdx6500PPCTX25PortEntry 23 }

        cdx6500X25CfgAdmnResetTimer OBJECT-TYPE
            SYNTAX INTEGER (5..180)
            ACCESS read-only
            STATUS mandatory
            DESCRIPTION
                "Reset-Request timeout timer in seconds. If timer expires,
                 request is sent again."
        ::= { cdx6500PPCTX25PortEntry 24 }

        cdx6500X25CfgAdmnCallTimer OBJECT-TYPE
            SYNTAX INTEGER (5..255)
            ACCESS read-only
            STATUS mandatory
            DESCRIPTION
                "Call-Request timeout timer in seconds. If timer expires,
                 call is cleared."
        ::= { cdx6500PPCTX25PortEntry 25 }

        cdx6500X25CfgAdmnClearTimer OBJECT-TYPE
            SYNTAX INTEGER (5..255)
            ACCESS read-only
            STATUS mandatory
            DESCRIPTION
                "Clear-Request timeout timer in seconds. If timer expires,
                 request is sent again."
        ::= { cdx6500PPCTX25PortEntry 26 }

        cdx6500X25CfgOutDelFacilities OBJECT-TYPE
            SYNTAX DisplayString (SIZE(3..17))
            ACCESS read-only
            STATUS mandatory
            DESCRIPTION
                "Specify facilities deleted from an outbound call before
                 it is forwarded: 
                 NONE - no facilities deleted.
                 THRO - delete throughput class negotiation.
                 NUI  - delete network user identification.
                 CUG  - delete closed user group.
                 Any combination of above specified by summing
                 (e.g. THRO+NUI. . .)."
        ::= { cdx6500PPCTX25PortEntry 27 }

        cdx6500X25CfgOutAddFacilities OBJECT-TYPE
            SYNTAX DisplayString (SIZE(3..18))
            ACCESS read-only
            STATUS mandatory
            DESCRIPTION
                "Specify facilities added to an outbound call before it is
                 forwarded:
                 NONE - no facilities added.
                 REV  - add reverse charging.
                 PACK - add packet size negotiation.
                 WIND - add window size negotiation.
                 Any combination of above specified by summing
                 (e.g. PACK+WIND+. . .)."
        ::= { cdx6500PPCTX25PortEntry 28 }

        cdx6500X25CfgOutBarFacilities OBJECT-TYPE
            SYNTAX DisplayString (SIZE(3..24))
            ACCESS read-only
            STATUS mandatory
            DESCRIPTION
                "Specify facilities which, if present in an outbound call
                 will be blocked by the port:
                 NONE  - no facility blocked.
                 REV   - bar reverse charging.
                 FAST  - bar fast select.
                 BCUG  - bar Bilateral Closed User Group.
                 DGRAM - bar datagram.
                 Any combination of above specified by summing
                 (e.g. REV+FAST)."
        ::= { cdx6500PPCTX25PortEntry 29 }

        cdx6500X25CfgInBarFacilities OBJECT-TYPE
            SYNTAX DisplayString (SIZE(3..19))
            ACCESS read-only
            STATUS mandatory
            DESCRIPTION
                "Specify facilities which, if present in an inbound call,
                 will be blocked by the port:
                 NONE  - no facility blocked.
                 BCUG  - bar Bilateral Closed User Group.
                 DGRAM - bar datagram.
                 REV   - bar Reverse Charging.
                 Any combination of above specified by summing
                 (e.g. DGRAM+BCUG)."
        ::= { cdx6500PPCTX25PortEntry 30 }

        cdx6500X25CfgOptions OBJECT-TYPE
            SYNTAX DisplayString (SIZE(3..107))
            ACCESS read-only
            STATUS mandatory
            DESCRIPTION
                "Select options on this X.25 port as follows:
                 NONE  - no option specified.
                 1980  - use X.25 1980.
                 NUI   - perform network user identification validation check.
                 PDN   - connected to Public Data Network.
                 CUD   - use call user data subaddressing.
                 IBAR  - bar all calls coming in from X.25 port user.
                 OBAR  - bar all calls going out to X.25 port user.
                 CBCK  - allow routing inbound calls back out this port.
                 CUG   - check closed user group; otherwise, CUG passes
                         transparently.
                 CAUSE - pass cause, diagnostic, code in outbound
                         packets.
                 HOLD  - hold calls over link restart.
                 NRST  - do not send restart packet on link-up.
                 BKUP  - this is a backup port to be activated if other
                         ports are down.
                 INL   - inter-node link. Link goes to another 6500
                         device.
                 INLA  - set with INL option when an X.25 link
                         connection is to a 6500 node using 2.12.04 or
                         earlier.
                 DELAY - enable Delay and Path trace on this link (link
                         must connected to Rel. 4.xx node).
                 Any combination of above specified by summing
                 (e.g. 1980+NUI+. . .)."
        ::= { cdx6500PPCTX25PortEntry 31 }

        cdx6500X25CfgNumRoutDigits OBJECT-TYPE
            SYNTAX INTEGER (0..12)
            ACCESS read-only
            STATUS mandatory
            DESCRIPTION
                "This specifies the number of routing digits in the call 
                 user data. It is used on X.25 links attached to a Public
                 Data Network where the private network address is carried
                 in the call user data."
        ::= { cdx6500PPCTX25PortEntry 32 }

        cdx6500X25CfgPortDigitsToStrip OBJECT-TYPE
            SYNTAX INTEGER (0..14)
            ACCESS read-only
            STATUS mandatory
            DESCRIPTION
                "For X.25 links connected to a Public Data Network, this
                 parameter specifies the number of prefix digits to
                 remove from the called address before forwarding the call
                 to the PDN."
        ::= { cdx6500PPCTX25PortEntry 33 }

        cdx6500X25CfgInDigitsToStrip OBJECT-TYPE
            SYNTAX INTEGER (0..15)
            ACCESS read-only
            STATUS mandatory
            DESCRIPTION
                "For X.25 links connected to a Public Data Network, this
                 parameter specifies the number of prefix digits to remove
                 from the incoming calling address before forwarding the
                 call from the PDN."
        ::= { cdx6500PPCTX25PortEntry 34 }

        cdx6500X25CfgRestrictConn OBJECT-TYPE
            SYNTAX DisplayString (SIZE(0..32))
            ACCESS read-only
            STATUS mandatory
            DESCRIPTION
                "All calls entering this port will be routed to the
                 destination specified in this parameter, irrespective of
                 route selection table entries. Blank this field to
                 disable this function."
        ::= { cdx6500PPCTX25PortEntry 35 }

        cdx6500X25CfgPortAddress OBJECT-TYPE
            SYNTAX DisplayString (SIZE(0..15))
            ACCESS read-only
            STATUS mandatory
            DESCRIPTION
                "On X.25 links:
                 If the X.25 Option REGO or REGI is selected, this
                 address is inserted into the calling address field of
                 the outbound or inbound call packet.

                 On MUX links:
                 When a MUX channel makes a call, the subaddress of the
                 channel is appended to this address and inserted into
                 the calling address field of the call packet."
        ::= { cdx6500PPCTX25PortEntry 36 }

        cdx6500X25CfgCUGMember OBJECT-TYPE
            SYNTAX DisplayString (SIZE(0..23))
            ACCESS read-only
            STATUS mandatory
            DESCRIPTION
                "The port may be a member of up to 8 different Closed User
                 Groups (CUGs). Each CUG membership must be a two digit
                 number (except `--') and separated by a comma.
                 ( e.g. 12,34,56,09,02,03 ).

                 `--'    - No CUG Membership.
                 00-99   - CUG Membership."
        ::= { cdx6500PPCTX25PortEntry 37 }

        cdx6500X25CfgBillRec OBJECT-TYPE
            SYNTAX INTEGER { 
                    off (1),
                    on  (2)
                    }
            ACCESS read-only
            STATUS mandatory
            DESCRIPTION
                "This controls whether billing (accounting) records will
                  be created for calls on this port."
        ::= { cdx6500PPCTX25PortEntry 38 }

        cdx6500X25CfgSubAddrSize OBJECT-TYPE
            SYNTAX INTEGER (0..3)
            ACCESS read-only
            STATUS mandatory
            DESCRIPTION
                "For ports connected to a Public Data Network, this
                 parameter specifies the number of digits in the
                 subaddress of an X.25 address."
        ::= { cdx6500PPCTX25PortEntry 39 }

        cdx6500X25CfgIdleDiscTimer OBJECT-TYPE
            SYNTAX INTEGER (0..3200)
            ACCESS read-only
            STATUS mandatory
            DESCRIPTION
                "The time in seconds that the port must be idle (no calls)
                 before being automatically disconnected. A value of 0
                 disables the Idle Disconnect feature. This feature may
                 only be enabled on DIMO/DIMOa/DIMOb/DIMOv/SIMPv ports
                 with the BKUP option selected."
        ::= { cdx6500PPCTX25PortEntry 40 }

        cdx6500X25CfgCallSecurity OBJECT-TYPE
            SYNTAX INTEGER { 
                    disable (1),
                    enable  (2)
                    }
            ACCESS read-only
            STATUS mandatory
            DESCRIPTION
                "For ports used as V.25 bis backup, this parameter
                 specifies the type of call security to use prior to
                 the link being detected up :

                 disable - Disable will allow both incoming and
                           outgoing calls.
                 enable  - Enable will allow ONLY outgoing calls.
                           Incoming calls will be immediately
                           terminated.
                 This parameter is only used with Link Backup."
        ::= { cdx6500PPCTX25PortEntry 41 }

        cdx6500X25CfgProtectLevel OBJECT-TYPE
            SYNTAX INTEGER { 
                    none    (1),
                    cpOnly  (2),
                    fullDcp (3)
                    }
            ACCESS read-only
            STATUS mandatory
            DESCRIPTION
                "This specifies the level of data or connection protection
                 which will be applied to calls to or from this port.  The
                 actual level for a call will be negotiated to the lesser
                 of this level and the level configured for the other end
                 of the call :

                 none    - No protection.
                 cpOnly  - Connection protection only.
                 fullDcp - Full data and connection protection."
        ::= { cdx6500PPCTX25PortEntry 42 }

        cdx6500X25CfgReconnTimeout OBJECT-TYPE
            SYNTAX INTEGER (1..128)
            ACCESS read-only
            STATUS mandatory
            DESCRIPTION
                "This specifies the number of seconds that DCP on the
                 originating side will wait between reconnection
                 attempts."
        ::= { cdx6500PPCTX25PortEntry 43 }

        cdx6500X25CfgReconnTriesLimit OBJECT-TYPE
            SYNTAX INTEGER (0..127)
            ACCESS read-only
            STATUS mandatory
            DESCRIPTION
                "This specifies the number of times that DCP on the
                 originating side will attempt to reconnect before
                 clearing the call. If 0 is entered, it will not
                 attempt to reconnect."
        ::= { cdx6500PPCTX25PortEntry 44 }

        cdx6500X25CfgFacilSubscripCont OBJECT-TYPE
            SYNTAX DisplayString (SIZE(4..34))
            ACCESS read-only
            STATUS mandatory
            DESCRIPTION
                "NONE    - Subscription to facilities not enforced.
                 FCN_ON  - Flow Control Negotiation enabled.
                           Packet and Window size negotiation facilities
                           in an inbound call will be allowed. Packet
                           and Window size facilities will always be
                           included in outbound calls and call accepted/
                           connected when this parameter is set.
                 FCN_OFF - Flow Control Negotiation disabled.
                           Inbound calls containing Packet and Window
                           size facilities will be cleared.  Packet
                           and Window size facilities will not be
                           present in outbound calls and call accepted/
                           connected when this parameter is set.
                 TCN_ON  - Throughput Class Negotiation enabled.
                           The throughput class negotiation facility in
                           an inbound call will be allowed. The
                           throughput class negotiation facility will
                           always be included in outbound calls and
                           call accepted/connected when this parameter
                           is set. The facility is passed onward to the
                           destination in the call packet transparently
                           and does not alter the handling of the SVC
                           data within the node.
                 TCN_OFF - Throughput Class Negotiation disabled.
                           Inbound calls containing the throughput class
                           negotiation facility will be cleared. The
                           throughput class negotiation facility will
                           not be present in outbound calls and call 
                           accepted/connected when this parameter is 
                           set. 
                 Some combinations of above options are allowed
                 (e.g. FCN_ON+TCN_ON)."
        ::= { cdx6500PPCTX25PortEntry 45 }

        cdx6500X25CfgAlarmPriority OBJECT-TYPE
            SYNTAX INTEGER { 
                    network (1),
                    access  (2)
                    }
            ACCESS read-only
            STATUS mandatory
            DESCRIPTION
                "Specify the severity level of LINK UP and LINK DOWN alarms :
                 network - Severity HIGH alarms will be generated.
                 access  - Severity LOW alarms will be generated."
        ::= { cdx6500PPCTX25PortEntry 46 }
         
        cdx6500X25CfgAddrTrans OBJECT-TYPE
            SYNTAX DisplayString (SIZE(3..107))
            ACCESS read-only
            STATUS mandatory
            DESCRIPTION
                "Select any of the  following address translation options
                 NONE  - no option specified
                 Outbound Call Processing:
                 DEDO  - delete called address.
                 DEGO  - delete calling address.
                 REGO  - replace calling address with configured Port Address.
                 REGSO - replace calling address with configured Port
                         Address plus Inbound Subaddress obtained from 
                         the Inbound Call Translation Table entry where
                         Private Network Address matches the entire
                         calling address.
                 INGO  - replace calling address with configured Port 
                         Address and retain original calling subaddress.
                 SAGO  - strip calling address, but retain subaddress.
    
                 Inbound Call Processing:
                 INGI  - replace calling address with configured Port
                         Address and retain original calling subaddress.
                 REGI  - replace calling address with configured Port
                         Address.
                 SRGI  - select route from the Calling Address 
                         Translation Table by replacing the called
                         address with the Private Network Address
                         where the Inbound Calling Address matches
                         the beginning of the calling address.
   
                 Call Accept Processing:
                 DADA  - delete called address in inbound/outbound 
                         call accept.
                 DAGA  - delete calling address in inbound/outbound 
                         call accept.
                 IADD  - copy called and calling addresses from call
                         request into outbound call accepted/connected.
                 Some of the options may be combined (e.g. DEDO+DEGO+...)"
        ::= { cdx6500PPCTX25PortEntry 47 }

        -- The 6500 X.25 Port Statistics Sub-group
        -- This sub-group belongs to the 6500 Port Protocol Statistics
        -- group. It holds statistics  peculiar to the 6500
        -- implementation of the x.25 protocol

        cdx6500PPSTX25PortTable OBJECT-TYPE
            SYNTAX SEQUENCE OF Cdx6500PPSTX25PortEntry
            ACCESS not-accessible
            STATUS mandatory
            DESCRIPTION
                "A table of X.25 Port statistics."
        ::= { cdx6500PSTPortProtocolGroup 2 }

        cdx6500PPSTX25PortEntry OBJECT-TYPE
            SYNTAX Cdx6500PPSTX25PortEntry
            ACCESS not-accessible
            STATUS mandatory
            DESCRIPTION
                "An X.25 Statistics Table entry. Each entry
                 contains the statistics for a single X.25
                 port."
            INDEX { cdx6500X25StatPortNumber }
        ::= { cdx6500PPSTX25PortTable 1 }

        Cdx6500PPSTX25PortEntry ::=
            SEQUENCE {
                cdx6500X25StatPortNumber
                    INTEGER,
                cdx6500X25StatPortStatus
                    DisplayString,
                cdx6500X25StatPortState
                    INTEGER,
                cdx6500X25StatActualPortSpeed
                    INTEGER,
                cdx6500X25StatPortUtilIn
                    INTEGER,
                cdx6500X25StatPortUtilOut
                    INTEGER,
                cdx6500X25StatMaxSVCCount
                    Gauge,
                cdx6500X25StatCurrSVCCount
                    INTEGER,
                cdx6500X25StatInChars
                    Counter,
                cdx6500X25StatOutChars
                    Counter,
                cdx6500X25StatInPkts
                    Counter,
                cdx6500X25StatOutPkts
                    Counter,
                cdx6500X25StatInDataFrames
                    Counter,
                cdx6500X25StatOutDataFrames
                    Counter,
                cdx6500X25StatNumPktsQueued
                    INTEGER,
                cdx6500X25StatCharRateIn
                    INTEGER,
                cdx6500X25StatCharRateOut
                    INTEGER,
                cdx6500X25StatPktRateIn
                    INTEGER,
                cdx6500X25StatPktRateOut
                    INTEGER,
                cdx6500X25StatFrameRateIn
                    INTEGER,
                cdx6500X25StatFrameRateOut
                    INTEGER,
                cdx6500X25StatOverrunErrs
                    Counter16,
                cdx6500X25StatUnderrunErrs
                    Counter16,
                cdx6500X25StatCRCErrs
                    Counter16,
                cdx6500X25StatInInfoFrames
                    Counter,
                cdx6500X25StatOutInfoFrames
                    Counter,
                cdx6500X25StatInRNRFrames
                    Counter,
                cdx6500X25StatOutRNRFrames
                    Counter,
                cdx6500X25StatInRRFrames
                    Counter,
                cdx6500X25StatOutRRFrames
                    Counter,
                cdx6500X25StatInREJFrames
                    Counter,
                cdx6500X25StatOutREJFrames
                    Counter,
                cdx6500X25StatInDataPkts
                    Counter,
                cdx6500X25StatOutDataPkts
                    Counter,
                cdx6500X25StatNumRxCallsSinceLastReset
                    INTEGER,
                cdx6500X25StatNumRxCallsRejected
                    INTEGER,
                cdx6500X25StatRxLastCallFailureCause
                    INTEGER,
                cdx6500X25StatRxLastCalledNumber
                    DisplayString,
                cdx6500X25StatRxLastCallingNumber
                    DisplayString,
                cdx6500X25StatRxMinCallDuration
                    DisplayString,
                cdx6500X25StatRxMaxCallDuration
                    DisplayString,
                cdx6500X25StatRxAvgCallDuration
                    DisplayString,
                cdx6500X25StatNumTxCallsSinceLastReset
                    INTEGER,
                cdx6500X25StatNumTxCallsRejected
                    INTEGER,
                cdx6500X25StatTxLastCallFailureCause
                    INTEGER,                
                cdx6500X25StatTxLastCalledNumber
                    DisplayString,
                cdx6500X25StatTxLastCallingNumber
                    DisplayString,
                cdx6500X25StatTxMinCallDuration
                    DisplayString,
                cdx6500X25StatTxMaxCallDuration
                    DisplayString,
                cdx6500X25StatTxAvgCallDuration
                    DisplayString,
                cdx6500X25StatSignalingState
                    INTEGER,
                cdx6500X25StatMaxPortUtilIn
                    INTEGER,
                cdx6500X25StatMaxPortUtilOut
                    INTEGER,
                cdx6500X25StatMaxPortUtilInTime
                    DisplayString,
                cdx6500X25StatMaxPortUtilOutTime
                    DisplayString,
                cdx6500X25StatMaxSVCCountTime
                    DisplayString
                }

        cdx6500X25StatPortNumber OBJECT-TYPE
            SYNTAX INTEGER (1..255)
            ACCESS read-only
            STATUS mandatory
            DESCRIPTION
                "The port number for this X.25 port."
        ::= { cdx6500PPSTX25PortEntry 1 }

        cdx6500X25StatPortStatus OBJECT-TYPE
            SYNTAX DisplayString (SIZE(2..8))
            ACCESS read-only
            STATUS mandatory
            DESCRIPTION
                "Status of this port :
                 Up       - Port is active
                 Down     - Port Is inactive
                 Disabled - An operator has disabled the port
                 Busy Out - an operator has busied out the port"
        ::= { cdx6500PPSTX25PortEntry 2 }

        cdx6500X25StatPortState OBJECT-TYPE
            SYNTAX INTEGER {
                    discPhase   (1),
                    linkDisk    (2),
                    linkSetup   (3),
                    sabmColl    (4),
                    frameReject (5),
                    normal      (6),
                    remoteBusy  (7),
                    reset       (8),
                    sendReject  (9),
                    rbSr        (10)
                    }
            ACCESS read-only
            STATUS mandatory
            DESCRIPTION
                "discPhase    - Disconnect Phase.
                 linkDisk     - Link Disconnect.
                 linkSetup    - The port is sending SABM frames and
                                waiting for a UA response.
                 sabmColl     - SABM Collision.
                 frameReject  - The port has rejected a received frame.
                 normal       - The port sending/receiving data.
                 remoteBusy   - The port is receiving RNR frames.
                 reset        - The port is being reset.
                 sendRej      - The port is sending REJ frames.
                 rbSr         - The port is receiving RNR frames and
                                sending REJ frames."
        ::= { cdx6500PPSTX25PortEntry 3 }

        cdx6500X25StatActualPortSpeed OBJECT-TYPE
            SYNTAX INTEGER
            ACCESS read-only
            STATUS mandatory
            DESCRIPTION
                "This is the speed of the port when Clock = INT; this is
                 the detected clock speed if Clock = EXT. If Port Speed
                 is 0, Clock = EXT, but clocking is not being received
                 fom attatched device."
        ::= { cdx6500PPSTX25PortEntry 4 }

        cdx6500X25StatPortUtilIn OBJECT-TYPE
            SYNTAX INTEGER (0..100)
            ACCESS read-only
            STATUS mandatory
            DESCRIPTION
                "Percentage of port bandwidth in use."
        ::= { cdx6500PPSTX25PortEntry 5 }

        cdx6500X25StatPortUtilOut OBJECT-TYPE
            SYNTAX INTEGER (0..100)
            ACCESS read-only
            STATUS mandatory
            DESCRIPTION
                "Percentage of port bandwidth in use."
        ::= { cdx6500PPSTX25PortEntry 6 }

        cdx6500X25StatMaxSVCCount OBJECT-TYPE
            SYNTAX Gauge
            ACCESS read-only
            STATUS mandatory
            DESCRIPTION
                "Maximum number of SVCs in use since last node, port or
                 statistics reset."
        ::= { cdx6500PPSTX25PortEntry 7 }

        cdx6500X25StatCurrSVCCount OBJECT-TYPE
            SYNTAX INTEGER (0..2000)
            ACCESS read-only
            STATUS mandatory
            DESCRIPTION
                "Current number of SVCs in use."
        ::= { cdx6500PPSTX25PortEntry 8 }

         cdx6500X25StatInChars OBJECT-TYPE
            SYNTAX Counter
            ACCESS read-only
            STATUS mandatory
            DESCRIPTION
                "Number of characters received since last node, port or
                 statistics reset."
        ::= { cdx6500PPSTX25PortEntry 9 }

         cdx6500X25StatOutChars OBJECT-TYPE
            SYNTAX Counter
            ACCESS read-only
            STATUS mandatory
            DESCRIPTION
                "Number of characters sent since last node, port or
                 statistics reset."
        ::= { cdx6500PPSTX25PortEntry 10 }

         cdx6500X25StatInPkts OBJECT-TYPE
            SYNTAX Counter
            ACCESS read-only
            STATUS mandatory
            DESCRIPTION
                "Number of packets received since last node, port or
                 statistics reset."
        ::= { cdx6500PPSTX25PortEntry 11 }

         cdx6500X25StatOutPkts OBJECT-TYPE
            SYNTAX Counter
            ACCESS read-only
            STATUS mandatory
            DESCRIPTION
                "Number of packets sent since last node, port or
                 statistics reset."
        ::= { cdx6500PPSTX25PortEntry 12 }

         cdx6500X25StatInDataFrames OBJECT-TYPE
            SYNTAX Counter
            ACCESS read-only
            STATUS mandatory
            DESCRIPTION
                "Number of frames received since last node, port or
                 statistics reset."
        ::= { cdx6500PPSTX25PortEntry 13 }

         cdx6500X25StatOutDataFrames OBJECT-TYPE
            SYNTAX Counter
            ACCESS read-only
            STATUS mandatory
            DESCRIPTION
                "Number of frames sent since last node, port or
                 statistics reset."
        ::= { cdx6500PPSTX25PortEntry 14 }

         cdx6500X25StatNumPktsQueued OBJECT-TYPE
            SYNTAX INTEGER
            ACCESS read-only
            STATUS mandatory
            DESCRIPTION
                "Number of packets currently queued."
        ::= { cdx6500PPSTX25PortEntry 15 }

         cdx6500X25StatCharRateIn OBJECT-TYPE
            SYNTAX INTEGER
            ACCESS read-only
            STATUS mandatory
            DESCRIPTION
                 "Summary of the characters being received by the port."
        ::= { cdx6500PPSTX25PortEntry 16 }

         cdx6500X25StatCharRateOut OBJECT-TYPE
            SYNTAX INTEGER
            ACCESS read-only
            STATUS mandatory
            DESCRIPTION
                 "Summary of the characters being sent by the port."
        ::= { cdx6500PPSTX25PortEntry 17 }

         cdx6500X25StatPktRateIn OBJECT-TYPE
            SYNTAX INTEGER
            ACCESS read-only
            STATUS mandatory
            DESCRIPTION
                 "Summary of the packets being received by the port."
        ::= { cdx6500PPSTX25PortEntry 18 }

         cdx6500X25StatPktRateOut OBJECT-TYPE
            SYNTAX INTEGER
            ACCESS read-only
            STATUS mandatory
            DESCRIPTION
                 "Summary of the packets being sent by the port."
        ::= { cdx6500PPSTX25PortEntry 19 }

         cdx6500X25StatFrameRateIn OBJECT-TYPE
            SYNTAX INTEGER
            ACCESS read-only
            STATUS mandatory
            DESCRIPTION
                 "Summary of the frames being received by the port."
        ::= { cdx6500PPSTX25PortEntry 20 }

         cdx6500X25StatFrameRateOut OBJECT-TYPE
            SYNTAX INTEGER
            ACCESS read-only
            STATUS mandatory
            DESCRIPTION
                 "Summary of the frames being sent by the port."
        ::= { cdx6500PPSTX25PortEntry 21 }

         cdx6500X25StatOverrunErrs OBJECT-TYPE
            SYNTAX Counter16
            ACCESS read-only
            STATUS mandatory
            DESCRIPTION
                "Number of Overrun errors since the last node or
                 statistics reset."
        ::= { cdx6500PPSTX25PortEntry 22 }

         cdx6500X25StatUnderrunErrs OBJECT-TYPE
            SYNTAX Counter16
            ACCESS read-only
            STATUS mandatory
            DESCRIPTION
                "Number of Underrun errors since the last node or
                 statistics reset."
        ::= { cdx6500PPSTX25PortEntry 23 }

         cdx6500X25StatCRCErrs OBJECT-TYPE
            SYNTAX Counter16
            ACCESS read-only
            STATUS mandatory
            DESCRIPTION
                "Number of CRC errors since the last node or
                 statistics reset."
        ::= { cdx6500PPSTX25PortEntry 24 }

         cdx6500X25StatInInfoFrames OBJECT-TYPE
            SYNTAX Counter
            ACCESS read-only
            STATUS mandatory
            DESCRIPTION
                "Number of Info frames received since last node, port or
                 statistics reset."
        ::= { cdx6500PPSTX25PortEntry 25 }

         cdx6500X25StatOutInfoFrames OBJECT-TYPE
            SYNTAX Counter
            ACCESS read-only
            STATUS mandatory
            DESCRIPTION
                "Number of Info frames sent since last node, port or
                 statistics reset."
        ::= { cdx6500PPSTX25PortEntry 26 }

         cdx6500X25StatInRNRFrames OBJECT-TYPE
            SYNTAX Counter
            ACCESS read-only
            STATUS mandatory
            DESCRIPTION
                "Number of frames received since last node, port or
                 statistics reset indicating RNR."
        ::= { cdx6500PPSTX25PortEntry 27 }

         cdx6500X25StatOutRNRFrames OBJECT-TYPE
            SYNTAX Counter
            ACCESS read-only
            STATUS mandatory
            DESCRIPTION
                "Number of frames sent since last node, port or
                 statistics reset indicating RNR."
        ::= { cdx6500PPSTX25PortEntry 28 }

         cdx6500X25StatInRRFrames OBJECT-TYPE
            SYNTAX Counter
            ACCESS read-only
            STATUS mandatory
            DESCRIPTION
                "Number of frames received since last node, port or
                 statistics reset indicating RR."
        ::= { cdx6500PPSTX25PortEntry 29 }

         cdx6500X25StatOutRRFrames OBJECT-TYPE
            SYNTAX Counter
            ACCESS read-only
            STATUS mandatory
            DESCRIPTION
                "Number of frames sent since last node, port or
                 statistics reset indicating RR."
        ::= { cdx6500PPSTX25PortEntry 30 }

         cdx6500X25StatInREJFrames OBJECT-TYPE
            SYNTAX Counter
            ACCESS read-only
            STATUS mandatory
            DESCRIPTION
                "Number of frames received since last node, port or
                 statistics reset indicating REJ."
        ::= { cdx6500PPSTX25PortEntry 31 }

         cdx6500X25StatOutREJFrames OBJECT-TYPE
            SYNTAX Counter
            ACCESS read-only
            STATUS mandatory
            DESCRIPTION
                "Number of frames sent since last node, port or
                 statistics reset indicating REJ."
        ::= { cdx6500PPSTX25PortEntry 32 }

         cdx6500X25StatInDataPkts OBJECT-TYPE
            SYNTAX Counter
            ACCESS read-only
            STATUS mandatory
            DESCRIPTION
                "Number of data packets received since last node, port or
                 statistics reset."
        ::= { cdx6500PPSTX25PortEntry 33 }

         cdx6500X25StatOutDataPkts OBJECT-TYPE
            SYNTAX Counter
            ACCESS read-only
            STATUS mandatory
            DESCRIPTION
                "Number of data packets sent since last node, port or
                 statistics reset."
        ::= { cdx6500PPSTX25PortEntry 34 }

        -- ISDN Call Status related statistics : these statistics
        -- are only valid for (virtual) switched data ports.

        cdx6500X25StatNumRxCallsSinceLastReset OBJECT-TYPE
            SYNTAX INTEGER
            ACCESS read-only
            STATUS mandatory
            DESCRIPTION
                "The number of inbound calls that were attempted
                 since the last statistics reset."
        ::= { cdx6500PPSTX25PortEntry 35 }

        cdx6500X25StatNumRxCallsRejected OBJECT-TYPE
            SYNTAX INTEGER
            ACCESS read-only
            STATUS mandatory
            DESCRIPTION
                "The number of inbound calls that were rejected
                 since the last statistics reset."
        ::= { cdx6500PPSTX25PortEntry 36 }

        cdx6500X25StatRxLastCallFailureCause OBJECT-TYPE
            SYNTAX INTEGER {
                    notAvailable               (100),
                    noFailureReported          (193),
                    noAvailableVirtualPort     (194),
                    securityViolation          (195),
                    noResourcesAvailable       (196),
                    callRejected               (197),
                    invalidPhoneNumber         (198),
                    outgoingCallRequestTimeout (199),
                    callCollision              (200),
                    virtualPortNotAvailable    (201),
                    invalidConfiguration       (202),
                    failureNotSupported        (203)
                    }
            ACCESS read-only
            STATUS mandatory
            DESCRIPTION
                "The reason the last inbound call was rejected,
                 since the last statistics reset.
                 The posssible values are:
                 notAvailable               : Value not available if not
                                              a (virtual) switched data 
                                              port.
                 noFailureReported          : No call failure
                 noAvailableVirtualPort     : No virtual port available
                 securityViolation          : Password security failed
                 noResourcesAvailable       : No resources available
                 callRejected               : Call failed by Xircom card
                 invalidPhoneNumber         : Phone number is incorrect
                 outgoingCallRequestTimeout : Outgoing call req timeout
                 callCollision              : Call collision
                 virtualPortNotAvailable    : This port is not available
                 invalidConfiguration       : Configuration is incorrect
                 failureNotSupported        : Failure is not supported"
        ::= { cdx6500PPSTX25PortEntry 37 }

        cdx6500X25StatRxLastCalledNumber OBJECT-TYPE
            SYNTAX DisplayString (SIZE (0..15))
            ACCESS read-only
            STATUS mandatory
            DESCRIPTION
                "The phone number of the virtual port of the last ISDN
                 call made into this port."
        ::= { cdx6500PPSTX25PortEntry 38 }

        cdx6500X25StatRxLastCallingNumber OBJECT-TYPE
            SYNTAX DisplayString (SIZE (0..15))
            ACCESS read-only
            STATUS mandatory
            DESCRIPTION
                "The phone number of last party to make an ISDN
                 call into this port."
        ::= { cdx6500PPSTX25PortEntry 39 }

        cdx6500X25StatRxMinCallDuration OBJECT-TYPE
            SYNTAX DisplayString
            ACCESS read-only
            STATUS mandatory
            DESCRIPTION
                "The minimum call duration of all inbound ISDN calls made
                 into this port, since the last statistics reset."
        ::= { cdx6500PPSTX25PortEntry 40 }

        cdx6500X25StatRxMaxCallDuration OBJECT-TYPE
            SYNTAX DisplayString
            ACCESS read-only
            STATUS mandatory
            DESCRIPTION
                "The maximum call duration of all inbound ISDN calls made
                 into this port, since the last statistics reset."
        ::= { cdx6500PPSTX25PortEntry 41 }

        cdx6500X25StatRxAvgCallDuration OBJECT-TYPE
            SYNTAX DisplayString
            ACCESS read-only
            STATUS mandatory
            DESCRIPTION
                "The average call duration of all inbound ISDN calls made
                 into this port, since the last statistics reset."
        ::= { cdx6500PPSTX25PortEntry 42 }

        cdx6500X25StatNumTxCallsSinceLastReset OBJECT-TYPE
            SYNTAX INTEGER
            ACCESS read-only
            STATUS mandatory
            DESCRIPTION
                "The number of outbound calls that were attempted
                 since the last statistics reset."
        ::= { cdx6500PPSTX25PortEntry 43 }

        cdx6500X25StatNumTxCallsRejected OBJECT-TYPE
            SYNTAX INTEGER
            ACCESS read-only
            STATUS mandatory
            DESCRIPTION
                "The number of outbound calls that were rejected
                 since the last statistics reset."
        ::= { cdx6500PPSTX25PortEntry 44 }

        cdx6500X25StatTxLastCallFailureCause OBJECT-TYPE
            SYNTAX INTEGER {
                    notAvailable               (100),
                    noFailureReported          (193),
                    noAvailableVirtualPort     (194),
                    securityViolation          (195),
                    noResourcesAvailable       (196),
                    callRejected               (197),
                    invalidPhoneNumber         (198),
                    outgoingCallRequestTimeout (199),
                    callCollision              (200),
                    virtualPortNotAvailable    (201),
                    invalidConfiguration       (202),
                    failureNotSupported        (203)
                    }
            ACCESS read-only
            STATUS mandatory
            DESCRIPTION
                "The reason the last inbound call was rejected,
                 since the last statistics reset.
                 The posssible values are:
                 notAvailable               : Value not available if not
                                              a (virtual) switched data 
                                              port.
                 noFailureReported          : No call failure
                 noAvailableVirtualPort     : No virtual port available
                 securityViolation          : Password security failed
                 noResourcesAvailable       : No resources available
                 callRejected               : Call failed by Xircom card
                 invalidPhoneNumber         : Phone number is incorrect
                 outgoingCallRequestTimeout : Outgoing call req timeout
                 callCollision              : Call collision
                 virtualPortNotAvailable    : This port is not available
                 invalidConfiguration       : Configuration is incorrect
                 failureNotSupported        : Failure is not supported"
        ::= { cdx6500PPSTX25PortEntry 45 }

        cdx6500X25StatTxLastCalledNumber OBJECT-TYPE
            SYNTAX DisplayString (SIZE (0..15))
            ACCESS read-only
            STATUS mandatory
            DESCRIPTION
                "The phone number of the last ISDN call made by a virtual 
                 port from this port."
        ::= { cdx6500PPSTX25PortEntry 46 }

        cdx6500X25StatTxLastCallingNumber OBJECT-TYPE
            SYNTAX DisplayString (SIZE (0..15))
            ACCESS read-only
            STATUS mandatory
            DESCRIPTION
                "The phone number of the virtual port that made the last 
                 ISDN call from this port."
        ::= { cdx6500PPSTX25PortEntry 47 }

        cdx6500X25StatTxMinCallDuration OBJECT-TYPE
            SYNTAX DisplayString
            ACCESS read-only
            STATUS mandatory
            DESCRIPTION
                "The minimum call duration of all outbound ISDN calls made
                 from this port, since the last statistics reset."
        ::= { cdx6500PPSTX25PortEntry 48 }

        cdx6500X25StatTxMaxCallDuration OBJECT-TYPE
            SYNTAX DisplayString
            ACCESS read-only
            STATUS mandatory
            DESCRIPTION
                "The maximum call duration of all outbound ISDN calls made
                 from this port, since the last statistics reset."
        ::= { cdx6500PPSTX25PortEntry 49 }

        cdx6500X25StatTxAvgCallDuration OBJECT-TYPE
            SYNTAX DisplayString
            ACCESS read-only
            STATUS mandatory
            DESCRIPTION
                "The average call duration of all outbound ISDN calls made
                 from this port, since the last statistics reset."
        ::= { cdx6500PPSTX25PortEntry 50 }

        cdx6500X25StatSignalingState OBJECT-TYPE
            SYNTAX INTEGER {
                    idle                 (1),
                    ringing              (2),
                    connected            (3),
                    congested            (4),
                    disabled             (5),
                    dChannelDown         (6),
                    disabledDChannelDown (7),
                    disconnecting        (8),
                    notAvailable         (100)
                    }
            ACCESS read-only
            STATUS mandatory
            DESCRIPTION
                "ISDN call signaling state.
                 The possible values are:
                 idle                   : No ISDN call present.
                 ringing                : Pending outgoing ISDN call request.
                 connected              : ISDN call is connected.
                 congested              : Congested mode.
                 disabled               : Virtual Port is disabled.
                 dChannelDown           : D-channel is down.
                 disabledChannelDown    : Disable and D-channel is down.
                 disconnecting          : Pending ISDN call disconnection.
                 notAvailable           : Value not available if not a 
                                          (virtual) switched data port."
        ::= { cdx6500PPSTX25PortEntry 51 }

        cdx6500X25StatMaxPortUtilIn OBJECT-TYPE
            SYNTAX INTEGER (0..100)
            ACCESS read-only
            STATUS mandatory
            DESCRIPTION
                "Max percentage of port bandwidth in use since last
                 node, port or statistics reset."
        ::= { cdx6500PPSTX25PortEntry 52 }

        cdx6500X25StatMaxPortUtilOut OBJECT-TYPE
            SYNTAX INTEGER (0..100)
            ACCESS read-only
            STATUS mandatory
            DESCRIPTION
                "Max percentage of port bandwidth in use since last 
                 node, port or statistics reset."
        ::= { cdx6500PPSTX25PortEntry 53 }

        cdx6500X25StatMaxPortUtilInTime OBJECT-TYPE
            SYNTAX DisplayString 
            ACCESS read-only
            STATUS mandatory
            DESCRIPTION
                "Time stamp of Max percentage of port bandwidth in use
                 since last node, port or statistics reset."
        ::= { cdx6500PPSTX25PortEntry 54 }

        cdx6500X25StatMaxPortUtilOutTime OBJECT-TYPE
            SYNTAX DisplayString 
            ACCESS read-only
            STATUS mandatory
            DESCRIPTION
                "Time stamp of Max percentage of port bandwidth in use
                 since last node, port or statistics reset."
        ::= { cdx6500PPSTX25PortEntry 55 }

        cdx6500X25StatMaxSVCCountTime OBJECT-TYPE
            SYNTAX DisplayString 
            ACCESS read-only
            STATUS mandatory
            DESCRIPTION
                "Time stamp of Maximum number of SVCs in use since 
                 last node, port or statistics reset."
        ::= { cdx6500PPSTX25PortEntry 56 }

        -- This Table contains Configuration paramaters 
        -- for the Inbound Call Translation table.
  
        cdx6500CGTInboundCallTranTable OBJECT-TYPE
            SYNTAX SEQUENCE OF Cdx6500CGTInboundCallTranEntry
            ACCESS not-accessible
            STATUS mandatory
            DESCRIPTION
                "All of the configuration parameters relevant
                 to the Inbound Call Translation table."
        ::= { cdx6500CfgGeneralGroup 2 }
  
        cdx6500CGTInboundCallTranEntry OBJECT-TYPE
            SYNTAX Cdx6500CGTInboundCallTranEntry
            ACCESS not-accessible
            STATUS mandatory
            DESCRIPTION
                "A row of Inbound Call Translation configuration parameters."
            INDEX { cdx6500InCallTranEntryNum }
        ::= { cdx6500CGTInboundCallTranTable 1 }
  
        Cdx6500CGTInboundCallTranEntry ::=
            SEQUENCE {
                cdx6500InCallTranEntryNum
                    INTEGER,
                cdx6500InCallTranInSubAddr
                    DisplayString,
                cdx6500InCallTranPrivNetAddr
                    DisplayString
                }
  
        cdx6500InCallTranEntryNum OBJECT-TYPE
            SYNTAX INTEGER (1..1000)
            ACCESS read-only
            STATUS mandatory
            DESCRIPTION
                "This is not a configuration parameter. Instead, it 
                 identifies the particular Inbound Call Translation 
                 Table entry being configured by the other parameters
                 in the record."
        ::= { cdx6500CGTInboundCallTranEntry 1 }
  
        cdx6500InCallTranInSubAddr OBJECT-TYPE
            SYNTAX DisplayString (SIZE(0..3))
            ACCESS read-only
            STATUS mandatory
            DESCRIPTION
                "This is the subaddress contained in an inbound call 
                 from another network, usually a public data network (PDN).
                 It will be translated into a private network address before
                 the call is forwarded."
        ::= { cdx6500CGTInboundCallTranEntry 2 }
  
        cdx6500InCallTranPrivNetAddr OBJECT-TYPE
            SYNTAX DisplayString (SIZE(0..15))
            ACCESS read-only
            STATUS mandatory
            DESCRIPTION
                "This is the private network address to translate to,
                 before forwarding calls from a PDN."
        ::= { cdx6500CGTInboundCallTranEntry 3 }
  
        -- The Outbound Call Translation Configuration Table
        -- This table contains Configuration paramaters 
        -- for the Outbound Call Translation table.
  
        cdx6500CGTOutboundCallTranTable OBJECT-TYPE
            SYNTAX SEQUENCE OF Cdx6500CGTOutboundCallTranEntry
            ACCESS not-accessible
            STATUS mandatory
            DESCRIPTION
                "All of the configuration parameters relevant
                 to the Outbound Call Translation table."
        ::= { cdx6500CfgGeneralGroup 3 }
  
        cdx6500CGTOutboundCallTranEntry OBJECT-TYPE
            SYNTAX Cdx6500CGTOutboundCallTranEntry
            ACCESS not-accessible
            STATUS mandatory
            DESCRIPTION
                "A row of Outbound Call Translation configuration parameters."
            INDEX { cdx6500OutCallTranEntryNum }
        ::= { cdx6500CGTOutboundCallTranTable 1 }
  
        Cdx6500CGTOutboundCallTranEntry ::=
            SEQUENCE {
                cdx6500OutCallTranEntryNum
                    INTEGER,
                cdx6500OutCallTranPrivNetAddr
                    DisplayString,
                cdx6500OutCallTranOutNetAddr
                    DisplayString,
                cdx6500OutCallTranOptions
                    INTEGER
                }
  
        cdx6500OutCallTranEntryNum OBJECT-TYPE
            SYNTAX INTEGER (1..1600)
            ACCESS read-only
            STATUS mandatory
            DESCRIPTION
                "This is not a configuration parameter. Instead, it 
                 identifies the particular Outbound Call Translation 
                 Table entry being configured by the other parameters 
                 in the record."
        ::= { cdx6500CGTOutboundCallTranEntry 1 }
  
        cdx6500OutCallTranPrivNetAddr OBJECT-TYPE
            SYNTAX DisplayString (SIZE(0..15))
            ACCESS read-only
            STATUS mandatory
            DESCRIPTION
                "This is the private network address contained in an 
                 outbound call to another network, usually a public 
                 data network (PDN). It will be translated into a PDN 
                 address before the call is forwarded."
        ::= { cdx6500CGTOutboundCallTranEntry 2 }
  
        cdx6500OutCallTranOutNetAddr OBJECT-TYPE
            SYNTAX DisplayString (SIZE(0..15))
            ACCESS read-only
            STATUS mandatory
            DESCRIPTION
                "This is the public network address to translate to,
                 before forwarding calls to a PDN."
        ::= { cdx6500CGTOutboundCallTranEntry 3 }
  
  
        cdx6500OutCallTranOptions OBJECT-TYPE
            SYNTAX INTEGER {
                    none       (0),
                    olda       (1),
                    newvalNone (50)
                    }
            ACCESS read-only
            STATUS mandatory
            DESCRIPTION
                "This parameter specifies options for outbound call address
                 translation as follows:
                 olda - insert the original called address into outbound 
                        call user data.
                 newvalNone - same functionality as 'none', new enumeration
                        added for RFC1155 compatibility."
        ::= { cdx6500CGTOutboundCallTranEntry 4 }

        -- The Calling Address Translation Configuration Table
        -- This table contains Configuration paramaters 
        -- for the Calling Address Translation table.
  
        cdx6500CGTCallingAddrTranTable OBJECT-TYPE
            SYNTAX SEQUENCE OF Cdx6500CGTCallingAddrTranEntry
            ACCESS not-accessible
            STATUS mandatory
            DESCRIPTION
                "All of the configuration parameters relevant
                 to the Calling AddressTranslation table."
        ::= { cdx6500CfgGeneralGroup 13 }
  
        cdx6500CGTCallingAddrTranEntry OBJECT-TYPE
            SYNTAX Cdx6500CGTCallingAddrTranEntry
            ACCESS not-accessible
            STATUS mandatory
            DESCRIPTION
                "A row of Calling Address Translation configuration 
                 parameters."
            INDEX { cdx6500CalladdrtranEntryNum }
        ::= { cdx6500CGTCallingAddrTranTable 1 }
  
        Cdx6500CGTCallingAddrTranEntry ::=
            SEQUENCE {
                cdx6500CalladdrtranEntryNum
                    INTEGER,
                cdx6500CalladdrtranInCallAddr
                    DisplayString,
                cdx6500CalladdrtranPrivNetAddr
                    DisplayString
                }
  
        cdx6500CalladdrtranEntryNum OBJECT-TYPE
            SYNTAX INTEGER (1..64)
            ACCESS read-only
            STATUS mandatory
            DESCRIPTION
                "This is not a configuration parameter. Instead, it 
                 identifies the entry being configured by the other 
                 parameters in the record."
        ::= { cdx6500CGTCallingAddrTranEntry 1 }
  
        cdx6500CalladdrtranInCallAddr OBJECT-TYPE
            SYNTAX DisplayString (SIZE(0..15))
            ACCESS read-only
            STATUS mandatory
            DESCRIPTION
                "This is the calling address contained in an inbound call,
                 it will be translated into a private network address
                 (if a match is found in the Translation Table),
                 before the call is forwarded."
        ::= { cdx6500CGTCallingAddrTranEntry 2 }
  
        cdx6500CalladdrtranPrivNetAddr OBJECT-TYPE
            SYNTAX DisplayString (SIZE(0..15))
            ACCESS read-only
            STATUS mandatory
            DESCRIPTION
                "This is the private network address to translate to,
                 before forwarding the call."
        ::= { cdx6500CGTCallingAddrTranEntry 3 }

        END
