-- Version 1.6, modified 02/12/98

        VOICE-OPT-MIB DEFINITIONS ::= BEGIN
                        
        IMPORTS
                Counter, Gauge
            FROM RFC1155-SMI

                OBJECT-TYPE
            FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }
     cdx6500CfgGeneralGroup OBJECT IDENTIFIER ::= { cdx6500Configuration 2 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Conventions

        DisplayString ::= OCTET STRING
                        
        PhysicalPortNumber ::= INTEGER (1..54)


        cdx6500PCTVoicePortTable OBJECT IDENTIFIER 
            ::= { cdx6500PCTPortProtocolGroup 25 }

        cdx6500PSTVoicePortTable OBJECT IDENTIFIER 
            ::= { cdx6500PSTPortProtocolGroup 26 }

        cdx6500GCTVoiceSwitchTable OBJECT IDENTIFIER 
            ::= { cdx6500CfgGeneralGroup 21 }


        -- Voice Port Configuration Table

        cdx6500PPCTVoicePortTable OBJECT-TYPE
            SYNTAX SEQUENCE OF Cdx6500PPCTVoicePortEntry
            ACCESS not-accessible
            STATUS mandatory
            DESCRIPTION
                "This table contains the port configuration parameters to    
                 configure the DSPM/E&M, DSPM/FXS, DSPM/HC, and DSPM/SM."
        ::= { cdx6500PCTVoicePortTable 1 }

        cdx6500PPCTVoicePortEntry OBJECT-TYPE
            SYNTAX Cdx6500PPCTVoicePortEntry
            ACCESS not-accessible
            STATUS mandatory
            DESCRIPTION
                "A Voice Port Configuration Table Entry. Each entry contains 
                 the configuration parameters for a single Voice Port."
            INDEX { cdx6500VoiceCfgPortNumber }
        ::= { cdx6500PPCTVoicePortTable 1 }

        Cdx6500PPCTVoicePortEntry ::=
            SEQUENCE {
                cdx6500VoiceCfgPortNumber
                    INTEGER,
                cdx6500VoiceCfgPortType
                    INTEGER,
                cdx6500VoiceCfgInterfaceType
                    INTEGER,
                cdx6500VoiceCfgSignalingType
                    INTEGER,
                cdx6500VoiceCfgELeadFilter
                    INTEGER,
                cdx6500VoiceCfgHybridFXS
                    INTEGER,
                cdx6500VoiceCfgHybridEAndM2
                    INTEGER,
                cdx6500VoiceCfgSignalingMode
                    INTEGER,
                cdx6500VoiceCfgSignalingControl
                    INTEGER,
                cdx6500VoiceCfgNoOfDigitsToCollect
                    INTEGER,
                cdx6500VoiceCfgNoOfRings
                    INTEGER,
                cdx6500VoiceCfgPCMMode
                    INTEGER,
                cdx6500VoiceCfgCompressionRate
                    INTEGER,
                cdx6500VoiceCfgDSIControl
                    INTEGER,
                cdx6500VoiceCfgSmoothingDelay
                    INTEGER,
                cdx6500VoiceCfgEchoControl
                    INTEGER,
                cdx6500VoiceCfgEchoReturnLoss
                    INTEGER,
                cdx6500VoiceCfgTxInputSignalLevel
                    DisplayString,
                cdx6500VoiceCfgRxOutputSignalLevel
                    DisplayString,
                cdx6500VoiceCfgFaxSupport
                    INTEGER,
                cdx6500VoiceCfgFaxRates
                    INTEGER,
                cdx6500VoiceCfgVoiceBandDetection
                    INTEGER,
                cdx6500VoiceCfgAutoCallMnemonic
                    DisplayString,
                cdx6500VoiceCfgCallControl
                    INTEGER,
                cdx6500VoiceCfgAutoCallTimeout
                    INTEGER,
                cdx6500VoiceCfgCallRetries
                    INTEGER,
                cdx6500VoiceCfgGroupSubaddress
                    INTEGER,
                cdx6500VoiceCfgBilling
                    INTEGER,
                cdx6500VoiceCfgRxSignalingStateChangeFilter
                    INTEGER,
                cdx6500VoiceCfgT1E1RxIdleOnhookState
                    DisplayString,
                cdx6500VoiceCfgT1E1TxIdleOnhookState
                    DisplayString,
                cdx6500VoiceCfgT1E1RxActiveOffhookState
                    DisplayString,
                cdx6500VoiceCfgT1E1TxActiveOffhookState
                    DisplayString,
                cdx6500VoiceCfgT1E1RingingState
                    DisplayString,
                cdx6500VoiceCfgT1E1NoRingingState
                    DisplayString,
                cdx6500VoiceCfgRxWinkStartTimer
                    INTEGER,
                cdx6500VoiceCfgRxMinimumReceiveWink
                    INTEGER,
                cdx6500VoiceCfgRxCalledEndGlareDetect
                    INTEGER,
                cdx6500VoiceCfgRxFirstDigitTimer
                    INTEGER,
                cdx6500VoiceCfgRxInterdigitTimer
                    INTEGER,
                cdx6500VoiceCfgTxWinkDelay
                    INTEGER,
                cdx6500VoiceCfgTxWinkWidth
                    INTEGER,
                cdx6500VoiceCfgTxDigitDelay
                    INTEGER,
                cdx6500VoiceCfgTxDigitOn
                    INTEGER,
                cdx6500VoiceCfgTxInterdigitTime
                    INTEGER,
                cdx6500VoiceCfgRxInterringWait
                    INTEGER,
                cdx6500VoiceCfgRxRingStateChangeFilter
                    INTEGER,
                cdx6500VoiceCfgTxRingerOffLong
                    INTEGER,
                cdx6500VoiceCfgTxRingerOffShort
                    INTEGER,
                cdx6500VoiceCfgTxRingerOn
                    INTEGER,
                cdx6500VoiceCfgRxDisconnectTimer
                    INTEGER,
                cdx6500VoiceCfgRxCalledEndDisconnectDelayTimer
                    INTEGER,
                cdx6500VoiceCfgLineErrorRecovery
                    INTEGER,
                cdx6500VoiceCfgSignalingSampleRate
                    INTEGER,
                cdx6500VoiceCfgWaitForParams
                    INTEGER,
                cdx6500VoiceCfgSpareTimer1
                    INTEGER,
                cdx6500VoiceCfgSpareTimer2
                    INTEGER,
                cdx6500VoiceCfgTxInterdigitPauseTime
                    INTEGER,
                cdx6500VoiceCfgRxMinimumFlashHookTime
                    INTEGER,
                cdx6500VoiceCfgRxMaximumFlashHookTime
                    INTEGER,
                cdx6500VoiceCfgTransparentSignalingIdleState
                    DisplayString,
                cdx6500VoiceCfgTransparentRxDisconnectFilter
                    INTEGER,
                cdx6500VoiceCfgTransparentSignalingBusyoutState
                    DisplayString,
                cdx6500VoiceCfgXlateSigInfo0000FromRemoteToLocalPort
                    DisplayString,
                cdx6500VoiceCfgXlateSigInfo1000FromRemoteToLocalPort
                    DisplayString,
                cdx6500VoiceCfgXlateSigInfo0100FromRemoteToLocalPort
                    DisplayString,
                cdx6500VoiceCfgXlateSigInfo1100FromRemoteToLocalPort
                    DisplayString,
                cdx6500VoiceCfgXlateSigInfo0010FromRemoteToLocalPort
                    DisplayString,
                cdx6500VoiceCfgXlateSigInfo1010FromRemoteToLocalPort
                    DisplayString,
                cdx6500VoiceCfgXlateSigInfo0110FromRemoteToLocalPort
                    DisplayString,
                cdx6500VoiceCfgXlateSigInfo1110FromRemoteToLocalPort
                    DisplayString,
                cdx6500VoiceCfgXlateSigInfo0001FromRemoteToLocalPort
                    DisplayString,
                cdx6500VoiceCfgXlateSigInfo1001FromRemoteToLocalPort
                    DisplayString,
                cdx6500VoiceCfgXlateSigInfo0101FromRemoteToLocalPort
                    DisplayString,
                cdx6500VoiceCfgXlateSigInfo1101FromRemoteToLocalPort
                    DisplayString,
                cdx6500VoiceCfgXlateSigInfo0011FromRemoteToLocalPort
                    DisplayString,
                cdx6500VoiceCfgXlateSigInfo1011FromRemoteToLocalPort
                    DisplayString,
                cdx6500VoiceCfgXlateSigInfo0111FromRemoteToLocalPort
                    DisplayString,
                cdx6500VoiceCfgXlateSigInfo1111FromRemoteToLocalPort
                    DisplayString,
                cdx6500VoiceCfgDialToneLowerFrequency
                    INTEGER,
                cdx6500VoiceCfgDialToneLowerFrequencyAmplitude
                    DisplayString,
                cdx6500VoiceCfgDialToneUpperFrequency
                    INTEGER,
                cdx6500VoiceCfgDialToneUpperFrequencyAmplitude
                    DisplayString,
                cdx6500VoiceCfgRingBackToneLowerFrequency
                    INTEGER,
                cdx6500VoiceCfgRingBackToneLowerFrequencyAmplitude
                    DisplayString,
                cdx6500VoiceCfgRingBackToneUpperFrequency
                    INTEGER,
                cdx6500VoiceCfgRingBackToneUpperFrequencyAmplitude
                    DisplayString,
                cdx6500VoiceCfgBusyToneLowerFrequency
                    INTEGER,
                cdx6500VoiceCfgBusyToneLowerFrequencyAmplitude
                    DisplayString,
                cdx6500VoiceCfgBusyToneUpperFrequency
                    INTEGER,
                cdx6500VoiceCfgBusyToneUpperFrequencyAmplitude
                    DisplayString,
                cdx6500VoiceCfgTxBusyToneOffTime
                    INTEGER,
                cdx6500VoiceCfgTxBusyToneOnTime
                    INTEGER,
                cdx6500VoiceCfgFastBusyToneLowerFrequency
                    INTEGER,
                cdx6500VoiceCfgFastBusyToneLowerFrequencyAmplitude
                    DisplayString,
                cdx6500VoiceCfgFastBusyToneUpperFrequency
                    INTEGER,
                cdx6500VoiceCfgFastBusyToneUpperFrequencyAmplitude
                    DisplayString,
                cdx6500VoiceCfgTxFastBusyToneOffTime
                    INTEGER,
                cdx6500VoiceCfgTxFastBusyToneOnTime
                    INTEGER,
                cdx6500VoiceCfgHybridFXO
                    INTEGER,
                cdx6500VoiceCfgTxPulse
                    INTEGER,
                cdx6500VoiceCfgRxMinPulse
                    INTEGER,
                cdx6500VoiceCfgRxMaxPulse
                    INTEGER,
                cdx6500VoiceCfgTxMasterClear
                    INTEGER,
                cdx6500VoiceCfgRxMinMasterClear
                    INTEGER,
                cdx6500VoiceCfgRxMaxMasterClear
                    INTEGER,
                cdx6500VoiceCfgTxSlaveClear
                    INTEGER,
                cdx6500VoiceCfgRxMinSlaveClear
                    INTEGER,
                cdx6500VoiceCfgRxMaxSlaveClear
                    INTEGER,
                cdx6500VoiceCfgTxSlaveRelease
                    INTEGER,
                cdx6500VoiceCfgRxMinSlaveRelease
                    INTEGER,
                cdx6500VoiceCfgRxMaxSlaveRelease
                    INTEGER,
                cdx6500VoiceCfgTxPTSTime
                    INTEGER,
                cdx6500VoiceCfgRxPTSTime
                    INTEGER,
                cdx6500VoiceCfgMasterGuard
                    INTEGER,
                cdx6500VoiceCfgSlaveGuard
                    INTEGER,
                cdx6500VoiceCfgTxFlashHookTime
                    INTEGER,
                cdx6500VoiceCfgDtmfAmplitude
                    DisplayString,
                cdx6500VoiceCfgFXSOffhookFilter
                    INTEGER
                }

        cdx6500VoiceCfgPortNumber OBJECT-TYPE
            SYNTAX INTEGER (1..255)
            ACCESS read-only
            STATUS mandatory
            DESCRIPTION
                "Port number of the Voice port."
        ::= { cdx6500PPCTVoicePortEntry 1 }

        cdx6500VoiceCfgPortType OBJECT-TYPE
            SYNTAX INTEGER {
                    voice (43)
                    }
            ACCESS read-only
            STATUS mandatory
            DESCRIPTION
                "This parameter represents the  port type of the port.
                 voice   :This is a voice port."
        ::= { cdx6500PPCTVoicePortEntry 2 }

        cdx6500VoiceCfgInterfaceType OBJECT-TYPE
            SYNTAX INTEGER {
                    eAndM2 (1),
                    eAndM4 (2),
                    fxo    (3),
                    fxs    (4),
                    nc     (100)
                    }
            ACCESS read-only
            STATUS mandatory
            DESCRIPTION
                "Select one of the following physical interfaces being used 
                 for this port. The entry must match the hardware.
                 eAndM2 :2 wire E&M (Ear and Mouth) Interface.
                 eAndM4 :4 wire E&M (Ear and Mouth) Interface.                  
                 fxo    :FXO (Foreign Exchange Office ) Interface.
                 fxs    :FXS (Foreign Exchange Station) Interface.
                 nc     :Skipped during configuration.
                 eAndM2 is only displayed for port numbers 1..54."
        ::= { cdx6500PPCTVoicePortEntry 3 }

        cdx6500VoiceCfgSignalingType OBJECT-TYPE
            SYNTAX INTEGER {
                    i   (1),
                    ii  (2),
                    v   (3),
                    iii (4),
                    nc  (100)                    
                    }
            ACCESS read-only
            STATUS mandatory
            DESCRIPTION
                "Select the E&M signalling type.
                 i   : EandMTypeI.
                 ii  : EandMTypeII.
                 v   : EandMTypeV.
                 iii : EandMTypeIII.
                 nc  : Skipped during configuration.
                 This parameter is displayed for DSPM/E&M and skipped for 
                 FXS, FXO, and all virtual port types."
        ::= { cdx6500PPCTVoicePortEntry 4 }

        cdx6500VoiceCfgELeadFilter OBJECT-TYPE
            SYNTAX INTEGER {
                    disabled (1),
                    enabled  (2),
                    nc       (100)
                    }
            ACCESS read-only
            STATUS mandatory
            DESCRIPTION
                "Selection for E lead filter enable or disable option.
                 disabled : Disables E-lead filter.
                 enabled  : Enables  E-lead filter.
                 nc       : Skipped during configuration.
                 This parameter is displayed for DSPM/E&M and skipped for 
                 FXS, FXO, and all virtual port types."
        ::= { cdx6500PPCTVoicePortEntry 5 }

        cdx6500VoiceCfgHybridFXS OBJECT-TYPE
            SYNTAX INTEGER {
                    sixHundred (1),
                    canada     (2),
                    germany    (3),
                    uk         (5),
                    belgium    (8),
                    france     (9),
                    nc         (100)
                    }
            ACCESS read-only
            STATUS mandatory
            DESCRIPTION
                "Hybrid balance filters and termination type based on country.
                 sixHundred : 600 ohm interface for USA, Japan and Ireland.
                 canada     : 600 ohms with 2.16 uF
                 germany    : 220 ohms in series with (820 ohms in parallel
                              with 115nF).
                 uk         : 300 ohms in series with (1K ohms in parallel
                              with 220nF).
                 belgium    : 150 ohms in series with (830 ohms in parallel
                              with 72nF).
                 france     : 215 ohms in series with (1K ohms in parallel
                              with 137nF).
                 nc         : Skipped during configuration.
                 This parameter is displayed for DSPM/FXS 
                 and skipped for DSPM/E&M, DSPM/HC(FXO) and all virtual 
                 port types."
        ::= { cdx6500PPCTVoicePortEntry 6 }

        cdx6500VoiceCfgHybridEAndM2 OBJECT-TYPE
            SYNTAX INTEGER {
                    sixHundred (1),
                    germany    (3),
                    uk         (10),
                    nc         (100)
                    }
            ACCESS read-only
            STATUS mandatory
            DESCRIPTION
                "Hybrid balance filters and termination type based on country.
                 (Only for E&M-2wire interfaces.)
                 sixHundred  : 600 ohm interface for USA, Japan and Ireland.
                 germany     : 220 ohms in series with (820 ohms in parallel
                               with 115nF).
                 uk          : 370 ohms in series with (620 ohms  in parallel
                               with 310nF).
                 nc          : Skipped during configuration."
        ::= { cdx6500PPCTVoicePortEntry 7 }

        cdx6500VoiceCfgSignalingMode OBJECT-TYPE
            SYNTAX INTEGER {
                    normal (1),
                    none   (2),
                    nc     (100)
                    }
            ACCESS read-only
            STATUS mandatory
            DESCRIPTION
                "Select the voice signalling mode.
                 normal : Allows signalling to pass end to end and 
                          signalling will be used to control 
                          circuit state and packet flow.
                 none   : A permanent voice path is established and
                          packet flow is always enabled, but no
                          signalling will be passed through.
                 nc     : Skipped during configuration."
        ::= { cdx6500PPCTVoicePortEntry 8 }

        cdx6500VoiceCfgSignalingControl OBJECT-TYPE
            SYNTAX INTEGER {
                    immediate          (1),
                    wink               (2),
                    transparent        (3),
                    delay              (4),
                    masterColisee      (5),
                    slaveColisee       (6),
                    seizureAcknowledge (7),
                    nc                 (100)
                    }
            ACCESS read-only
            STATUS mandatory
            DESCRIPTION
                "Select signaling control transmission mode in E&M 
                 interface type.
                 immediate          : Digits are transmitted immediately.
                 wink               : Digits are transmitted after the 
                                      WINK pulse.
                 transparent        : The voice signalling states are 
                                      transmitted end to end without 
                                      interpreting the signalling state.
                 delay              : Digits are transmitted after the end 
                                      of the Delay Dial signal.
                 masterColisee      : 65xx is simulating Colisee master mode.
                 slaveColisee       : 65xx is simulating Colisee slave mode.
                 seizureAcknowledge : Transmit Seizure acknowledge immediately 
                                      after receiving a Seizure signal from 
                                      the PBX.
                 nc                 : Skipped during configuration.
                 The parameter will be skipped for FXO & FXS type interface."
        ::= { cdx6500PPCTVoicePortEntry 9 }

        cdx6500VoiceCfgNoOfDigitsToCollect OBJECT-TYPE
            SYNTAX INTEGER (0..11)
            ACCESS read-only
            STATUS deprecated
            DESCRIPTION
                "Select number of digits to collect before making a call.
                 The parameter will not be supported."
        ::= { cdx6500PPCTVoicePortEntry 10 }

        cdx6500VoiceCfgNoOfRings OBJECT-TYPE
            SYNTAX INTEGER (0..9)
            ACCESS read-only
            STATUS mandatory
            DESCRIPTION
                "Number of rings to be received before a call can be 
                 accepted. This parameter is displayed for FXO and skipped   
                 for E&M and FXS interface types. A value of 0 implies that
                 this parameter was skipped during configuration."
        ::= { cdx6500PPCTVoicePortEntry 11 }

        cdx6500VoiceCfgPCMMode OBJECT-TYPE
            SYNTAX INTEGER {
                    aLaw  (1),
                    muLaw (2),
                    nc    (100)
                    }
            ACCESS read-only
            STATUS mandatory
            DESCRIPTION
                "Select the PCM encoder/decoder mode.
                 aLaw   :PCM encoder/decoder mode = A Law.
                 muLaw  :PCM encoder/decoder mode = Mu Law.
                 nc     :Skipped during configuration."
        ::= { cdx6500PPCTVoicePortEntry 12 }

        cdx6500VoiceCfgCompressionRate OBJECT-TYPE
            SYNTAX INTEGER {
                    cD8K   (1),
                    cD16K  (2),
                    cBD8K  (3),
                    cBD16K (4),
                    cE8Kb  (12),
                    cE16Kb (13),
                    nc     (100)
                    }
            ACCESS read-only
            STATUS mandatory
            DESCRIPTION
                "Select the voice compression rate to be used by the DSP.
                 cD8K   : 8k  CVSELP
                 c16k   : 16k CVSELP
                 cBD8K  : Bundled 8k  CVSELP
                 cB16k  : Bundled 16k CVSELP.
                 cE8Kb  : Enhanced Bundled 8k CVSELP
                 cE16Kb : Enhanced Bundled 16k CVSELP
                 nc     : Skipped during configuration."
        ::= { cdx6500PPCTVoicePortEntry 13 }

        cdx6500VoiceCfgDSIControl OBJECT-TYPE
            SYNTAX INTEGER {
                    disabled (1),
                    enabled  (2),
                    nc       (100)
                    }
            ACCESS read-only
            STATUS mandatory
            DESCRIPTION
                "Select if the Digital Speech Interpolation (Silence Detector)
                 will be used with this channel.
                 enabled  : DSI is activated.
                 disabled : DSI is not used.
                 nc       : Skipped during configuration."
        ::= { cdx6500PPCTVoicePortEntry 14 }

        cdx6500VoiceCfgSmoothingDelay OBJECT-TYPE
            SYNTAX INTEGER (5..150)
            ACCESS read-only
            STATUS mandatory
            DESCRIPTION
                "Select maximum inter packet arrival jitter due to network in 
                 milliseconds."
        ::= { cdx6500PPCTVoicePortEntry 15 }

        cdx6500VoiceCfgEchoControl OBJECT-TYPE
            SYNTAX INTEGER {
                    disabled (1),
                    enabled  (2),
                    nc       (100)
                    }
            ACCESS read-only
            STATUS mandatory
            DESCRIPTION
                "Select echo control.
                 disabled : Echo pass through. 
                 enabled  : This enables echo control logic.
                 nc       : Skipped during configuration.
                 Echo not detected and not cancelled. 
                 This parameter will be skipped in normal mode and 
                 only displayed when DEBUG is turned on."
        ::= { cdx6500PPCTVoicePortEntry 16 }

        cdx6500VoiceCfgEchoReturnLoss OBJECT-TYPE
            SYNTAX INTEGER {
                    minus3  (2),
                    minus6  (3),
                    minus9  (4),
                    minus12 (5),
                    nc      (100)
                    }
            ACCESS read-only
            STATUS mandatory
            DESCRIPTION
                "Select echo return loss in dBm.
                 minus3  : -3 dBm.
                 minus6  : -6 dBm.
                 minus9  : -9 dBm.
                 minus12 : -12dBm.
                 nc      :Skipped during configuration."
        ::= { cdx6500PPCTVoicePortEntry 17 }

        cdx6500VoiceCfgTxInputSignalLevel OBJECT-TYPE
            SYNTAX DisplayString
            ACCESS read-only
            STATUS mandatory
            DESCRIPTION
                "Enter the input signal level. To be specified in steps 
                 of 0.5 dBm
                 FXO Interface Type :  600 Ohms           +6.0 to -2.5dbm
                                       600 Ohms Adaptive  +6.0 to -2.5dbm
                 FXS Interface Type :  600 Ohms           +6.0 to -6.0dbm
                                       Canada             +6.0 to -5.5dbm
                                       UK                 +4.5 to -7.5dbm
                                       Germany            +4.0 to -8.0dbm
                                       France             -2.0 to -9.0dbm
                                       Belgium            +4.0 to -8.0dbm
                 E&M Interface Type :  4-Wire/600         +7.0 to -16.0dbm
                                       2-Wire/600         +7.0 to -16.0dbm
                                       2-Wire/UK          +5.0 to -16.0dbm
                                       2-Wire/Germany     +5.0 to -16.0dbm
                 Virtual Ports(100 and above):            +8.0 to  -6.0dbm
                 Entering a negative number for the 'Input Signal Level' 
                 will result in the DSPM card amplifying the signal by that 
                 many dB. Entering a positive number for the 'Input Signal 
                 Level' will result in the DSPM card attenuating the signal 
                 by that many dB."
        ::= { cdx6500PPCTVoicePortEntry 18 }

        cdx6500VoiceCfgRxOutputSignalLevel OBJECT-TYPE
            SYNTAX DisplayString
            ACCESS read-only
            STATUS mandatory
            DESCRIPTION
                "Enter the output signal level. To be selected in steps of 
                 0.5 dBm.
                 FXO Interface Type : 600 Ohms           +0.0 to -8.0dbm
                                      600 Ohms Adaptive  +0.0 to -8.0dbm
                 FXS Interface Type : 600 Ohms           +0.0 to -9.0dbm
                                      Canada             +0.0 to -9.0dbm
                                      UK                 -1.5 to -9.0dbm
                                      Germany            -2.0 to -9.0dbm
                                      France             -1.5 to -9.0dbm
                                      Belgium            -1.5 to -9.0dbm
                 E&M Interface Type : 4-Wire/600         +7.0 to -16.0dbm
                                      2-Wire/600         +3.0 to -16.0dbm
                                      2-Wire/UK          +1.0 to -16.0dbm
                                      2-Wire/Germany     +0.0 to -16.0dbm
                 Virtual Ports(100 and above):           +6.0 to  -8.0dbm
                 Entering a negative number for the 'Output Signal Level' 
                 will result in the DSPM card attenuating the signal by that 
                 many dB. Entering a positive number for the 'Output Signal 
                 Level' will result in the DSPM card amplifying the signal 
                 by that many dB."
        ::= { cdx6500PPCTVoicePortEntry 19 }

        cdx6500VoiceCfgFaxSupport OBJECT-TYPE
            SYNTAX INTEGER {
                    disabled (1),
                    enabled  (2),
                    nc       (100)
                    }
            ACCESS read-only
            STATUS mandatory
            DESCRIPTION
                "This parameter selects whether the FAX data is to be 
                 supported.
                 disabled : FAX data will not be detected.
                 enabled  : Detects presence of FAX data.
                 nc       : Skipped during configuration."
        ::= { cdx6500PPCTVoicePortEntry 20 }

        cdx6500VoiceCfgFaxRates OBJECT-TYPE
            SYNTAX INTEGER {
                    fr9600 (1),
                    fr4800 (2),
                    nc     (100)
                    }
            ACCESS read-only
            STATUS mandatory
            DESCRIPTION
                "Specify the speed to switch to, when FAX data is detected. 
                 This parameter is ignored if Fax support was disabled.
                 fr9600  : FAX to be transmitted across the network at 9600 
                           bits per second.
                 fr4800  : FAX to be transmitted across the network at 4800 
                           bits per second.
                 nc      : Skipped during configuration."
        ::= { cdx6500PPCTVoicePortEntry 21 }

        cdx6500VoiceCfgVoiceBandDetection OBJECT-TYPE
            SYNTAX INTEGER {
                    yes (1),
                    no  (2),
                    nc  (100)
                    }
            ACCESS read-only
            STATUS mandatory
            DESCRIPTION
                "Modem data detection.
                 yes : Detection of modem data enabled.
                 no  : Detection of modem data disabled.
                 nc  : Skipped during configuration.
                 This parameter will be skipped in normal mode.Displayed only 
                 when DEBUG is turned on."
        ::= { cdx6500PPCTVoicePortEntry 22 }

        cdx6500VoiceCfgAutoCallMnemonic OBJECT-TYPE
            SYNTAX DisplayString (SIZE (0..8))
            ACCESS read-only
            STATUS mandatory
            DESCRIPTION
                "This mnemonic name is used to originate the call. It consists 
                 of 0 - 8 alphanumeric characters."
        ::= { cdx6500PPCTVoicePortEntry 23 }

        cdx6500VoiceCfgCallControl OBJECT-TYPE
            SYNTAX INTEGER {
                    offhook  (1),
                    auto     (2),
                    switched (3),
                    nc       (100)
                    }
            ACCESS read-only
            STATUS mandatory
            DESCRIPTION
                "Select calling method.
                 offhook  : Call only when Offhook.Disconnect on Onhook.
                 auto     : SVC does not depend on On/Offhook condition.It 
                            remains established permanently after the power-up.
                 switched : Call only when interface goes offhook and
                            disconnect call when interface goes onhook.
                            Destination is determined by the DTMF
                            digits received.
                 nc       : Skipped during configuration."
        ::= { cdx6500PPCTVoicePortEntry 24 }

        cdx6500VoiceCfgAutoCallTimeout OBJECT-TYPE
            SYNTAX INTEGER (5..255)
            ACCESS read-only
            STATUS mandatory
            DESCRIPTION
                "Time interval between two successive calls in case of failure
                 of previous call.Used only in `Auto' call control mode.This 
                 parameter will be skipped if Call Control is Offhook 
                 and Switched."
        ::= { cdx6500PPCTVoicePortEntry 25 }

        cdx6500VoiceCfgCallRetries OBJECT-TYPE
            SYNTAX INTEGER (0..255)
            ACCESS read-only
            STATUS mandatory
            DESCRIPTION
                "Enter maximum number of call retries when previous call 
                 failed.Used only in Auto Call Control mode.'0' means try 
                 forever. This parameter will be skipped if Call Control is 
                 Offhook and Switched."
        ::= { cdx6500PPCTVoicePortEntry 26 }

        cdx6500VoiceCfgGroupSubaddress OBJECT-TYPE
            SYNTAX INTEGER (0..999)
            ACCESS read-only
            STATUS mandatory
            DESCRIPTION
                "Specifies a port subaddress that is shared by several Voice
                 ports. Incoming calls with this subaddress are routed to one 
                 of several ports sharing this subaddress. Another name for 
                 the group of ports with the same Group Subaddress is Hunt 
                 Group."
        ::= { cdx6500PPCTVoicePortEntry 27 }

        cdx6500VoiceCfgBilling OBJECT-TYPE
            SYNTAX INTEGER {
                    disabled (1),
                    enabled  (2),
                    nc       (100)
                    }
            ACCESS read-only
            STATUS mandatory
            DESCRIPTION
                "This controls whether billing (accounting) records will be 
                 created for calls on this port.
                 enabled  : Billing is enabled.
                 disabled : Billing is disabled.
                 nc       : Skipped during configuration."
        ::= { cdx6500PPCTVoicePortEntry 28 }

        cdx6500VoiceCfgRxSignalingStateChangeFilter OBJECT-TYPE
            SYNTAX INTEGER (0..1000)
            ACCESS read-only
            STATUS mandatory
            DESCRIPTION
                "The amount of time to declare a valid supervisory signaling 
                 state change. The granularity is 10 milliseconds."
        ::= { cdx6500PPCTVoicePortEntry 29 }

        cdx6500VoiceCfgT1E1RxIdleOnhookState OBJECT-TYPE
            SYNTAX DisplayString (SIZE (4))
            ACCESS read-only
            STATUS mandatory
            DESCRIPTION
                "The signalling state that represents the idle state.
                 For E1 ports and T1 ESF ports, these bits represent 
                 the ABCD signalling bits on the interface. For T1 SF ports
                 these bits represent ABAB signalling bits. `x' means don't 
                 care.The range is from 0000 to 1111."
        ::= { cdx6500PPCTVoicePortEntry 30 }

        cdx6500VoiceCfgT1E1TxIdleOnhookState OBJECT-TYPE
            SYNTAX DisplayString (SIZE (4))
            ACCESS read-only
            STATUS mandatory
            DESCRIPTION 
                "The signalling state that represents the idle state.
                 For E1 ports and T1 ESF ports, these bits represent 
                 the ABCD signalling bits on the interface. For T1 SF ports
                 these bits represent ABAB signalling bits.
                 The range is from 0000 to 1111."
        ::= { cdx6500PPCTVoicePortEntry 31 }

        cdx6500VoiceCfgT1E1RxActiveOffhookState OBJECT-TYPE
            SYNTAX DisplayString (SIZE (4))
            ACCESS read-only
            STATUS mandatory
            DESCRIPTION
                "The signalling state that represents the active state.
                 For E1 ports and T1 ESF ports, these bits represent 
                 the ABCD signalling bits on the interface. For T1 SF ports
                 these bits represent ABAB signalling bits. ` x' means don't 
                 care. The range is from 0000 to 1111."
        ::= { cdx6500PPCTVoicePortEntry 32 }   

        cdx6500VoiceCfgT1E1TxActiveOffhookState OBJECT-TYPE
            SYNTAX DisplayString (SIZE (4))
            ACCESS read-only
            STATUS mandatory
            DESCRIPTION
                "The signalling state that represents the active state.
                 For E1 ports and T1 ESF ports, these bits represent 
                 the ABCD signalling bits on the interface. 
                 The range is from 0000 to 1111."
        ::= { cdx6500PPCTVoicePortEntry 33 }

        cdx6500VoiceCfgT1E1RingingState OBJECT-TYPE
            SYNTAX DisplayString (SIZE (4))
            ACCESS read-only
            STATUS mandatory
            DESCRIPTION
                "The signalling state that represents the ringing state. For 
                 E1 ports and T1 ESF ports, these bits represent the ABCD 
                 signalling bits on the interface. For T1 SF ports
                 these bits represent ABAB signalling bits. `x' means 
                 don't care.
                 The range is from 0000 to 1111."
        ::= { cdx6500PPCTVoicePortEntry 34 }

        cdx6500VoiceCfgT1E1NoRingingState OBJECT-TYPE
            SYNTAX DisplayString (SIZE (4))
            ACCESS read-only
            STATUS mandatory
            DESCRIPTION
                "The signalling state that represents the no ringing  
                 state. For E1 ports and T1 ESF ports, these bits represent 
                 the ABCD signalling bits on the interface. For T1 SF ports
                 these bits represent ABAB signalling bits. `x' means don't 
                 care. The range is from 0000 to 1111."
        ::= { cdx6500PPCTVoicePortEntry 35 }

        cdx6500VoiceCfgRxWinkStartTimer OBJECT-TYPE
            SYNTAX INTEGER (0..2000)
            ACCESS read-only
            STATUS mandatory
            DESCRIPTION
                "This is the maximum time to wait for the beginning of the 
                 wink signal from the PBX before declaring a wink start 
                 malfunction. Granularity is 50 milliseconds."
        ::= { cdx6500PPCTVoicePortEntry 36 } 

        cdx6500VoiceCfgRxMinimumReceiveWink OBJECT-TYPE
            SYNTAX INTEGER (10..2000)
            ACCESS read-only
            STATUS mandatory
            DESCRIPTION
                "The amount of time required to declare a valid wink. 
                 Granularity is 10 milliseconds."
        ::= { cdx6500PPCTVoicePortEntry 37 }

        cdx6500VoiceCfgRxCalledEndGlareDetect OBJECT-TYPE
            SYNTAX INTEGER (50..10000)
            ACCESS read-only
            STATUS mandatory
            DESCRIPTION
                "The length of time when a wink pulse will be detected as a 
                 glare condition. Granularity is 50 milliseconds."
        ::= { cdx6500PPCTVoicePortEntry 38 }

        cdx6500VoiceCfgRxFirstDigitTimer OBJECT-TYPE
            SYNTAX INTEGER (1..60)
            ACCESS read-only
            STATUS mandatory
            DESCRIPTION
                "The maximum time (in seconds) to wait for the first DTMF 
                 digit before declaring a `busyout' state. Granularity is 
                 1 second."
        ::= { cdx6500PPCTVoicePortEntry 39 }

        cdx6500VoiceCfgRxInterdigitTimer OBJECT-TYPE
            SYNTAX INTEGER (1..60)
            ACCESS read-only
            STATUS mandatory
            DESCRIPTION
                "This is the maximum time (in seconds) to wait for a 
                 subsequent receive digit before declaring a misdial. 
                 Granularity is 1 second."
        ::= { cdx6500PPCTVoicePortEntry 40 }

        cdx6500VoiceCfgTxWinkDelay OBJECT-TYPE
            SYNTAX INTEGER (10..1000)
            ACCESS read-only
            STATUS mandatory
            DESCRIPTION
                "The time delay from receiving a valid Offhook state to start 
                 transmitting a wink. Granularity is 10 milliseconds."
        ::= { cdx6500PPCTVoicePortEntry 41 }

        cdx6500VoiceCfgTxWinkWidth OBJECT-TYPE
            SYNTAX INTEGER (10..2000)
            ACCESS read-only
            STATUS mandatory
            DESCRIPTION
                "The width of the transmitted wink pulse. Granularity is 10 
                 milliseconds."
        ::= { cdx6500PPCTVoicePortEntry 42 }

        cdx6500VoiceCfgTxDigitDelay OBJECT-TYPE
            SYNTAX INTEGER (0..5000)
            ACCESS read-only
            STATUS mandatory
            DESCRIPTION
                "The time delay before transmitting the first DTMF digit 
                 after a wink is received.Granularity is 10 milliseconds."
        ::= { cdx6500PPCTVoicePortEntry 43 }

        cdx6500VoiceCfgTxDigitOn OBJECT-TYPE
            SYNTAX INTEGER (60..1000)
            ACCESS read-only
            STATUS mandatory
            DESCRIPTION
                "The time DTMF digits are transmitted. Granularity is 10 
                 milliseconds."
        ::= { cdx6500PPCTVoicePortEntry 44 }

        cdx6500VoiceCfgTxInterdigitTime OBJECT-TYPE
            SYNTAX INTEGER (60..1000)
            ACCESS read-only
            STATUS mandatory
            DESCRIPTION
                "The time between transmitting DTMF digits. Granularity is 10 
                 milliseconds."
        ::= { cdx6500PPCTVoicePortEntry 45 }

        cdx6500VoiceCfgRxInterringWait OBJECT-TYPE
            SYNTAX INTEGER (1..60)
            ACCESS read-only
            STATUS mandatory
            DESCRIPTION
                "This is the maximum time to wait for subsequent receive 
                 rings before declaring a call abandoned condition.
                 Granularity is 1 second."
        ::= { cdx6500PPCTVoicePortEntry 46 }

        cdx6500VoiceCfgRxRingStateChangeFilter OBJECT-TYPE
            SYNTAX INTEGER (0..2000)
            ACCESS read-only
            STATUS mandatory
            DESCRIPTION
                "The amount of time to declare the change in the ring state. 
                 Granularity is 50 milliseconds."
        ::= { cdx6500PPCTVoicePortEntry 47 }

        cdx6500VoiceCfgTxRingerOffLong OBJECT-TYPE
            SYNTAX INTEGER (100..10000)
            ACCESS read-only
            STATUS mandatory
            DESCRIPTION
                "This timer is the long off period for ringer cadences that 
                 have a short and long off period.For the cases where the 
                 ring cadence defines one off period, the Tx Ringer Off Long 
                 must be equal to Tx Ringer Off Short. Granularity is 50 
                 milliseconds."
        ::= { cdx6500PPCTVoicePortEntry 48 }

        cdx6500VoiceCfgTxRingerOffShort OBJECT-TYPE
            SYNTAX INTEGER (100..10000)
            ACCESS read-only
            STATUS mandatory
            DESCRIPTION
                "This timer is the short off period for ringer cadences that 
                 have a short and long off period.For the cases where the 
                 ring cadence defines one off period, the Tx Ringer Off Long 
                 must be equal to Tx Ringer Off Short. Granularity is 50 
                 milliseconds."
        ::= { cdx6500PPCTVoicePortEntry 49 }

        cdx6500VoiceCfgTxRingerOn OBJECT-TYPE
            SYNTAX INTEGER (100..10000)
            ACCESS read-only
            STATUS mandatory
            DESCRIPTION
                "The time of the ringer on pulse. Granularity is 50 
                 milliseconds."
        ::= { cdx6500PPCTVoicePortEntry 50 }

        cdx6500VoiceCfgRxDisconnectTimer OBJECT-TYPE
            SYNTAX INTEGER (200..30000)
            ACCESS read-only
            STATUS mandatory
            DESCRIPTION
                "The amount of time required to receive idle signaling to 
                 disconnect a call.
                 For an analog FXO port, RX idle signaling is the loss of 
                 loop current.
                 For a FXS port, RX idle signaling is when the interface 
                 goes onhook.
                 For an analog E&M port, RX idle signaling is when the 'M' 
                 lead goes idle.
                 For digital interfaces, the RX idle state is defined by the
                 'T1/E1 Rx Idle (on-hook) State' parameter."
        ::= { cdx6500PPCTVoicePortEntry 51 }

        cdx6500VoiceCfgRxCalledEndDisconnectDelayTimer OBJECT-TYPE
            SYNTAX INTEGER (0..20)
            ACCESS read-only
            STATUS mandatory
            DESCRIPTION
                "The additional amount of time beyond the Rx Disconnect filter
                 the calling end must be Onhook to disconnect a call. 
                 Granularity is 1 second."
        ::= { cdx6500PPCTVoicePortEntry 52 }

        cdx6500VoiceCfgLineErrorRecovery OBJECT-TYPE
            SYNTAX INTEGER (0..1000)
            ACCESS read-only
            STATUS mandatory
            DESCRIPTION
                "The length of time voice will be suppressed after LOS or OF 
                 condition clears.Granularity is 10 milliseconds. This parameter
                 will be displayed for virtual ports only."
        ::= { cdx6500PPCTVoicePortEntry 53 }

        cdx6500VoiceCfgSignalingSampleRate OBJECT-TYPE
            SYNTAX INTEGER (1..20)
            ACCESS read-only
            STATUS mandatory
            DESCRIPTION
                "The time between sampling received signalling states and line 
                 states.Granularity is 1 millisecond. This parameter will be 
                 displayed only when the DEBUG flag is set."
        ::= { cdx6500PPCTVoicePortEntry 54 }

        cdx6500VoiceCfgWaitForParams OBJECT-TYPE
            SYNTAX INTEGER (0..10)
            ACCESS read-only
            STATUS mandatory
            DESCRIPTION
                "The amount of time to wait for a message to set the parameters
                 after receiving a disconnect message (messages occur in the 
                 form of an event) before busying out the port. 
                 Granularity is 1 second.
                 This parameter will be displayed only when the DEBUG flag 
                 is set."
        ::= { cdx6500PPCTVoicePortEntry 55 }

        cdx6500VoiceCfgSpareTimer1 OBJECT-TYPE
            SYNTAX INTEGER (1..10000)
            ACCESS read-only
            STATUS mandatory
            DESCRIPTION
                "Spare timer number 1.Granularity is 1 millisecond.This 
                 parameter will be displayed only when the DEBUG flag is set."
        ::= { cdx6500PPCTVoicePortEntry 56 }

        cdx6500VoiceCfgSpareTimer2 OBJECT-TYPE
            SYNTAX INTEGER (1..10000)
            ACCESS read-only
            STATUS mandatory
            DESCRIPTION
                "Spare timer number 2.Granularity is 1 millisecond. This 
                 parameter will be displayed only when the DEBUG flag is set."
        ::= { cdx6500PPCTVoicePortEntry 57 }

        cdx6500VoiceCfgTxInterdigitPauseTime OBJECT-TYPE
            SYNTAX INTEGER (1..10000)
            ACCESS read-only
            STATUS mandatory
            DESCRIPTION
                "The time between transmitting DTMF digits.
                 Enter in steps of 10 msec. "
        ::= { cdx6500PPCTVoicePortEntry 58 }

        cdx6500VoiceCfgRxMinimumFlashHookTime OBJECT-TYPE
            SYNTAX INTEGER (100..10000)
            ACCESS read-only
            STATUS mandatory
            DESCRIPTION
                "The shortest length of time required to be onhook to be 
                 recognized as a flash-hook. This value must be less than 
                 Rx Maximum Flash-Hook Time for flash-hook to be recognized."
        ::= { cdx6500PPCTVoicePortEntry 59 }

        cdx6500VoiceCfgRxMaximumFlashHookTime OBJECT-TYPE
            SYNTAX INTEGER (100..10000)
            ACCESS read-only
            STATUS mandatory
            DESCRIPTION
                "The longest length of time to be onhook to be recognized as 
                 a flash-hook. This value must be less than Rx Disconnect Timer
                 for flash-hook to be recognized. Note: the average of the 
                 minimum and maximum flash-hook values will be the pulse width
                 for a transmitted flash-hook."
        ::= { cdx6500PPCTVoicePortEntry 60 }

        cdx6500VoiceCfgTransparentSignalingIdleState OBJECT-TYPE
            SYNTAX DisplayString (SIZE (4))
            ACCESS read-only
            STATUS mandatory
            DESCRIPTION
                "The received signalling state that represents the idle 
                 state. For E1 ports and T1 ESF ports, these bits represent 
                 the ABCD signalling bits on the interface.`x' means don't care.
                 For E&M analog ports, Onhook is assumed for the idle state.
                 The range is 0000 to 1111."
        ::= { cdx6500PPCTVoicePortEntry 61 }

        cdx6500VoiceCfgTransparentRxDisconnectFilter OBJECT-TYPE
            SYNTAX INTEGER (0..5)
            ACCESS read-only
            STATUS mandatory
            DESCRIPTION
                "The time the received signaling state must be equal to
                 the idle state to disconnect the voice call. Zero value
                 disables idle state disconnect and maintains the voice 
                 call in the answered state.Time is entered in minutes."
        ::= { cdx6500PPCTVoicePortEntry 62 }

        cdx6500VoiceCfgTransparentSignalingBusyoutState OBJECT-TYPE
            SYNTAX DisplayString (SIZE (4))
            ACCESS read-only
            STATUS mandatory
            DESCRIPTION
                "The received signalling state that represents the Busyout 
                 state. For E1 ports and T1 ESF ports, these bits represent 
                 the ABCD signalling bits on the interface.For E&M analog 
                 ports, Offhook is assumed for the busyout/alarm state. The 
                 range is 0000 to 1111."
        ::= { cdx6500PPCTVoicePortEntry 63 }

        cdx6500VoiceCfgXlateSigInfo0000FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 64 }

        cdx6500VoiceCfgXlateSigInfo1000FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 65 }

        cdx6500VoiceCfgXlateSigInfo0100FromRemoteToLocalPort OBJECT-TYPE
             SYNTAX DisplayString (SIZE (4))
             ACCESS read-only
             STATUS mandatory
             DESCRIPTION
                 "Translate the signalling information received from the remote 
                  end to a value to be transmitted out the local port.If the 
                  local port is a T1/ESF or E1 port enter the ABCD values, for 
                  a T1/SF port, enter the AB(AB) value.
                  If the local port is an analog E&M port, enter 0000 for idle 
                  (Onhook) and 1111 for active (Offhook). The range is 0000 to 
                  1111."
        ::= { cdx6500PPCTVoicePortEntry 66 }

        cdx6500VoiceCfgXlateSigInfo1100FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 67 }
        
        cdx6500VoiceCfgXlateSigInfo0010FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 68 }

        cdx6500VoiceCfgXlateSigInfo1010FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 69 }

        cdx6500VoiceCfgXlateSigInfo0110FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 70 }

        cdx6500VoiceCfgXlateSigInfo1110FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 71 }

        cdx6500VoiceCfgXlateSigInfo0001FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 72 }

        cdx6500VoiceCfgXlateSigInfo1001FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 73 }

        cdx6500VoiceCfgXlateSigInfo0101FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 74 }

        cdx6500VoiceCfgXlateSigInfo1101FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 75 }

        cdx6500VoiceCfgXlateSigInfo0011FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 76 }

        cdx6500VoiceCfgXlateSigInfo1011FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 77 }

        cdx6500VoiceCfgXlateSigInfo0111FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 78 }

        cdx6500VoiceCfgXlateSigInfo1111FromRemoteToLocalPort OBJECT-TYPE
            SYNTAX DisplayString (SIZE (4))
            ACCESS read-only
            STATUS mandatory
            DESCRIPTION
                "Translate the signalling information received from the remote 
                 end to a value to be transmitted out the local port.If the 
                 local port is a T1/ESF or E1 port enter the ABCD values, for 
                 a T1/SF port, enter the AB(AB) value.
                 If the local port is an analog E&M port, enter 0000 for idle 
                 (Onhook) and 1111 for active (Offhook). The range is 0000 to 
                 1111."
        ::= { cdx6500PPCTVoicePortEntry 79 }

        cdx6500VoiceCfgDialToneLowerFrequency OBJECT-TYPE
            SYNTAX INTEGER (200..3500)
            ACCESS read-only
            STATUS mandatory
            DESCRIPTION
                "The lower of the two frequencies needed to generate the dial 
                 tone."
        ::= { cdx6500PPCTVoicePortEntry 80 }

        cdx6500VoiceCfgDialToneLowerFrequencyAmplitude OBJECT-TYPE
            SYNTAX DisplayString
            ACCESS read-only
            STATUS mandatory
            DESCRIPTION
                "The amplitude of the lower frequency to generate the dial tone.
                 To be specified in steps of 0.5dB, -30dB turn off output.
                 The range is from -30dBm to -3dBm."
        ::= { cdx6500PPCTVoicePortEntry 81 }

        cdx6500VoiceCfgDialToneUpperFrequency OBJECT-TYPE
            SYNTAX INTEGER (200..3500)
            ACCESS read-only
            STATUS mandatory
            DESCRIPTION
                "The higher of the two frequencies needed to generate the dial 
                 tone."
        ::= { cdx6500PPCTVoicePortEntry 82 }

        cdx6500VoiceCfgDialToneUpperFrequencyAmplitude OBJECT-TYPE
            SYNTAX DisplayString
            ACCESS read-only
            STATUS mandatory
            DESCRIPTION
                "The amplitude of the upper frequency to generate the dial tone.
                 To be specified in steps of 0.5dB, -30dB turn off output.
                 The range is from -30dBm to -3dBm."
        ::= { cdx6500PPCTVoicePortEntry 83 }

        cdx6500VoiceCfgRingBackToneLowerFrequency OBJECT-TYPE
            SYNTAX INTEGER (200..3500)
            ACCESS read-only
            STATUS mandatory
            DESCRIPTION
                "The lower of the two frequencies needed to generate the 
                 Ringback tone."
        ::= { cdx6500PPCTVoicePortEntry 84 }

        cdx6500VoiceCfgRingBackToneLowerFrequencyAmplitude OBJECT-TYPE
            SYNTAX DisplayString
            ACCESS read-only
            STATUS mandatory
            DESCRIPTION
                "The amplitude of the lower frequency to generate the 
                 Ringback tone. To be specified in steps of 0.5dB, -30dB 
                 turn off output.The range is from -30dBm to -3dBm."
        ::= { cdx6500PPCTVoicePortEntry 85 }

        cdx6500VoiceCfgRingBackToneUpperFrequency OBJECT-TYPE
            SYNTAX INTEGER (200..3500)
            ACCESS read-only
            STATUS mandatory
            DESCRIPTION
                "The higher of the two frequencies needed to generate the 
                 Ring-back tone."
        ::= { cdx6500PPCTVoicePortEntry 86 }

        cdx6500VoiceCfgRingBackToneUpperFrequencyAmplitude OBJECT-TYPE
            SYNTAX DisplayString
            ACCESS read-only
            STATUS mandatory
            DESCRIPTION
                "The amplitude of the upper frequency to generate the 
                 Ringback tone. To be specified in steps of 0.5dB, -30dB 
                 turn off output. The range is from -30dBm to -3dBm."
        ::= { cdx6500PPCTVoicePortEntry 87 }

        cdx6500VoiceCfgBusyToneLowerFrequency OBJECT-TYPE
            SYNTAX INTEGER (200..3500)
            ACCESS read-only
            STATUS mandatory
            DESCRIPTION
                "The lower of the two frequencies needed to generate the Busy 
                 tone."
        ::= { cdx6500PPCTVoicePortEntry 88 }

        cdx6500VoiceCfgBusyToneLowerFrequencyAmplitude OBJECT-TYPE
            SYNTAX DisplayString
            ACCESS read-only
            STATUS mandatory
            DESCRIPTION
                "The amplitude of the lower frequency to generate the Busy 
                 tone. To be specified in steps of 0.5dB, -30dB turn off 
                 output. The range is from -30dBm to -3dBm."
        ::= { cdx6500PPCTVoicePortEntry 89 }

        cdx6500VoiceCfgBusyToneUpperFrequency OBJECT-TYPE
            SYNTAX INTEGER (200..3500)
            ACCESS read-only
            STATUS mandatory
            DESCRIPTION
                "The higher of the two frequencies needed to generate the Busy 
                 tone."
        ::= { cdx6500PPCTVoicePortEntry 90 }

        cdx6500VoiceCfgBusyToneUpperFrequencyAmplitude OBJECT-TYPE
            SYNTAX DisplayString
            ACCESS read-only
            STATUS mandatory
            DESCRIPTION
                "The amplitude of the upper frequency to generate the Busy 
                 tone. To be specified in steps of 0.5dB, -30dB turn off 
                 output. The range is from -30dBm to -3dBm."
        ::= { cdx6500PPCTVoicePortEntry 91 }

        cdx6500VoiceCfgTxBusyToneOffTime OBJECT-TYPE
            SYNTAX INTEGER (100..1000)
            ACCESS read-only
            STATUS mandatory
            DESCRIPTION
                "Timer for the Busy tone off state. Granularity is 50 
                 milliseconds."
        ::= { cdx6500PPCTVoicePortEntry 92 }

        cdx6500VoiceCfgTxBusyToneOnTime OBJECT-TYPE
            SYNTAX INTEGER (100..1000)
            ACCESS read-only
            STATUS mandatory
            DESCRIPTION
                "Timer for the busy tone on state. Granularity is 50 
                 milliseconds."
        ::= { cdx6500PPCTVoicePortEntry 93 }

        cdx6500VoiceCfgFastBusyToneLowerFrequency OBJECT-TYPE
            SYNTAX INTEGER (200..3500)
            ACCESS read-only
            STATUS mandatory
            DESCRIPTION
                "The lower of the two frequencies needed to generate the Fast 
                 Busy tone."
        ::= { cdx6500PPCTVoicePortEntry 94 }

        cdx6500VoiceCfgFastBusyToneLowerFrequencyAmplitude OBJECT-TYPE
            SYNTAX DisplayString
            ACCESS read-only
            STATUS mandatory
            DESCRIPTION
                "The amplitude of the lower frequency to generate the Fast Busy 
                 tone. To be specified in steps of 0.5dB, -30dB turn off 
                 output. The range is from -30dBm to -3dBm."
        ::= { cdx6500PPCTVoicePortEntry 95 }

        cdx6500VoiceCfgFastBusyToneUpperFrequency OBJECT-TYPE
            SYNTAX INTEGER (200..3500)
            ACCESS read-only
            STATUS mandatory
            DESCRIPTION
                "The higher of the two frequencies needed to generate the Fast 
                 Busy tone."
        ::= { cdx6500PPCTVoicePortEntry 96 }

        cdx6500VoiceCfgFastBusyToneUpperFrequencyAmplitude OBJECT-TYPE
            SYNTAX DisplayString
            ACCESS read-only
            STATUS mandatory
            DESCRIPTION
                "The amplitude of the upper frequency to generate the Fast Busy 
                 tone. To be specified in steps of 0.5dB, -30dB turn off output.
                 The range is from -30dBm to -3dBm."
        ::= { cdx6500PPCTVoicePortEntry 97 }

        cdx6500VoiceCfgTxFastBusyToneOffTime OBJECT-TYPE
            SYNTAX INTEGER (100..1000)
            ACCESS read-only
            STATUS mandatory
            DESCRIPTION
                "Timer for the Fast Busy tone off state. 
                 Granularity is 50 milliseconds."
        ::= { cdx6500PPCTVoicePortEntry 98 }

        cdx6500VoiceCfgTxFastBusyToneOnTime OBJECT-TYPE
            SYNTAX INTEGER (100..1000)
            ACCESS read-only
            STATUS mandatory
            DESCRIPTION
                "Timer for the Fast Busy tone on state. 
                 Granularity is 50 milliseconds."
        ::= { cdx6500PPCTVoicePortEntry 99 }

        cdx6500VoiceCfgHybridFXO OBJECT-TYPE
            SYNTAX INTEGER {
                    sixHundred (1),
                    adaptive   (11),
                    nc         (100)
                    }
            ACCESS read-only
            STATUS mandatory
            DESCRIPTION
                "Hybrid balance filters.
                 sixHundred  : 600 ohm interface.
                 adaptive    : 600 ohm with adaptive filter.
                 nc          : Skipped during configuration.
                 This parameter is displayed for DSPM/HC (FXO) and 
                 skipped for DSPM/E&M, DSPM/FXS and all virtual port types."
        ::= { cdx6500PPCTVoicePortEntry 100 }

        cdx6500VoiceCfgTxPulse OBJECT-TYPE
            SYNTAX INTEGER (50..200)
            ACCESS read-only
            STATUS mandatory
            DESCRIPTION
                "The width of the transmitted Seizure, PTS, or Answer 
                 pulse in msec."
        ::= { cdx6500PPCTVoicePortEntry 101 }

        cdx6500VoiceCfgRxMinPulse OBJECT-TYPE
            SYNTAX INTEGER (50..200)
            ACCESS read-only
            STATUS mandatory
            DESCRIPTION
                "The minimum pulse width to declare a valid received 
                 Seizure, PTS, or Answer pulse."
        ::= { cdx6500PPCTVoicePortEntry 102 }

        cdx6500VoiceCfgRxMaxPulse OBJECT-TYPE
            SYNTAX INTEGER (50..200)
            ACCESS read-only
            STATUS mandatory
            DESCRIPTION
                "The maximum pulse width to declare a valid received 
                 Seizure, PTS, or Answer."
        ::= { cdx6500PPCTVoicePortEntry 103 }

        cdx6500VoiceCfgTxMasterClear OBJECT-TYPE
            SYNTAX INTEGER (400..2000)
            ACCESS read-only
            STATUS mandatory
            DESCRIPTION
                "The width of the transmitted Master Clear-Forward, 
                 Clear-Back, or Release Guard pulse in msec."
        ::= { cdx6500PPCTVoicePortEntry 104 }

        cdx6500VoiceCfgRxMinMasterClear OBJECT-TYPE
            SYNTAX INTEGER (400..2000)
            ACCESS read-only
            STATUS mandatory
            DESCRIPTION
                "The minimum pulse width to declare a valid received Master 
                 Clear-Forward, Clear-Back, or Release Guard."
        ::= { cdx6500PPCTVoicePortEntry 105 }

        cdx6500VoiceCfgRxMaxMasterClear OBJECT-TYPE
            SYNTAX INTEGER (400..2000)
            ACCESS read-only
            STATUS mandatory
            DESCRIPTION
                "The maximum pulse width to declare a valid received Master 
                 Clear-Forward, Clear-Back, or Release Guard."
        ::= { cdx6500PPCTVoicePortEntry 106 }

        cdx6500VoiceCfgTxSlaveClear OBJECT-TYPE
            SYNTAX INTEGER (400..2000)
            ACCESS read-only
            STATUS mandatory
            DESCRIPTION
                "The width of the transmitted Slave Clear-Forward or 
                 Clear-Back pulse in msec."
        ::= { cdx6500PPCTVoicePortEntry 107 }

        cdx6500VoiceCfgRxMinSlaveClear OBJECT-TYPE
            SYNTAX INTEGER (400..2000)
            ACCESS read-only
            STATUS mandatory
            DESCRIPTION
                "The minimum pulse width to declare a valid received 
                 Slave Clear-Forward or Clear-Back."
        ::= { cdx6500PPCTVoicePortEntry 108 }

        cdx6500VoiceCfgRxMaxSlaveClear OBJECT-TYPE
            SYNTAX INTEGER (400..2000)
            ACCESS read-only
            STATUS mandatory
            DESCRIPTION
                "The maximum pulse width to declare a valid received 
                 Slave Clear-Forward or Clear-Back."
        ::= { cdx6500PPCTVoicePortEntry 109 }

        cdx6500VoiceCfgTxSlaveRelease OBJECT-TYPE
            SYNTAX INTEGER (0..2000)
            ACCESS read-only
            STATUS mandatory
            DESCRIPTION
                "The width of the transmitted Slave Release Guard pulse 
                 in msec."
        ::= { cdx6500PPCTVoicePortEntry 110 }

        cdx6500VoiceCfgRxMinSlaveRelease OBJECT-TYPE
            SYNTAX INTEGER (0..2000)
            ACCESS read-only
            STATUS mandatory
            DESCRIPTION
                "The minimum pulse width to declare a valid received Slave 
                 Release Guard."
        ::= { cdx6500PPCTVoicePortEntry 111 }

        cdx6500VoiceCfgRxMaxSlaveRelease OBJECT-TYPE
            SYNTAX INTEGER (0..2000)
            ACCESS read-only
            STATUS mandatory
            DESCRIPTION
                "The maximum pulse width to declare a valid received Slave 
                 Release Guard."
        ::= { cdx6500PPCTVoicePortEntry 112 }

        cdx6500VoiceCfgTxPTSTime OBJECT-TYPE
            SYNTAX INTEGER (0..2000)
            ACCESS read-only
            STATUS mandatory
            DESCRIPTION
                "The time delay from receiving a valid Seizure from the 
                 PBX to start transmitting a PTS pulse."
        ::= { cdx6500PPCTVoicePortEntry 113 }

        cdx6500VoiceCfgRxPTSTime OBJECT-TYPE
            SYNTAX INTEGER (0..2000)
            ACCESS read-only
            STATUS mandatory
            DESCRIPTION
                "The maximum time to wait for a PTS pulse from the PBX 
                 after sending a Seizure before giving up and clearing 
                 the trunk."
        ::= { cdx6500PPCTVoicePortEntry 114 }

        cdx6500VoiceCfgMasterGuard OBJECT-TYPE
            SYNTAX INTEGER (0..2000)
            ACCESS read-only
            STATUS mandatory
            DESCRIPTION
                "The time the master side waits in the guard state after 
                 transmitting a clear pulse."
        ::= { cdx6500PPCTVoicePortEntry 115 }

        cdx6500VoiceCfgSlaveGuard OBJECT-TYPE
            SYNTAX INTEGER (0..2000)
            ACCESS read-only
            STATUS mandatory
            DESCRIPTION
                "The time the slave side waits in the guard state after 
                 transmitting a clear pulse."
        ::= { cdx6500PPCTVoicePortEntry 116 }

        cdx6500VoiceCfgTxFlashHookTime OBJECT-TYPE
            SYNTAX INTEGER (100..10000)
            ACCESS read-only
            STATUS mandatory
            DESCRIPTION
                "The lenght of time a flash signal will be transmitted 
                 as a result of a flash-hook from the remote interface."
        ::= { cdx6500PPCTVoicePortEntry 117 }

        cdx6500VoiceCfgDtmfAmplitude OBJECT-TYPE
            SYNTAX DisplayString
            ACCESS read-only
            STATUS mandatory
            DESCRIPTION
                "The amplitude of the DTMF digits.
                 To be specified in steps of 0.5dB, -30.0 turn off output.
                 The range is from -30dBm to -3dBm."
        ::= { cdx6500PPCTVoicePortEntry 118 }

        cdx6500VoiceCfgFXSOffhookFilter OBJECT-TYPE
            SYNTAX INTEGER (20..500)
            ACCESS read-only
            STATUS mandatory
            DESCRIPTION
                "This is the amoung of time a valid OFFHOOK conidtion must be
                 present before an analog FXS will declare OFFHOOK."
        ::= { cdx6500PPCTVoicePortEntry 119 } 


        -- Voice Switch Configuration Table

        cdx6500GGCTVoiceSwitchTable OBJECT-TYPE
            SYNTAX SEQUENCE OF Cdx6500VoiceSwitchEntry
            ACCESS not-accessible
            STATUS mandatory
            DESCRIPTION
                "This table contains the Voice Switch Table configuration."
        ::= { cdx6500GCTVoiceSwitchTable 1 }

        cdx6500VoiceSwitchEntry OBJECT-TYPE
            SYNTAX Cdx6500VoiceSwitchEntry
            ACCESS not-accessible
            STATUS mandatory
            DESCRIPTION
                "Each entry contains a list of parameters that 
                 makeup the Voice Switch Table."
            INDEX { cdx6500VoiceSwitchEntryNumber }
        ::= { cdx6500GGCTVoiceSwitchTable 1 }

        Cdx6500VoiceSwitchEntry ::=
            SEQUENCE {
                cdx6500VoiceSwitchRxDTMFDigitString
                    DisplayString,
                cdx6500VoiceSwitchNumRxDigitToReceive
                    INTEGER,
                cdx6500VoiceSwitchCallParam
                    DisplayString,
                cdx6500VoiceSwitchAlternateDestination
                    INTEGER,
                cdx6500VoiceSwitchCompressionOverrideRate
                    INTEGER,
                cdx6500VoiceSwitchNumLeadingDigitToStrip
                    INTEGER,
                cdx6500VoiceSwitchPreFixDigits
                    DisplayString,
                cdx6500VoiceSwitchPostFixDigits
                    DisplayString,
                cdx6500VoiceSwitchEntryNumber
                    INTEGER
                }

        cdx6500VoiceSwitchRxDTMFDigitString OBJECT-TYPE
            SYNTAX DisplayString (SIZE (0..20))
            ACCESS read-only
            STATUS mandatory
            DESCRIPTION
                "Select the voice number plans for the 6520/6560 network.
                 The received DTMF digits received by the voice interface is
                 compared to this parameter.
                 - Enter a trailing asterisk(*) as a wild-card.
                 - Use the space bar to blank the parameter.
                 Range: 1 to 20 characters (valid characters are 0 through 9,
                 '-', ',', '/', and '*'). The characters '-', ',', and '/'
                 are allowed only for ease of reading. They are not sent to the
                 remote port.
                 Note: The maximum number of digits that can be sent
                 to the remote end is 16."
        ::= { cdx6500VoiceSwitchEntry 1 }

        cdx6500VoiceSwitchNumRxDigitToReceive OBJECT-TYPE
            SYNTAX INTEGER (1..20)
            ACCESS read-only
            STATUS mandatory
            DESCRIPTION
                "Select the number of DTMF digits to
                 be received before making the call request." 
        ::= { cdx6500VoiceSwitchEntry 2 }

        cdx6500VoiceSwitchCallParam OBJECT-TYPE
            SYNTAX DisplayString (SIZE (0..20))
            ACCESS read-only
            STATUS mandatory
            DESCRIPTION
                "Define the network address of the called
                 node and the port or Hunt Group number
                 of the desired destination port."                 
        ::= { cdx6500VoiceSwitchEntry 3 }

        cdx6500VoiceSwitchAlternateDestination OBJECT-TYPE
            SYNTAX INTEGER {
                    deprecatedObj (1)
                    }
            ACCESS read-only
            STATUS deprecated
            DESCRIPTION
                "This object is no longer supported."
        ::= { cdx6500VoiceSwitchEntry 4 }

        cdx6500VoiceSwitchCompressionOverrideRate OBJECT-TYPE
            SYNTAX INTEGER {
                    none   (6),
                    cD8K   (7),
                    cD16K  (8),
                    cBD8K  (10),
                    cBD16K (11),
                    cE8Kb  (14),
                    cE16Kb (15),
                    nc     (100)
                    } 
            ACCESS read-only
            STATUS mandatory
            DESCRIPTION
                "Select the voice compression override algorithm.
                 none  - No override, use port configured value. 
                 c8k   - 8k CVSELP
                 c16k  - 16k CVSELP
                 cB8k  - Bundled 8k CVSELP
                 cB16k - Bundled 16k CVSELP
                 cE8Kb - Enhanced Bundled 8k CVSELP
                 cE8Kb - Enhanced Bundled 16k CVSELP
                 nc    - Skipped during configuration."
        ::= { cdx6500VoiceSwitchEntry 5 }

        cdx6500VoiceSwitchNumLeadingDigitToStrip OBJECT-TYPE
            SYNTAX INTEGER (0..20)
            ACCESS read-only
            STATUS mandatory
            DESCRIPTION
                "Select the number of leading digits to
                 be stripped off the received digits stream
                 before sending the digits stream to the
                 remote port."
        ::= { cdx6500VoiceSwitchEntry 6 }

        cdx6500VoiceSwitchPreFixDigits OBJECT-TYPE
            SYNTAX DisplayString (SIZE (0..20))
            ACCESS read-only
            STATUS mandatory
            DESCRIPTION
                "Select digits to be added in front of or at the end
                 of the received stream (after the stripped digits are
                 removed) before sending the digit stream to the remote port.
                 Range: 1 to 20 characters (valid characters are 0 through 9,
                 '*', '#', 'R', 'P', and '-'). The character '-' is allowed
                 only for ease of reading. It is not sent to the remote port.
                 The 'P' character is used to indicate a pause is required in
                 the playout of the digits at the remote end. The length of
                 the pause is equal to 'Tx Interdigit Pause Time' as defined
                 at the called port (destination port). Leading 'P' characters
                 are not supported. The character 'R' is used to separate the
                 prefix digit string from the postfix digit string
                 Note: The maximum number of digits that can be sent
                 to the remote end is 16."
        ::= { cdx6500VoiceSwitchEntry 7 }

        cdx6500VoiceSwitchPostFixDigits OBJECT-TYPE
            SYNTAX DisplayString (SIZE (0..20))
            ACCESS read-only
            STATUS deprecated
            DESCRIPTION
                "Select DTMF digits to be added at the end of the received DTMF
                 stream before sending the digit stream to the remote port.
                 Range: 1 to 20 characters (valid characters are 0 through 9,
                 '-', ',', '/', '*', '#', and 'P'). The characters '-', ',',
                 and '/' are allowed only for ease of reading. They are not
                 sent to the remote port. The 'P' character is used to indicate
                 a pause is required in the playout of the digits at the remote
                 end. The length of the pause is equal to 'Tx Interdigit 
                 Pause Time' as defined at the called port (destination port).
                 Note: The maximum number of digits that can be sent
                 to the remote end is 16. 
                 This object is no longer supported."
        ::= { cdx6500VoiceSwitchEntry 8 }

        cdx6500VoiceSwitchEntryNumber OBJECT-TYPE
            SYNTAX INTEGER
            ACCESS read-only
            STATUS mandatory
            DESCRIPTION
                "This is the entry number in the Voice Switch Table."
        ::= { cdx6500VoiceSwitchEntry 9 }

        -- Voice Port Statistics Table

        cdx6500PPSTVoicePortTable OBJECT-TYPE
            SYNTAX SEQUENCE OF Cdx6500PPSTVoicePortEntry
            ACCESS not-accessible
            STATUS mandatory
            DESCRIPTION
                "This table contains the port statistics for Voice ports."
        ::= { cdx6500PSTVoicePortTable 1 }

        cdx6500PPSTVoicePortEntry OBJECT-TYPE
            SYNTAX Cdx6500PPSTVoicePortEntry
            ACCESS not-accessible
            STATUS mandatory
            DESCRIPTION
                "A Voice Port Statistics Table Entry. Each entry contains   
                 the statistics for a single Voice Port."
            INDEX { cdx6500VoiceStatsPortNumber }
        ::= { cdx6500PPSTVoicePortTable 1 }

        Cdx6500PPSTVoicePortEntry ::=
            SEQUENCE {
                cdx6500VoiceStatsPortNumber
                    INTEGER,
                cdx6500VoiceStatsPortInterfaceType
                    INTEGER,
                cdx6500VoiceStatsHWRevAndPartNumber
                    DisplayString, 
                cdx6500VoiceStatsFortyEightVolts
                    INTEGER,
                cdx6500VoiceStatsPortState
                    INTEGER,
                cdx6500VoiceStatsCircuitState
                    INTEGER,
                cdx6500VoiceStatsCurrentMode
                    INTEGER,
                cdx6500VoiceStatsTimeOfLastStatReset
                    DisplayString,
                cdx6500VoiceStatsCallDuration
                    DisplayString,
                cdx6500VoiceStatsTotalCallDuration
                    DisplayString,
                cdx6500VoiceStatsPortUtilization
                    INTEGER,
                cdx6500VoiceStatsNumberOfCalls
                    Counter,
                cdx6500VoiceStatsLastDigitsTransmitted
                    DisplayString,
                cdx6500VoiceStatsLastDigitsReceived
                    DisplayString,
                cdx6500VoiceStatsTxPacketDropped
                    Counter,
                cdx6500VoiceStatsRxPacketDropped
                    Counter,
                cdx6500VoiceStatsDroppedPackets
                    Counter,
                cdx6500VoiceStatsDSPInternalFaults
                    Counter,
                cdx6500VoiceStatsTxPackets
                    Counter,
                cdx6500VoiceStatsRxPackets
                    Counter,
                cdx6500VoiceStatsTxPacketsPerSecond
                    Counter,
                cdx6500VoiceStatsRxPacketsPerSecond
                    Counter,
                cdx6500VoiceStatsDSIEfficiency
                    INTEGER,
                cdx6500VoiceStatsCurrentRate
                    INTEGER,
                cdx6500VoiceStatsInputPower
                    DisplayString,
                cdx6500VoiceStatsOutputPower
                    DisplayString,
                cdx6500VoiceStatsFAXTransmissions
                    INTEGER,
                cdx6500VoiceStatsUnsupportedFmtsFAXXmissions
                    INTEGER,
                cdx6500PPSTSignalingSequenceTrapTxState
                    DisplayString,
                cdx6500PPSTSignalingSequenceTrapRxState
                    DisplayString,
                cdx6500PPSTSignalingSequenceTrapMachineState
                    DisplayString,
                cdx6500PPSTSignalingSequenceTrapTimeSinceLastChange
                    INTEGER,
                cdx6500PPSTSignalingSequenceTrapComment
                    DisplayString,
                cdx6500VoiceStatsCurrentStatus
                    INTEGER,
                cdx6500VoiceStatsLastClearCauseCode
                    DisplayString,
                cdx6500VoiceStatsLastClearDiagnosticCode
                    DisplayString,
                cdx6500VoiceStatsLastInboundCallPacketCalledAddress
                    DisplayString,
                cdx6500VoiceStatsLastInboundCallPacketCallingAddress
                    DisplayString,
                cdx6500VoiceStatsLastInboundCallPacketFacilities
                    DisplayString,
                cdx6500VoiceStatsLastInboundCallPacketCUD
                    DisplayString,
                cdx6500VoiceStatsLastOutboundCallPacketCalledAddress
                    DisplayString,
                cdx6500VoiceStatsLastOutboundCallPacketCallingAddress
                    DisplayString,
                cdx6500VoiceStatsLastOutboundCallPacketFacilities
                    DisplayString,
                cdx6500VoiceStatsLastOutboundCallPacketCUD
                    DisplayString,
                cdx6500VoiceStatsRingerStatus
                    INTEGER,
                cdx6500VoiceStatsDSPMSMSlotNumber
                    INTEGER,
                cdx6500VoiceStatsDSPMNumber
                    INTEGER,
                cdx6500VoiceStatsT1E1PortNumber
                    INTEGER,
                cdx6500VoiceStatsTimeSlotNumber
                    DisplayString,
                cdx6500VoiceStatsDaughterCardRevAndPartNumber
                    DisplayString
                }

        cdx6500VoiceStatsPortNumber OBJECT-TYPE
            SYNTAX INTEGER (1..255)
            ACCESS read-only
            STATUS mandatory
            DESCRIPTION
                "Port number of the Voice Port."
        ::= { cdx6500PPSTVoicePortEntry 1 }

        cdx6500VoiceStatsPortInterfaceType OBJECT-TYPE
            SYNTAX INTEGER {
                    eAndM2 (1),
                    eAndM4 (2),
                    fxo    (3),
                    fxs    (4)
                    }
            ACCESS read-only
            STATUS mandatory
            DESCRIPTION
                 "This parameter indicates the type of DPSM card used.
                  eAndM2 : DPSM/E&M.
                  eAndM4 : DPSM/E&M.
                  fxo    : DPSM/HC(FXO).
                  fxs    : DPSM/FXS."
        ::= { cdx6500PPSTVoicePortEntry 2 }

        cdx6500VoiceStatsHWRevAndPartNumber OBJECT-TYPE
            SYNTAX DisplayString
            ACCESS read-only
            STATUS mandatory
            DESCRIPTION
                "Hardware revision and part number of the main card. The 
                 revision number has format n.n and the part number is an 8 
                 digit number of the form nnnnnnnn."
        ::= { cdx6500PPSTVoicePortEntry 3 }

        cdx6500VoiceStatsFortyEightVolts OBJECT-TYPE
            SYNTAX INTEGER {
                    none    (1),
                    present (2),
                    na      (100)
                    }
            ACCESS read-only
            STATUS mandatory
            DESCRIPTION
                "This parameter indicates whether the 48 volt power supply is 
                 installed in the node.
                 none    : power supply not installed.
                 present : power supply installed.
                 na      : Value not available.
                 This parameter will not be displayed for DSPM/HC."
        ::= { cdx6500PPSTVoicePortEntry 4 }

        cdx6500VoiceStatsPortState OBJECT-TYPE
            SYNTAX INTEGER {
                    disabled (1),
                    enabled  (2)
                    }
            ACCESS read-only
            STATUS mandatory
            DESCRIPTION
                "This parameter indicates ths status of the port.
                 disabled : The port is disabled.
                 enabled  : The port is enabled."
        ::= { cdx6500PPSTVoicePortEntry 5 }
        
        cdx6500VoiceStatsCircuitState OBJECT-TYPE
            SYNTAX INTEGER {
                    connected    (1),
                    disconnected (2)
                    }
            ACCESS read-only
            STATUS mandatory
            DESCRIPTION
                "This parameter indicates the state of the SVC associated 
                 with this port.
                 connected    : SVC established.
                 disconnected : SVC not established."
        ::= { cdx6500PPSTVoicePortEntry 6 }

        cdx6500VoiceStatsCurrentMode OBJECT-TYPE
            SYNTAX INTEGER {
                    voice (1),
                    pcm   (2),
                    fax   (3)
                    }
            ACCESS read-only
            STATUS mandatory
            DESCRIPTION
                "This parameter indicates the current operating mode 
                 of the DSP.
                 voice : DSP is currently operating in voice mode.
                 pcm   : PCM mode is not supported.
                 fax   : DSP is currently operating in fax mode."
        ::= { cdx6500PPSTVoicePortEntry 7 }

        cdx6500VoiceStatsTimeOfLastStatReset OBJECT-TYPE
            SYNTAX DisplayString
            ACCESS read-only
            STATUS mandatory
            DESCRIPTION
                "This parameter indicates the time since the last statistic 
                 reset using the format month:day:year:hours:minutes:seconds 
                 (mm:dd:yyyy:hh:mm:ss)."
        ::= { cdx6500PPSTVoicePortEntry 8 }

        cdx6500VoiceStatsCallDuration OBJECT-TYPE
            SYNTAX DisplayString
            ACCESS read-only
            STATUS mandatory
            DESCRIPTION
                "This parameter indicates the duration of the current (last) 
                 call using the format hours:minutes:seconds (hh:mm:ss)."
        ::= { cdx6500PPSTVoicePortEntry 9 }

        cdx6500VoiceStatsTotalCallDuration OBJECT-TYPE
            SYNTAX DisplayString
            ACCESS read-only
            STATUS mandatory
            DESCRIPTION
                "This parameter indicates the total time of all calls since 
                 last reset.It is measured from Offhook to Onhook and uses 
                 the format hours:minutes:seconds (hh:mm:ss)."
        ::= { cdx6500PPSTVoicePortEntry 10 }

        cdx6500VoiceStatsPortUtilization OBJECT-TYPE
            SYNTAX INTEGER (0..100)
            ACCESS read-only
            STATUS mandatory
            DESCRIPTION
                "This parameter is calculated as the ratio of `Total Call 
                 Duration' to `Time Of Last Reset'. It is a percentage 
                 value of the form nnn%." 
        ::= { cdx6500PPSTVoicePortEntry 11 }

        cdx6500VoiceStatsNumberOfCalls OBJECT-TYPE
            SYNTAX Counter
            ACCESS read-only
            STATUS mandatory
            DESCRIPTION
                "This parameter indicates the total number of calls since the 
                 last reset."
        ::= { cdx6500PPSTVoicePortEntry 12 }

        cdx6500VoiceStatsLastDigitsTransmitted OBJECT-TYPE
            SYNTAX DisplayString
            ACCESS read-only
            STATUS mandatory
            DESCRIPTION
                "This parameter indicates the last DTMF digits transmitted to 
                 the voice interface. Not supported at this time." 
        ::= { cdx6500PPSTVoicePortEntry 13 }

        cdx6500VoiceStatsLastDigitsReceived OBJECT-TYPE
            SYNTAX DisplayString
            ACCESS read-only
            STATUS mandatory
            DESCRIPTION
                "This parameter indicates the last DTMF digits received from 
                 the voice interface. Not supported at this time." 
        ::= { cdx6500PPSTVoicePortEntry 14 }

        cdx6500VoiceStatsTxPacketDropped OBJECT-TYPE
            SYNTAX Counter
            ACCESS read-only
            STATUS mandatory
            DESCRIPTION
                "This parameter indicates the number of times transmit packets 
                 were dropped due to DSPM congestion."
        ::= { cdx6500PPSTVoicePortEntry 15 }

        cdx6500VoiceStatsRxPacketDropped OBJECT-TYPE
            SYNTAX Counter
            ACCESS read-only
            STATUS mandatory
            DESCRIPTION
                "This parameter indicates the number of times receive packets 
                 were dropped due to network overload or processor loading."
        ::= { cdx6500PPSTVoicePortEntry 16 }

        cdx6500VoiceStatsDroppedPackets OBJECT-TYPE
            SYNTAX Counter
            ACCESS read-only
            STATUS mandatory
            DESCRIPTION
                "This parameter indicates the estimate of packets dropped 
                 end to end in the network."
        ::= { cdx6500PPSTVoicePortEntry 17 }

        cdx6500VoiceStatsDSPInternalFaults OBJECT-TYPE
            SYNTAX Counter
            ACCESS read-only
            STATUS mandatory
            DESCRIPTION
                "This parameter indicates the number of recoverable software 
                 faults.It is displayed only when the DEBUG flag is set."
        ::= { cdx6500PPSTVoicePortEntry 18 }

        cdx6500VoiceStatsTxPackets OBJECT-TYPE
            SYNTAX Counter
            ACCESS read-only
            STATUS mandatory
            DESCRIPTION
                "This parameter indicates the number of packets received from 
                 the network port since the last reset."
        ::= { cdx6500PPSTVoicePortEntry 19 }

        cdx6500VoiceStatsRxPackets OBJECT-TYPE
            SYNTAX Counter
            ACCESS read-only
            STATUS mandatory
            DESCRIPTION
                "This parameter indicates the number of packets sent to the 
                 network port since the last reset."
        ::= { cdx6500PPSTVoicePortEntry 20 }

        cdx6500VoiceStatsTxPacketsPerSecond OBJECT-TYPE
            SYNTAX Counter
            ACCESS read-only
            STATUS mandatory
            DESCRIPTION
                "This parameter indicates the average number of packets    
                 transmitted per second.It is calculated as the ratio of `Tx 
                 Packets' to `Total Call Duration'."
        ::= { cdx6500PPSTVoicePortEntry 21 }

        cdx6500VoiceStatsRxPacketsPerSecond OBJECT-TYPE
            SYNTAX Counter
            ACCESS read-only
            STATUS mandatory
            DESCRIPTION
                "This parameter indicates the average number of packets    
                 received per second.It is calculated as the ratio of `Rx 
                 Packets' to `Total Call Duration'."
        ::= { cdx6500PPSTVoicePortEntry 22 }

        cdx6500VoiceStatsDSIEfficiency OBJECT-TYPE
            SYNTAX INTEGER (0..100)
            ACCESS read-only
            STATUS mandatory
            DESCRIPTION
                "This parameter is calculated by dividing `Rx Packets/sec'   
                 by the packet rate. It is a percentage value."
        ::= { cdx6500PPSTVoicePortEntry 23 }

        cdx6500VoiceStatsCurrentRate OBJECT-TYPE
            SYNTAX INTEGER {
                    cD8K   (1),
                    cBD8K  (2),
                    cE8Kb  (3),
                    cD16K  (4),
                    cBD16K (5),
                    cE16Kb (6),
                    cPcm   (7),
                    cFax   (8),
                    na     (100)
                    }
            ACCESS read-only
            STATUS mandatory
            DESCRIPTION
                "This parameter indicates the current compression rate 
                 being used.
                 cD8K    : Compression rate is 8K.
                 cBD8K   : Compression rate is bundled 8K.
                 cE8Kb   : Compression rate is Enhanced bundled D8K.
                 cD16K   : Compression rate is 16K.
                 cBD16K  : Compression rate is bundled 16K.
                 cE16Kb  : Compression rate is Enhanced bundled D16K.
                 cPcm    : Compression rate is PCM.
                 cFax    : Compression rate is FAX.
                 na      : Value not available."
        ::= { cdx6500PPSTVoicePortEntry 24 }

        cdx6500VoiceStatsInputPower OBJECT-TYPE
            SYNTAX DisplayString
            ACCESS read-only
            STATUS mandatory
            DESCRIPTION
                "This parameter indicates the input power level in dBm.
                 (Measured power)."
        ::= { cdx6500PPSTVoicePortEntry 25 }

        cdx6500VoiceStatsOutputPower OBJECT-TYPE
            SYNTAX DisplayString 
            ACCESS read-only
            STATUS mandatory
            DESCRIPTION
                "This parameter indicates the output power level in dBm.
                (Measured power)."
        ::= { cdx6500PPSTVoicePortEntry 26 }

        cdx6500VoiceStatsFAXTransmissions OBJECT-TYPE
            SYNTAX INTEGER
            ACCESS read-only
            STATUS mandatory
            DESCRIPTION
                "This parameter indicates the number of FAX 
                 transmissions spoofed."
        ::= { cdx6500PPSTVoicePortEntry 27 }

        cdx6500VoiceStatsUnsupportedFmtsFAXXmissions OBJECT-TYPE
            SYNTAX INTEGER
            ACCESS read-only
            STATUS mandatory
            DESCRIPTION
                "This parameter indicates the number of FAX transmissions    
                 requesting unsupported formats but transmitted using 
                 ISG formats."
        ::= { cdx6500PPSTVoicePortEntry 28 }

        cdx6500PPSTSignalingSequenceTrapTxState OBJECT-TYPE
            SYNTAX DisplayString
            ACCESS read-only
            STATUS deprecated
            DESCRIPTION
                "The transmitting voice signalling state is displayed 
                 as ABCD (i.e. 1010).
                 This object is no longer supported. Refer to 
                 cdx6500SignalingSequenceTrapTxState."
        ::= { cdx6500PPSTVoicePortEntry 29 }

        cdx6500PPSTSignalingSequenceTrapRxState OBJECT-TYPE
            SYNTAX DisplayString
            ACCESS read-only
            STATUS deprecated
            DESCRIPTION
                "The receiving voice signalling state is displayed 
                 as ABCD (i.e. 1010).
                 This object is no longer supported. Refer to 
                 cdx6500SignalingSequenceTrapRxState."
        ::= { cdx6500PPSTVoicePortEntry 30 }

        cdx6500PPSTSignalingSequenceTrapMachineState OBJECT-TYPE
            SYNTAX DisplayString (SIZE (11))
            ACCESS read-only
            STATUS deprecated
            DESCRIPTION
                "The voice signalling state machine state is a 11 character 
                 field representing the state of the signalling software.
                 This object is no longer supported. Refer to 
                 cdx6500SignalingSequenceTrapMachineState."
        ::= { cdx6500PPSTVoicePortEntry 31 }

        cdx6500PPSTSignalingSequenceTrapTimeSinceLastChange OBJECT-TYPE
            SYNTAX INTEGER
            ACCESS read-only
            STATUS deprecated
            DESCRIPTION
                "This parameter indicates the time from the previous state to 
                 this state, measured in milliseconds.
                 This object is no longer supported. Refer to 
                 cdx6500SignalingSequenceTrapTimeSinceLastChange."
        ::= { cdx6500PPSTVoicePortEntry 32 }

        cdx6500PPSTSignalingSequenceTrapComment OBJECT-TYPE
            SYNTAX DisplayString (SIZE (0..16))
            ACCESS read-only
            STATUS deprecated
            DESCRIPTION
                "The comment field is an ASCII string upto 16 characters long.
                 This object is no longer supported. Refer to 
                 cdx6500SignalingSequenceTrapComment."
        ::= { cdx6500PPSTVoicePortEntry 33 }

        cdx6500VoiceStatsCurrentStatus OBJECT-TYPE
            SYNTAX INTEGER {
                    inhibited    (1),
                    disconnected (2),
                    calling      (3),
                    called       (4),
                    connected    (5),
                    null         (6)
                    }
            ACCESS read-only
            STATUS mandatory
            DESCRIPTION
                "This is the call processing state machine status.
                inhibited    : Current Status = Disconnected.
                disconnected : Current Status = Disconnected.
                calling      : Current Status = Calling.
                called       : Current Status = Called.
                connected    : Current Status = Connected (data transfer).
                null         : Current Status = Undefined."
        ::= { cdx6500PPSTVoicePortEntry 34 }

        cdx6500VoiceStatsLastClearCauseCode OBJECT-TYPE
            SYNTAX DisplayString
            ACCESS read-only
            STATUS mandatory
            DESCRIPTION
                "This parameter indicates the last clear cause code received   
                 Every code corresponds to an integer value followed by its  
                 text description in paranthesis. eg.Consider the clear 
                 cause code for `number busy' which is CAUSE_CLR_NUM_BSY.   
                 This corresponds to : 001  (number busy)."
        ::= { cdx6500PPSTVoicePortEntry 35 }

        cdx6500VoiceStatsLastClearDiagnosticCode OBJECT-TYPE
            SYNTAX DisplayString
            ACCESS read-only
            STATUS mandatory
            DESCRIPTION
                "This parameter indicates the last clear diagnostic 
                 received.Every code corresponds to an integer value followed
                 by its text description in paranthesis. eg.Consider 
                 the diagnostic code for `invalid bits in packet' which is 
                 DIAG_INV_PKT_BITS.This corresponds to :041  (invalid bits 
                 in packet)."
        ::= { cdx6500PPSTVoicePortEntry 36 }

        cdx6500VoiceStatsLastInboundCallPacketCalledAddress OBJECT-TYPE
            SYNTAX DisplayString (SIZE (3..15))
            ACCESS read-only
            STATUS mandatory
            DESCRIPTION
                "This parameter contains the called address present in the 
                 last inbound call packet."
        ::= { cdx6500PPSTVoicePortEntry 37 }

        cdx6500VoiceStatsLastInboundCallPacketCallingAddress OBJECT-TYPE
            SYNTAX DisplayString (SIZE (3..15))
            ACCESS read-only
            STATUS mandatory
            DESCRIPTION
                "This parameter contains the calling address present in the 
                 last inbound call packet."
        ::= { cdx6500PPSTVoicePortEntry 38 }

        cdx6500VoiceStatsLastInboundCallPacketFacilities OBJECT-TYPE
            SYNTAX DisplayString (SIZE (0..105))
            ACCESS read-only
            STATUS mandatory
            DESCRIPTION
                "This parameter contains the facilities present in the last 
                 inbound call packet."
        ::= { cdx6500PPSTVoicePortEntry 39 }

        cdx6500VoiceStatsLastInboundCallPacketCUD OBJECT-TYPE
            SYNTAX DisplayString (SIZE (0..16))
            ACCESS read-only
            STATUS mandatory
            DESCRIPTION
                "This parameter contains the call user data present in the 
                 last inbound call packet."
        ::= { cdx6500PPSTVoicePortEntry 40 }

        cdx6500VoiceStatsLastOutboundCallPacketCalledAddress OBJECT-TYPE
            SYNTAX DisplayString (SIZE (3..15))
            ACCESS read-only
            STATUS mandatory
            DESCRIPTION
                "This parameter contains the called address present in the 
                 last outbound call packet."
        ::= { cdx6500PPSTVoicePortEntry 41 }

        cdx6500VoiceStatsLastOutboundCallPacketCallingAddress OBJECT-TYPE
            SYNTAX DisplayString (SIZE (3..15))
            ACCESS read-only
            STATUS mandatory
            DESCRIPTION
                "This parameter contains the calling address present in the 
                 last outbound call packet."
        ::= { cdx6500PPSTVoicePortEntry 42 }

        cdx6500VoiceStatsLastOutboundCallPacketFacilities OBJECT-TYPE
            SYNTAX DisplayString (SIZE (0..105))
            ACCESS read-only
            STATUS mandatory
            DESCRIPTION
                "This parameter contains the facilities present in the last 
                 outbound call packet."
        ::= { cdx6500PPSTVoicePortEntry 43 }

        cdx6500VoiceStatsLastOutboundCallPacketCUD OBJECT-TYPE
            SYNTAX DisplayString (SIZE (0..16))
            ACCESS read-only
            STATUS mandatory
            DESCRIPTION
                "This parameter contains the call user data present in the 
                 last outbound call packet."
        ::= { cdx6500PPSTVoicePortEntry 44 }

        cdx6500VoiceStatsRingerStatus OBJECT-TYPE
            SYNTAX INTEGER {
                   rs25Hz (1),
                   rs50Hz (2),
                   na     (100)
                   }
            ACCESS read-only
            STATUS mandatory
            DESCRIPTION
                "This parameter indicates the Ringer status on the board.
                 It is displayed only for DSPM/FXS interfaces.
                 rs25Hz : 25Hz Ringer status on board.
                 rs50Hz : 50Hz Ringer status on board.
                 na     : Value not available."
        ::= { cdx6500PPSTVoicePortEntry 45 }

        cdx6500VoiceStatsDSPMSMSlotNumber OBJECT-TYPE
            SYNTAX INTEGER (0..99)
            ACCESS read-only
            STATUS mandatory
            DESCRIPTION
                "This parameter indicates the slot of the DSPM/SM. It is 
                 displayed only for DSPM/SM interfaces. A value of 0
                 indicates that this parameter is not available."
        ::= { cdx6500PPSTVoicePortEntry 46 }

        cdx6500VoiceStatsDSPMNumber OBJECT-TYPE
            SYNTAX INTEGER (0..4)
            ACCESS read-only
            STATUS mandatory
            DESCRIPTION
                "This parameter indicates the DSP used for the virtual 
                 port.It is displayed only for DSPM/SM interfaces. A value 
                 of 0 indicates that this parameter is not available."
        ::= { cdx6500PPSTVoicePortEntry 47 }

        cdx6500VoiceStatsT1E1PortNumber OBJECT-TYPE
            SYNTAX INTEGER
            ACCESS read-only
            STATUS mandatory
            DESCRIPTION
                "This is the port number of the T1 or E1 port this voice 
                 channel is on.It is displayed only for DSPM/SM interfaces.
                 A value of 0 indicates that this parameter is not available."
        ::= { cdx6500PPSTVoicePortEntry 48 }

        cdx6500VoiceStatsTimeSlotNumber OBJECT-TYPE
            SYNTAX DisplayString 
            ACCESS read-only
            STATUS mandatory
            DESCRIPTION
                "This parameter indicates the time slot number. It is 
                 displayed only for DSPM/SM interfaces. For multiple 
                 time slots it will be displayed as 1,2-5,.."
        ::= { cdx6500PPSTVoicePortEntry 49 }

        cdx6500VoiceStatsDaughterCardRevAndPartNumber OBJECT-TYPE
            SYNTAX DisplayString
            ACCESS read-only
            STATUS mandatory
            DESCRIPTION
                "Hardware revision and part number of the daughter card.The 
                 revision number has format n.n and the part number is an 8 
                 digit number of the form nnnnnnnn.It is displayed only for 
                 DSPM/HC interfaces."
        ::= { cdx6500PPSTVoicePortEntry 50 }

        -- Signaling Sequence Trap Table

        cdx6500PPSTSignalingSequenceTrapTable OBJECT-TYPE
            SYNTAX SEQUENCE OF Cdx6500PPSTSignalingSequenceTrapEntry
            ACCESS not-accessible
            STATUS mandatory
            DESCRIPTION
                "A table containing the Signaling Sequence Trap entries."
        ::= { cdx6500PSTVoicePortTable 2 }

        cdx6500PPSTSignalingSequenceTrapEntry OBJECT-TYPE
            SYNTAX Cdx6500PPSTSignalingSequenceTrapEntry
            ACCESS not-accessible
            STATUS mandatory
            DESCRIPTION
                "An entry in the Signaling Sequence Trap table."
            INDEX { cdx6500SignalingSequenceTrapPortNumber,
                    cdx6500SignalingSequenceTrapEventNumber }
        ::= { cdx6500PPSTSignalingSequenceTrapTable 1 }

        Cdx6500PPSTSignalingSequenceTrapEntry ::=
            SEQUENCE {
               cdx6500SignalingSequenceTrapPortNumber
                   INTEGER,
               cdx6500SignalingSequenceTrapEventNumber
                   INTEGER,
               cdx6500SignalingSequenceTrapTxState
                   DisplayString,
               cdx6500SignalingSequenceTrapRxState
                   DisplayString,
               cdx6500SignalingSequenceTrapMachineState
                   DisplayString,
               cdx6500SignalingSequenceTrapTimeSinceLastChange
                   INTEGER,
               cdx6500SignalingSequenceTrapComment
                   DisplayString
               }

        cdx6500SignalingSequenceTrapPortNumber OBJECT-TYPE
            SYNTAX INTEGER
            ACCESS read-only
            STATUS mandatory
            DESCRIPTION
                "Port number of the Voice Port."
        ::= { cdx6500PPSTSignalingSequenceTrapEntry 1 }

        cdx6500SignalingSequenceTrapEventNumber OBJECT-TYPE
            SYNTAX INTEGER (1..32)
            ACCESS read-only
            STATUS mandatory
            DESCRIPTION
                "Event number in the Signaling Sequence Trap Entry."
        ::= { cdx6500PPSTSignalingSequenceTrapEntry 2 }

        cdx6500SignalingSequenceTrapTxState OBJECT-TYPE
            SYNTAX DisplayString
            ACCESS read-only
            STATUS mandatory
            DESCRIPTION
                "The transmitting voice signalling state is displayed 
                 as ABCD (i.e. 1010)."
        ::= { cdx6500PPSTSignalingSequenceTrapEntry 3 }

        cdx6500SignalingSequenceTrapRxState OBJECT-TYPE
            SYNTAX DisplayString
            ACCESS read-only
            STATUS mandatory
            DESCRIPTION
                "The receiving voice signalling state is displayed 
                 as ABCD (i.e. 1010)."
        ::= { cdx6500PPSTSignalingSequenceTrapEntry 4 }

        cdx6500SignalingSequenceTrapMachineState OBJECT-TYPE
            SYNTAX DisplayString (SIZE (11))
            ACCESS read-only
            STATUS mandatory
            DESCRIPTION
                "The voice signalling state machine state is a 11 character 
                 field representing the state of the signalling software."
        ::= { cdx6500PPSTSignalingSequenceTrapEntry 5 }

        cdx6500SignalingSequenceTrapTimeSinceLastChange OBJECT-TYPE
            SYNTAX INTEGER
            ACCESS read-only
            STATUS mandatory
            DESCRIPTION
                "This parameter indicates the time from the previous state to 
                 this state, measured in milliseconds."
        ::= { cdx6500PPSTSignalingSequenceTrapEntry 6 }

        cdx6500SignalingSequenceTrapComment OBJECT-TYPE
            SYNTAX DisplayString (SIZE (0..16))
            ACCESS read-only
            STATUS mandatory
            DESCRIPTION
                "The comment field is an ASCII string upto 16 characters long."
        ::= { cdx6500PPSTSignalingSequenceTrapEntry 7 }

        END
