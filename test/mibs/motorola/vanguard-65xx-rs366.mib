-- Version 1.5, modified 02/12/98

        RS366-OPT-MIB DEFINITIONS ::= BEGIN

        IMPORTS
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
    cdx6500CfgProtocolGroup OBJECT IDENTIFIER ::= { cdx6500Configuration 1 }
cdx6500PCTPortProtocolGroup OBJECT IDENTIFIER ::= { cdx6500CfgProtocolGroup 1 }

          cdx6500Statistics OBJECT IDENTIFIER ::= { cdx6500 3 }
   cdx6500StatProtocolGroup OBJECT IDENTIFIER ::= { cdx6500Statistics 1 }
cdx6500PSTPortProtocolGroup OBJECT IDENTIFIER ::= { cdx6500StatProtocolGroup 1 }

            cdx6500Controls OBJECT IDENTIFIER ::= { cdx6500 4 }

        -- Textual Conventions

        DisplayString ::= OCTET STRING

        -- RS366 Port Objects

        -- The 6500 RS366 Port Configuration Sub-group
        -- This sub-group belongs to the 6500 Port Protocol Configuration
        -- sub-group. It holds configuration parameters peculiar to the 6500
        -- implementation of the RS366 protocol
  
        cdx6500PPCTRS366PortTable OBJECT-TYPE
            SYNTAX SEQUENCE OF Cdx6500PPCTRS366PortEntry
            ACCESS not-accessible
            STATUS mandatory
            DESCRIPTION
                "A list of RS366 Port configuration entries."
        ::= { cdx6500PCTPortProtocolGroup 21 }

        cdx6500PPCTRS366PortEntry OBJECT-TYPE
            SYNTAX Cdx6500PPCTRS366PortEntry
            ACCESS not-accessible
            STATUS mandatory
            DESCRIPTION
                "An RS366 Configuration Table entry. Each entry
                 contains the configuration parameters for a single
                 RS366 port."
            INDEX { cdx6500RS366CfgPortNumber }
        ::= { cdx6500PPCTRS366PortTable 1 }

        Cdx6500PPCTRS366PortEntry ::=
            SEQUENCE {
                cdx6500RS366CfgPortNumber
                    INTEGER,
                cdx6500RS366CfgADataPortNumber
                    INTEGER,
                cdx6500RS366CfgContXferMode
                    INTEGER,
                cdx6500RS366CfgMaxAddrDigits
                    INTEGER,
                cdx6500RS366CfgMaxRespTime
                    INTEGER
                }

        cdx6500RS366CfgPortNumber OBJECT-TYPE
            SYNTAX INTEGER (1..52)
            ACCESS read-only
            STATUS mandatory
            DESCRIPTION
                "Port Number."
        ::= { cdx6500PPCTRS366PortEntry 1 }

        cdx6500RS366CfgADataPortNumber OBJECT-TYPE
            SYNTAX INTEGER (1..54)
            ACCESS read-only
            STATUS mandatory
            DESCRIPTION
                "Associated Data Port Number"
        ::= { cdx6500PPCTRS366PortEntry 2 }

        cdx6500RS366CfgContXferMode OBJECT-TYPE
            SYNTAX INTEGER {
                    modeNull       (0),
                    modeEon        (1),
                    modeEbt        (2),
                    newvalModeNull (50)
                    }
            ACCESS read-only
            STATUS mandatory
            DESCRIPTION
                "modeEon - Transfer control after end of number digit detected.
                 modeEbt - Transfer control after maximum address digits 
                           accumulated and answerback tone is received.
                 newvalModeNull - same functionality as 'modeNull', new enumeration
                           added for RFC1155 compatibility."
        ::= { cdx6500PPCTRS366PortEntry 3 }

        cdx6500RS366CfgMaxAddrDigits OBJECT-TYPE
            SYNTAX INTEGER (1..15)
            ACCESS read-only
            STATUS mandatory
            DESCRIPTION
                "Number of digits required to transfer control in EBT mode.
                 This parameter is not required in EON mode and it is set to 
                 15 irrespective of the user entry."
        ::= { cdx6500PPCTRS366PortEntry 4 }

        cdx6500RS366CfgMaxRespTime OBJECT-TYPE
            SYNTAX INTEGER {
                    sec0       (0),
                    sec32      (32),
                    sec48      (48),
                    sec96      (96),
                    newvalSec0 (50)
                    }
            ACCESS read-only
            STATUS mandatory
            DESCRIPTION
                "Maximum EIA response time in seconds before a timeout 
                 can occur.
                 sec0  -  Indicates response time out should be disabled.
                 sec32 -  Maximum EIA response time is 32 seconds.
                 sec48 -  Maximum EIA response time is 48 seconds.
                 sec96 -  Maximum EIA response time is 96 seconds.
                 newvalSec0 - same functionality as 'sec0', new enumeration
                          added for RFC1155 compatibility."
        ::= { cdx6500PPCTRS366PortEntry 5 }

        -- The 6500 RS366 Port Statistics Sub-group
        -- This sub-group belongs to the 6500 Port Protocol Statistics
        -- group. It holds statistics  peculiar to the 6500
        -- implementation of the RS366 protocol

        cdx6500PPSTRS366PortTable OBJECT-TYPE
            SYNTAX SEQUENCE OF Cdx6500PPSTRS366PortEntry
            ACCESS not-accessible
            STATUS mandatory
            DESCRIPTION
                "A list of RS366 Port statistics."
        ::= { cdx6500PSTPortProtocolGroup 22 }

        cdx6500PPSTRS366PortEntry OBJECT-TYPE
            SYNTAX Cdx6500PPSTRS366PortEntry
            ACCESS not-accessible
            STATUS mandatory
            DESCRIPTION
                "An RS366 Statistics Table entry. Each entry
                 contains the statistics for a single RS366 port."
            INDEX { cdx6500RS366StatPortNumber }
        ::= { cdx6500PPSTRS366PortTable 1 }

        Cdx6500PPSTRS366PortEntry ::=
            SEQUENCE {
                cdx6500RS366StatPortNumber
                    INTEGER,
                cdx6500RS366StatPortStatus
                    DisplayString,
                cdx6500RS366StatPortState
                    DisplayString,
                cdx6500RS366StatDataNum
                    INTEGER,
                cdx6500RS366StatTotalCalls
                    INTEGER,
                cdx6500RS366StatFailedCalls
                    INTEGER,
                cdx6500RS366StatTotalTimeouts
                    INTEGER,
                cdx6500RS366StatTotalIllegalDigits
                    INTEGER,
                cdx6500RS366StatPortConnected
                    DisplayString
                }

        cdx6500RS366StatPortNumber OBJECT-TYPE
            SYNTAX INTEGER (1..52)
            ACCESS read-only
            STATUS mandatory
            DESCRIPTION
                "Port Number."
        ::= { cdx6500PPSTRS366PortEntry 1 }

        cdx6500RS366StatPortStatus OBJECT-TYPE
            SYNTAX DisplayString
            ACCESS read-only
            STATUS mandatory
            DESCRIPTION
                "Enabled or Disabled."
        ::= { cdx6500PPSTRS366PortEntry 2 }

        cdx6500RS366StatPortState OBJECT-TYPE
            SYNTAX DisplayString
            ACCESS read-only
            STATUS mandatory
            DESCRIPTION
                "Port State."
        ::= { cdx6500PPSTRS366PortEntry 3 }

        cdx6500RS366StatDataNum OBJECT-TYPE
            SYNTAX INTEGER
            ACCESS read-only
            STATUS mandatory
            DESCRIPTION
                "Data Port Number."
        ::= { cdx6500PPSTRS366PortEntry 4 }

        cdx6500RS366StatTotalCalls OBJECT-TYPE
            SYNTAX INTEGER
            ACCESS read-only
            STATUS mandatory
            DESCRIPTION
                "Number of calls made."
        ::= { cdx6500PPSTRS366PortEntry 5 }

        cdx6500RS366StatFailedCalls OBJECT-TYPE
            SYNTAX INTEGER
            ACCESS read-only
            STATUS mandatory
            DESCRIPTION
                "Number of failed calls."
        ::= { cdx6500PPSTRS366PortEntry 6 }

        cdx6500RS366StatTotalTimeouts OBJECT-TYPE
            SYNTAX INTEGER
            ACCESS read-only
            STATUS mandatory
            DESCRIPTION
                "Number of protocol time-outs."
        ::= { cdx6500PPSTRS366PortEntry 7 }

        cdx6500RS366StatTotalIllegalDigits OBJECT-TYPE
            SYNTAX INTEGER
            ACCESS read-only
            STATUS mandatory
            DESCRIPTION
                "Number of illegal digits received."
        ::= { cdx6500PPSTRS366PortEntry 8 }

        cdx6500RS366StatPortConnected OBJECT-TYPE
            SYNTAX DisplayString
            ACCESS read-only
            STATUS mandatory
            DESCRIPTION
                "Connected to Data Port."
        ::= { cdx6500PPSTRS366PortEntry 9 }

        END
