-- Version 1.5, modified 02/12/98

        EIA-OPT-MIB DEFINITIONS ::= BEGIN

        IMPORTS
            OBJECT-TYPE
                FROM RFC-1212;

        -- Codex MIB Group definitions

                      codex OBJECT IDENTIFIER ::= { enterprises 449 }
         cdxProductSpecific OBJECT IDENTIFIER ::= { codex 2 }
                    cdx6500 OBJECT IDENTIFIER ::= { cdxProductSpecific 1 }

      cdx6500Configuration  OBJECT IDENTIFIER ::= { cdx6500 2 }
     cdx6500CfgGeneralGroup OBJECT IDENTIFIER ::= { cdx6500Configuration 2 }

          cdx6500Statistics OBJECT IDENTIFIER ::= { cdx6500 3 }
 cdx6500StatOtherStatsGroup OBJECT IDENTIFIER ::= { cdx6500Statistics 2 }

            cdx6500Controls OBJECT IDENTIFIER ::= { cdx6500 4 }

        -- Textual conventions

        DisplayString ::= OCTET STRING

        -- The EIA Summary Statistics Table
        -- This table contains EIA Summary Statistics of a port

        cdx6500StatEIATable OBJECT-TYPE
            SYNTAX SEQUENCE OF Cdx6500StatEIAEntry
            ACCESS not-accessible
            STATUS mandatory
            DESCRIPTION
                "This table contains EIA Summary Statistics of a port"
        ::= { cdx6500StatOtherStatsGroup 7 }
     
        cdx6500StatEIAEntry OBJECT-TYPE
            SYNTAX Cdx6500StatEIAEntry 
            ACCESS not-accessible
            STATUS mandatory
            DESCRIPTION
                "A list of objects for EIA Summary statistics."
            INDEX { cdx6500StatEIAEntryPortNumber }
        ::= { cdx6500StatEIATable  1 }
    
        Cdx6500StatEIAEntry  ::=
            SEQUENCE  {
                cdx6500StatEIAEntryPortNumber
                    INTEGER,
                cdx6500StatEIAEntryDimType
                    INTEGER,
                cdx6500StatEIAEntryDimCfgn
                    INTEGER,
                cdx6500StatEIAEntryEiaState
                    DisplayString,
                cdx6500StatEIAEntryConnType
                    DisplayString,
                cdx6500StatEIAEntrySignalStatus
                    DisplayString
                }

        cdx6500StatEIAEntryPortNumber OBJECT-TYPE
            SYNTAX INTEGER (1..54)
            ACCESS read-only
            STATUS mandatory
            DESCRIPTION
                "Port number of this port."
        ::= { cdx6500StatEIAEntry 1}

        cdx6500StatEIAEntryDimType OBJECT-TYPE
            SYNTAX INTEGER {
                    dimTypeNone         (0),
                    dimTypeNotInstalled (1),
                    dimTypeEia232d      (2),
                    dimTypeX21          (3),
                    dimTypeV35          (4),
                    dimTypeV36          (5),
                    dimTypeV11          (6),
                    dimTypeEia530       (7),
                    dimTypeDsu          (8),
                    dimTypeI430         (10),
                    newvalDimTypeNone   (50)
                    }
            ACCESS read-only
            STATUS mandatory
            DESCRIPTION
                "The DIM Type for the port.
                 dimTypeNone           :  DIM type is none.
                 dimTypeNotInstalled   :  DIM type is not installed.
                 dimTypeEia232d        :  DIM type is EIA-232-D.
                 dimTypeX21            :  DIM type is X-21.
                 dimTypeV35            :  DIM type is V.35.
                 dimTypeV36            :  DIM type is V.36.
                 dimTypeV11            :  DIM type is V.11.
                 dimTypeEia530         :  DIM type is EIA-530.
                 dimTypeDsu            :  DIM type is DSU.
                 dimTypeI430           :  DIM type is I 430.
                 newvalDimTypeNone     :  same as 'dimTypeNone', new
                                          enumeration added for RFC1155
                                          compatibility."
        ::= { cdx6500StatEIAEntry 2}

        cdx6500StatEIAEntryDimCfgn OBJECT-TYPE
            SYNTAX INTEGER {
                    dimCfgnDte       (0),
                    dimCfgnDce       (1),
                    newvalDimCfgnDte (50)
                    }
            ACCESS read-only
            STATUS mandatory
            DESCRIPTION
                "The DIM Configuration for the port.
                 dimCfgnDte        : DIM Configuration is DTE.
                 dimCfgnDce        : DIM Configuration is DCE.
                 newvalDimCfgnNone : same functionality as 'dimTypeNone',
                                     new enumeration added for RFC1155
                                     compatibility."
        ::= { cdx6500StatEIAEntry 3 }

        cdx6500StatEIAEntryEiaState OBJECT-TYPE
            SYNTAX DisplayString
            ACCESS read-only
            STATUS mandatory
            DESCRIPTION
                "The EIA State for the port."
        ::= { cdx6500StatEIAEntry 4 }

        cdx6500StatEIAEntryConnType OBJECT-TYPE
            SYNTAX DisplayString
            ACCESS read-only
            STATUS mandatory
            DESCRIPTION
                "The EIA Connection Type."
        ::= { cdx6500StatEIAEntry  5 }

        cdx6500StatEIAEntrySignalStatus OBJECT-TYPE
            SYNTAX DisplayString
            ACCESS read-only
            STATUS mandatory
            DESCRIPTION
                "The Status of the EIA Signal levels for the port
                 with that combination of DIMTYPE and DIMCFGN."
        ::= { cdx6500StatEIAEntry  6 }

        -- Vanguard ISDN related objects

        isgVGIsdnEIAStatTable OBJECT-TYPE
            SYNTAX SEQUENCE OF IsgVGIsdnEIAStatEntry
            ACCESS not-accessible
            STATUS mandatory
            DESCRIPTION
                "This table contains EIA Summary Statistics of a port."
        ::= { cdx6500StatOtherStatsGroup 8 }
             
        isgVGIsdnEIAStatEntry OBJECT-TYPE
            SYNTAX IsgVGIsdnEIAStatEntry
            ACCESS not-accessible
            STATUS mandatory
            DESCRIPTION
                "A list of objects for ISDN EIA Summary statistics."
            INDEX { isgVGIsdnEIAStatPortNum }
        ::= { isgVGIsdnEIAStatTable 1 }
    
        IsgVGIsdnEIAStatEntry ::=
            SEQUENCE  {
                isgVGIsdnEIAStatPortNum
                    INTEGER,
                isgVGIsdnEIAStatDimType
                    INTEGER,
                isgVGIsdnEIAStatDimCfgn
                    INTEGER,
                isgVGIsdnEIAStatTEI
                    DisplayString,
                isgVGIsdnEIAStatSPBU
                    INTEGER,
                isgVGIsdnEIAStatL1State
                    INTEGER,
                isgVGIsdnEIAStatChanType
                    INTEGER,
                isgVGIsdnEIAStatAccType
                    INTEGER
                }

        isgVGIsdnEIAStatPortNum OBJECT-TYPE
            SYNTAX INTEGER
            ACCESS read-only
            STATUS mandatory
            DESCRIPTION
                "Port number of this port."
        ::= { isgVGIsdnEIAStatEntry 1 }

        isgVGIsdnEIAStatDimType OBJECT-TYPE
            SYNTAX INTEGER {
                    dimTypeIsdn (9)
                    }
            ACCESS read-only
            STATUS mandatory
            DESCRIPTION
                "The DIM Type for the port."
        ::= { isgVGIsdnEIAStatEntry 2 }

        isgVGIsdnEIAStatDimCfgn OBJECT-TYPE
            SYNTAX INTEGER {
                    dimIsdnST       (0),
                    dimIsdnU        (1),
                    newvalDimIsdnST (50)
                    }
            ACCESS read-only
            STATUS mandatory
            DESCRIPTION
                "The DIM Configuration for the port.
                 dimIsdnST       :  ISDN  ST  interface.
                 dimIsdnU        :  ISDN  U   interface.
                 newvalDimIsdnST : same as 'dimIsdnST', new enumeration
                                   added for RFC1155 compatibility."
        ::= { isgVGIsdnEIAStatEntry 3 }

        isgVGIsdnEIAStatTEI OBJECT-TYPE
            SYNTAX DisplayString
            ACCESS read-only
            STATUS mandatory
            DESCRIPTION
                "The Terminal Endpoint Indicator for the port."
        ::= { isgVGIsdnEIAStatEntry 4 }

        isgVGIsdnEIAStatSPBU OBJECT-TYPE
            SYNTAX INTEGER {
                    main       (0),
                    backup     (1),
                    disabled   (2),
                    newvalMain (50)
                    }
            ACCESS read-only
            STATUS mandatory
            DESCRIPTION
                "The Same Port Backup feature for the port.
                 newvalMain : same functionality as 'main', new enumeration
                 added for RFC1155 compatibility."
        ::= { isgVGIsdnEIAStatEntry 5 }

        isgVGIsdnEIAStatL1State OBJECT-TYPE
            SYNTAX INTEGER {
                    l1Setup       (0),
                    l1Deactive    (1),
                    l1Active      (2),
                    l1B1Loop      (3),
                    l1B2Loop      (4),
                    l1B1B2Loop    (5),
                    l12BDLoop     (6),
                    unknownState  (7),
                    newvalL1Setup (50)
                    }
            ACCESS read-only
            STATUS mandatory
            DESCRIPTION
                "The Level 1 State for the port.
                 l1Setup    : Setup State.
                 l1Deactive : Inactive State.
                 l1Active   : Active State.
                 l1B1Loop   : Loop Test State.
                 l1B2Loop   : Loop Test State.
                 l1B1B2Loop : Loop Test State.
                 l12BDLoop  : Loop Test State.
                 newvalL1Setup : same functionality as 'l1Setup', new
                 enumeration added for RFC1155 compatibility."
        ::= { isgVGIsdnEIAStatEntry 6 }

        isgVGIsdnEIAStatChanType OBJECT-TYPE
            SYNTAX INTEGER {
                    error       (0),
                    isdnD       (1),
                    isdnB1      (2),
                    isdnB2      (3),
                    isdn2B      (4),
                    isdnB       (5),
                    newvalError (50)
                    }
            ACCESS read-only
            STATUS mandatory
            DESCRIPTION
                "ISDN Channel Type.
                 newvalError : same functionaliy as 'error', new enumeration
                 added for RFC1155 compatibility."
        ::= { isgVGIsdnEIAStatEntry 7 }

        isgVGIsdnEIAStatAccType OBJECT-TYPE
            SYNTAX INTEGER {
                    permanent       (0),
                    cktMode         (1),
                    pktMode         (2),
                    dPckEnabled     (3),
                    dPckDisabled    (4),
                    notConnected    (5),
                    newvalPermanent (50)
                    }
            ACCESS read-only
            STATUS mandatory
            DESCRIPTION
                "ISDN Channel Access Type.
                 Value not available for D Channels.
                 permanent       : Access type permanent.
                 cktMode         : Access type circuit mode.
                 pktMode         : Access type packet mode.
                 dPckEnabled     : Access type D packet enabled.
                 dPckDisabled    : Access type D packet disabled.
                 notConnected    : Not connected.
                 newvalPermanent : same functionality as 'permanent', new
                                   enumeration added for RFC1155 compatibility."
        ::= { isgVGIsdnEIAStatEntry 8 }

        END
