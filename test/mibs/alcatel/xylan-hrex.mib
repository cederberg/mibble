XYLAN-HREX-MIB DEFINITIONS ::= BEGIN

     --  xylan-hrex.mib
     --  Revision: 1.0
     --  Date: December 1999

     --  Alcatel Internetworking, Inc.
     --  26801 W. Agoura Road
     --  Calabasas, CA 91301
     --  (818) 880-3500
     --  support@ind.alcatel.com

     --  This module provides authoritative definitions for Alcatel Internetworking, Inc.
     --  HRE-X.

     --  This module will be extended, as needed.

     --  Alcatel Internetworking, Inc. reserves the right to make changes in 
     --  specification and other information contained in this document 
     --  without prior notice.  The reader should consult Alcatel Internetworking,
     --  Inc. to determine whether any such changes have been made.
     --  Current MIBs are availible from the following URLs:
     --			ftp://ftp.ind.alcatel.com/pub/products/mibs
     --			http://www.ind.alcatel.com

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1998, Alcatel Internetworking, Inc. All Rights Reserved.

     
     	IMPORTS
		OBJECT-TYPE
			FROM RFC-1212
		Counter
      			FROM RFC1155-SMI
	        xylanHrexArch
			FROM XYLAN-BASE-MIB 
			;

--
--

xylanHrexRegisterTable OBJECT-TYPE
  SYNTAX       SEQUENCE OF HrexRegisterEntry
  ACCESS       not-accessible
  STATUS       mandatory
  DESCRIPTION  "Entry for an HRE-X Router Port MAC register."
  ::= {xylanHrexArch 1}

xylanHrexRegisterEntry OBJECT-TYPE
  SYNTAX      HrexRegisterEntry
  ACCESS      not-accessible
  STATUS      mandatory
  DESCRIPTION "Each entry corresponds to a single register."
  INDEX       {
              xylanHrexRegisterNumber
              }
  ::= {xylanHrexRegisterTable 1}

HrexRegisterEntry ::= SEQUENCE {
                xylanHrexRegisterNumber INTEGER,
		xylanHrexRegisterAllowType INTEGER,
		xylanHrexRegisterUseType INTEGER
                }

xylanHrexRegisterNumber OBJECT-TYPE
  SYNTAX  INTEGER       (1..3)
  ACCESS  read-only
  STATUS  mandatory
  DESCRIPTION   "The number of the HRE-X Router Port MAC register."
  ::= { xylanHrexRegisterEntry 1 }

xylanHrexRegisterAllowType OBJECT-TYPE
   SYNTAX       INTEGER        {
			       invalid (0),
                               any  (1),
                               cip  (2),
                               m013 (3),
                               mpoa (4),
                               routing (5),
                               vrrp (6)
                               }
   ACCESS       read-write
   STATUS       mandatory
   DESCRIPTION  "The service type that is permitted for the HRE-X Router
                 Router Port MAC register."
   ::= {xylanHrexRegisterEntry 2}

xylanHrexRegisterUseType OBJECT-TYPE
   SYNTAX       INTEGER        {
			       invalid (0),
                               unused  (1),
                               cip  (2),
                               m013 (3),
                               mpoa (4),
                               routing (5),
                               vrrp (6)
                               }
   ACCESS       read-only
   STATUS       mandatory
   DESCRIPTION  "The service type to which the register has been allocated."
   ::= {xylanHrexRegisterEntry 3}

xylanHrexStatistics OBJECT IDENTIFIER ::= { xylanHrexArch 2 }

xylanHrexIpPacketsReceived OBJECT-TYPE
	SYNTAX Counter 
	ACCESS read-only
	STATUS mandatory
	DESCRIPTION "The count of IP packets received by the HRE-Xs."
	::= { xylanHrexStatistics 1 }

xylanHrexIpPacketsForwarded OBJECT-TYPE
	SYNTAX Counter 
	ACCESS read-only
	STATUS mandatory
	DESCRIPTION "The count of IP packets forwarded by the HRE-Xs."
	::= { xylanHrexStatistics 2 }

xylanHrexIpPacketsDiscarded OBJECT-TYPE
	SYNTAX Counter 
	ACCESS read-only
	STATUS mandatory
	DESCRIPTION "The count of IP packets discarded by the HRE-Xs."
	::= { xylanHrexStatistics 3 }

xylanHrexIpxPacketsReceived OBJECT-TYPE
	SYNTAX Counter 
	ACCESS read-only
	STATUS mandatory
	DESCRIPTION "The count of IPX packets received by the HRE-Xs."
	::= { xylanHrexStatistics 4 }

xylanHrexIpxPacketsForwarded OBJECT-TYPE
	SYNTAX Counter 
	ACCESS read-only
	STATUS mandatory
	DESCRIPTION "The count of IPX packets forwarded by the HRE-Xs."
	::= { xylanHrexStatistics 5 }

xylanHrexIpxPacketsDiscarded OBJECT-TYPE
	SYNTAX Counter 
	ACCESS read-only
	STATUS mandatory
	DESCRIPTION "The count of IPX packets discarded by the HRE-Xs."
	::= { xylanHrexStatistics 6 }

xylanHrexUtilization OBJECT IDENTIFIER ::= { xylanHrexArch 3 }

xylanHrexPseudoCamHashTotal OBJECT-TYPE
	SYNTAX Counter 
	ACCESS read-only
	STATUS mandatory
	DESCRIPTION "The total number of HRE-X PseudoCAM hash entries that are 
	             configured for use."
	::= { xylanHrexUtilization 1 }

xylanHrexPseudoCamHashFree OBJECT-TYPE
	SYNTAX Counter 
	ACCESS read-only
	STATUS mandatory
	DESCRIPTION "The total number of HRE-X PseudoCAM hash entries that are 
	             currently not in use."
	::= { xylanHrexUtilization 2 }

xylanHrexPseudoCamCollisionTotal OBJECT-TYPE
	SYNTAX Counter 
	ACCESS read-only
	STATUS mandatory
	DESCRIPTION "The total number of HRE-X PseudoCAM collision entries 
	            that are configured for use."
	::= { xylanHrexUtilization 3 }

xylanHrexPseudoCamCollisionFree OBJECT-TYPE
	SYNTAX Counter 
	ACCESS read-only
	STATUS mandatory
	DESCRIPTION "The total number of HRE-X PseudoCAM collision entries 
	            that are currently not in use."
	::= { xylanHrexUtilization 4 }

xylanHrexCacheTotal OBJECT-TYPE
	SYNTAX Counter 
	ACCESS read-only
	STATUS mandatory
	DESCRIPTION "The total number of HRE-X Cache entries that are 
	            configured for use."
	::= { xylanHrexUtilization 5 }

xylanHrexCacheFree OBJECT-TYPE
	SYNTAX Counter 
	ACCESS read-only
	STATUS mandatory
	DESCRIPTION "The total number of HRE-X cache entries that are 
	            currently not in use."
	::= { xylanHrexUtilization 6 }

xylanHrexCollisionLengthMax OBJECT-TYPE
	SYNTAX Counter 
	ACCESS read-only
	STATUS mandatory
	DESCRIPTION "The longest collision chain currently in use in the
	            HRE-X."
	::= { xylanHrexUtilization 7 }

xylanHrexCollisionLengthAvg OBJECT-TYPE
	SYNTAX Counter 
	ACCESS read-only
	STATUS mandatory
	DESCRIPTION "The average collision chain length currently in use in the
	            HRE-X."
	::= { xylanHrexUtilization 8 }

xylanHrexHash OBJECT IDENTIFIER ::= { xylanHrexArch 4 }

xylanHrexHashOptimize OBJECT-TYPE
        SYNTAX INTEGER 
        ACCESS  write-only
        STATUS  mandatory
        DESCRIPTION "Causes the switch to compute an optimized hash function
	            for the HRE-X PseudoCAM and to program this into the 
                    HRE-X(s)."
	::= { xylanHrexHash 1 }

xylanHrexHashDefault OBJECT-TYPE
        SYNTAX INTEGER 
        ACCESS  write-only
        STATUS  mandatory
        DESCRIPTION "Causes the switch to restore the hash function for the 
	            HRE-X PseudoCAM to the default value and to program this
	            into the HRE-X(s)."
	::= { xylanHrexHash 2 }

END
