XYLAN-SONET-MIB DEFINITIONS ::= BEGIN


          IMPORTS
              OBJECT-TYPE
                    FROM RFC-1212
              ifIndex
                    FROM RFC1213-MIB
              xylanSonetArch
                    FROM XYLAN-BASE-MIB;


     xylanSonetErrConfig  OBJECT IDENTIFIER  ::=  { xylanSonetArch 1 }


          -- This is the Alcatel Internetworking, Inc. proprietary MIB module for 
          -- configuring the SONET/SDH Error Statistics gathering


          -- the SONET Error Collection configuration group


          xylanSonetTable OBJECT-TYPE
              SYNTAX  SEQUENCE OF XylanSonetEntry
              ACCESS  not-accessible
              STATUS  mandatory
              DESCRIPTION

                 "The SONET error statistics gathering configuration table."
               ::= { xylanSonetErrConfig 1 }


          xylanSonetEntry OBJECT-TYPE
              SYNTAX  XylanSonetEntry
              ACCESS  not-accessible
              STATUS  mandatory
              DESCRIPTION
                 "An entry in the SONET/SDH Medium table."
              INDEX   { ifIndex }
               ::= { xylanSonetTable 1 }


          XylanSonetEntry ::=
              SEQUENCE {
                   xylanSonetStatsEnable         INTEGER,
                   xylanSonetNumOfSamples        INTEGER,
                   xylanSonetClearCurrentSample  INTEGER
               }


          xylanSonetStatsEnable OBJECT-TYPE
              SYNTAX  INTEGER  {
                         enable(1),
                         disable(2)
                      }
              ACCESS  read-write
              STATUS  mandatory
              DESCRIPTION
                 "A value that indicates whether the SONET error
                 statistics is enabled or not."
              ::= { xylanSonetEntry 1 }


          xylanSonetNumOfSamples OBJECT-TYPE
              SYNTAX  INTEGER (4..96)
              ACCESS  read-write
              STATUS  mandatory
              DESCRIPTION
                 "The number of samples to be stored in the interval tables.
                  This variable can be set only if Sonet Error Collection
                  is enabled on the interface."
              ::= { xylanSonetEntry 2 }


          xylanSonetClearCurrentSample OBJECT-TYPE
              SYNTAX  INTEGER (0..31)
              ACCESS  read-write
              STATUS  mandatory
              DESCRIPTION
                 "This variable indicates which layer error statistics are 
                 to be cleared. When this variable is set, the corresponding 
                 current interval sample will be cleared. 
                 The xylanSonetClearCurrentSample is a bit map represented 
                 as a sum. So multiple tables can be cleared by one set. 

                 The bit positions are :
                     0   None
                     1   Section
                     2   Line
                     4   FarEndLine
                     8   Path
                     16  FarEndPath
                     31  All"
              ::= { xylanSonetEntry 3 }

     xylanSonetErrGroup  OBJECT IDENTIFIER  ::=  { xylanSonetArch 3 }

         xylanSonetSlotIndex OBJECT-TYPE
             SYNTAX   INTEGER (0..9)
             ACCESS   not-accessible
             STATUS   mandatory
             DESCRIPTION
                "A unique value which identifies this switch slot."
             ::= { xylanSonetErrGroup 1 }

         xylanSonetPortIndex OBJECT-TYPE
             SYNTAX   INTEGER (0..9)
             ACCESS   not-accessible
             STATUS   mandatory
             DESCRIPTION
                "A unique value which identifies this switch slot/port."
             ::= { xylanSonetErrGroup 2 }

         xylanSonetHardwareIndex OBJECT-TYPE
             SYNTAX   INTEGER
             ACCESS   not-accessible
             STATUS   mandatory
             DESCRIPTION
                "A unique value which identifies the hardware on the 
                switch slot/port where the error has occured"
             ::= { xylanSonetErrGroup 3 }

         xylanSonetErrType OBJECT-TYPE
             SYNTAX   INTEGER
             ACCESS   not-accessible
             STATUS   mandatory
             DESCRIPTION
                "A unique value which identifies the type of AIS error
                that has occured on the Sonet hardware."
             ::= { xylanSonetErrGroup 4 }

END
