--  Copyright (C) 2001 Alcatel Internetworking, Inc., all rights reserved.
--
--           Xylan Private Network-Network Interface MIB ASN.1 
--           Specification
--
-- File:        xylan-ipms-static.mib
--
-- Purpose:     Specifies Xylan's STATIC MIB definitions used only
--              to LOAD/ENABLE the IP Multicast Manager Software.
--		(Once the software is loaded/enabled, a fully-fledged
--		"dynamic" mib takes over.)
--
-- Conformance: Created proprietary MIB to address specific needs of
--              Xylan. This MIB does not attempt to conform to 
--              any existing MIBS.
--
-- Background:  The MIB is proprietary and bears no resemblance
--              to other MIBS.
--
--              History
--              =======
--              7/16/01    cpc  Hacked from xylan-ipms.mib
--
--

IPMS-MIB DEFINITIONS ::= BEGIN
 
IMPORTS
    OBJECT-TYPE             FROM RFC-1212
    xylanIpmsArch           FROM XYLAN-BASE-MIB;

    ipmsStaticMIB OBJECT IDENTIFIER ::= { xylanIpmsArch 1 }

    ipmsStaticMIBObjects OBJECT IDENTIFIER ::= { ipmsStaticMIB 1 }


--  The General Group **********************************************

ipmsStaticGeneralGroup OBJECT IDENTIFIER ::= { ipmsStaticMIBObjects 1 }

ipmsStaticState  OBJECT-TYPE                           
        SYNTAX        INTEGER {
            enabled(1),
            disabled(2)
            }
        ACCESS        read-write
        STATUS        mandatory
        DESCRIPTION
            "The current state of IPMS."
        ::= { ipmsStaticGeneralGroup 2 }

END
