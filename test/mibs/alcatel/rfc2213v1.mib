INTEGRATED-SERVICES-MIB DEFINITIONS ::= BEGIN

IMPORTS
--    TruthValue
--        FROM RFC1253-MIB
    OBJECT-TYPE
        FROM RFC-1212
    Counter
        FROM RFC1155-SMI
--    InterfaceIndex, ifIndex
--        FROM IF-MIB
    ifIndex
        FROM RFC1213-MIB
    RowStatus, TestAndIncr
        FROM SNMPv2-TC
    mib-2, Gauge32
        FROM SNMPv2-SMI;

-- created from intSrv (9511030500Z)

-- Added locally by David Morgan
TruthValue ::= INTEGER { true(1), false(2) }
InterfaceIndex ::= INTEGER

intSrv OBJECT IDENTIFIER ::= { mib-2  52 }

intSrvObjects OBJECT IDENTIFIER ::= { intSrv  1 }

intSrvGenObjects OBJECT IDENTIFIER ::= { intSrv  2 }

intSrvNotifications OBJECT IDENTIFIER ::= { intSrv  3 }

intSrvConformance OBJECT IDENTIFIER ::= { intSrv  4 }

SessionNumber ::=
    INTEGER

Protocol ::=
    INTEGER

SessionType ::=
    INTEGER

Port ::=
    OCTET STRING

MessageSize ::=
    INTEGER

BitRate ::=
    INTEGER

BurstSize ::=
    INTEGER

QosService ::=
    INTEGER {
 bestEffort(1),
 guaranteedDelay(2),
 controlledLoad(5)
 }

intSrvIfAttribTable OBJECT-TYPE
    SYNTAX  SEQUENCE OF IntSrvIfAttribEntry
    ACCESS  not-accessible
    STATUS  mandatory
    DESCRIPTION
           "The reservable attributes of the system's  in-
           terfaces."
    ::= { intSrvObjects  1 }

intSrvIfAttribEntry OBJECT-TYPE
    SYNTAX  IntSrvIfAttribEntry
    ACCESS  not-accessible
    STATUS  mandatory
    DESCRIPTION
           "The reservable attributes of  a  given  inter-
           face."
    INDEX   { ifIndex }
    ::= { intSrvIfAttribTable  1 }

IntSrvIfAttribEntry ::=
    SEQUENCE {
        intSrvIfAttribAllocatedBits
            BitRate,

        intSrvIfAttribMaxAllocatedBits
            BitRate,

        intSrvIfAttribAllocatedBuffer
            BurstSize,

        intSrvIfAttribFlows
            Gauge32,

        intSrvIfAttribPropagationDelay
            INTEGER (-2147483648..2147483647),

        intSrvIfAttribStatus
            RowStatus
    }

intSrvIfAttribAllocatedBits OBJECT-TYPE
    SYNTAX  BitRate	-- UNITS Bits per second

    ACCESS  read-only
    STATUS  mandatory
    DESCRIPTION
           "The number of bits/second currently  allocated
           to reserved sessions on the interface."
    ::= { intSrvIfAttribEntry  1 }

intSrvIfAttribMaxAllocatedBits OBJECT-TYPE
    SYNTAX  BitRate	-- UNITS Bits per second

    ACCESS  read-write
    STATUS  mandatory
    DESCRIPTION
           "The maximum number of bits/second that may  be
           allocated  to  reserved  sessions on the inter-
           face."
    ::= { intSrvIfAttribEntry  2 }

intSrvIfAttribAllocatedBuffer OBJECT-TYPE
    SYNTAX  BurstSize	-- UNITS Bytes

    ACCESS  read-only
    STATUS  mandatory
    DESCRIPTION
           "The amount of buffer space  required  to  hold
           the simultaneous burst of all reserved flows on
           the interface."
    ::= { intSrvIfAttribEntry  3 }

intSrvIfAttribFlows OBJECT-TYPE
    SYNTAX  Gauge32
    ACCESS  read-only
    STATUS  mandatory
    DESCRIPTION
           "The number of reserved flows currently  active
           on  this  interface.  A flow can be created ei-
           ther from a reservation protocol (such as  RSVP
           or ST-II) or via configuration information."
    ::= { intSrvIfAttribEntry  4 }

intSrvIfAttribPropagationDelay OBJECT-TYPE
    SYNTAX  INTEGER (-2147483648..2147483647)	-- UNITS microseconds

    ACCESS  read-write
    STATUS  mandatory
    DESCRIPTION
           "The amount of propagation delay that this  in-
           terface  introduces  in addition to that intro-
           diced by bit propagation delays."
    DEFVAL  { 0 }
    ::= { intSrvIfAttribEntry  5 }

intSrvIfAttribStatus OBJECT-TYPE
    SYNTAX  RowStatus
    ACCESS  read-write
    STATUS  mandatory
    DESCRIPTION
           "'active' on interfaces that are configured for
           RSVP."
    ::= { intSrvIfAttribEntry  6 }

intSrvFlowTable OBJECT-TYPE
    SYNTAX  SEQUENCE OF IntSrvFlowEntry
    ACCESS  not-accessible
    STATUS  mandatory
    DESCRIPTION
           "Information describing the reserved flows  us-
           ing the system's interfaces."
    ::= { intSrvObjects  2 }

intSrvFlowEntry OBJECT-TYPE
    SYNTAX  IntSrvFlowEntry
    ACCESS  not-accessible
    STATUS  mandatory
    DESCRIPTION
           "Information describing the use of a given  in-
           terface   by   a   given   flow.   The  counter
           intSrvFlowPoliced starts counting  at  the  in-
           stallation of the flow."
    INDEX   { intSrvFlowNumber }
    ::= { intSrvFlowTable  1 }

IntSrvFlowEntry ::=
    SEQUENCE {
        intSrvFlowNumber
            SessionNumber,

        intSrvFlowType
            SessionType,

        intSrvFlowOwner
            INTEGER,

        intSrvFlowDestAddr
            OCTET STRING,

        intSrvFlowSenderAddr
            OCTET STRING,

        intSrvFlowDestAddrLength
            INTEGER,

        intSrvFlowSenderAddrLength
            INTEGER,

        intSrvFlowProtocol
            Protocol,

        intSrvFlowDestPort
            Port,

        intSrvFlowPort
            Port,

        intSrvFlowFlowId
            INTEGER,

        intSrvFlowInterface
            InterfaceIndex,

        intSrvFlowIfAddr
            OCTET STRING,

        intSrvFlowRate
            BitRate,

        intSrvFlowBurst
            BurstSize,

        intSrvFlowWeight
            INTEGER (-2147483648..2147483647),

        intSrvFlowQueue
            INTEGER (-2147483648..2147483647),

        intSrvFlowMinTU
            MessageSize,

        intSrvFlowMaxTU
            MessageSize,

        intSrvFlowBestEffort
            Counter,

        intSrvFlowPoliced
            Counter,

        intSrvFlowDiscard
            TruthValue,

        intSrvFlowService
            QosService,

        intSrvFlowOrder
            INTEGER,

        intSrvFlowStatus
            RowStatus
    }

intSrvFlowNumber OBJECT-TYPE
    SYNTAX  SessionNumber
    ACCESS  not-accessible
    STATUS  mandatory
    DESCRIPTION
           "The number of this flow.  This is for SNMP In-
           dexing purposes only and has no relation to any
           protocol value."
    ::= { intSrvFlowEntry  1 }

intSrvFlowType OBJECT-TYPE
    SYNTAX  SessionType
    ACCESS  read-write
    STATUS  mandatory
    DESCRIPTION
           "The type of session (IP4, IP6, IP6  with  flow
           information, etc)."
    ::= { intSrvFlowEntry  2 }

intSrvFlowOwner OBJECT-TYPE
    SYNTAX  INTEGER {
                 other(1),
                 rsvp(2),
                 management(3)
               }
    ACCESS  read-write
    STATUS  mandatory
    DESCRIPTION
           "The process that installed this  flow  in  the
           queue policy database."
    ::= { intSrvFlowEntry  3 }

intSrvFlowDestAddr OBJECT-TYPE
    SYNTAX  OCTET STRING
    ACCESS  read-write
    STATUS  mandatory
    DESCRIPTION
           "The destination address used by all senders in
           this  session.   This object may not be changed
           when the value of the RowStatus object is  'ac-
           tive'."
    ::= { intSrvFlowEntry  4 }

intSrvFlowSenderAddr OBJECT-TYPE
    SYNTAX  OCTET STRING
    ACCESS  read-write
    STATUS  mandatory
    DESCRIPTION
           "The source address of the sender  selected  by
           this  reservation.  The value of all zeroes in-
           dicates 'all senders'.  This object may not  be
           changed  when the value of the RowStatus object
           is 'active'."
    ::= { intSrvFlowEntry  5 }

intSrvFlowDestAddrLength OBJECT-TYPE
    SYNTAX  INTEGER
    ACCESS  read-write
    STATUS  mandatory
    DESCRIPTION
           "The length of the destination address in bits.
           This  is  the CIDR Prefix Length, which for IP4
           hosts and multicast addresses is 32 bits.  This
           object may not be changed when the value of the
           RowStatus object is 'active'."
    ::= { intSrvFlowEntry  6 }

intSrvFlowSenderAddrLength OBJECT-TYPE
    SYNTAX  INTEGER
    ACCESS  read-write
    STATUS  mandatory
    DESCRIPTION
           "The length of the sender's  address  in  bits.
           This  is  the CIDR Prefix Length, which for IP4
           hosts and multicast addresses is 32 bits.  This
           object may not be changed when the value of the
           RowStatus object is 'active'."
    ::= { intSrvFlowEntry  7 }

intSrvFlowProtocol OBJECT-TYPE
    SYNTAX  Protocol
    ACCESS  read-write
    STATUS  mandatory
    DESCRIPTION
           "The IP Protocol used by a session.   This  ob-
           ject  may  not be changed when the value of the
           RowStatus object is 'active'."
    ::= { intSrvFlowEntry  8 }

intSrvFlowDestPort OBJECT-TYPE
    SYNTAX  Port
    ACCESS  read-write
    STATUS  mandatory
    DESCRIPTION
           "The UDP or TCP port number used as a  destina-
           tion  port for all senders in this session.  If
           the  IP   protocol   in   use,   specified   by
           intSrvResvFwdProtocol,  is 50 (ESP) or 51 (AH),
           this  represents  a  virtual  destination  port
           number.   A value of zero indicates that the IP
           protocol in use does not have ports.  This  ob-
           ject  may  not be changed when the value of the
           RowStatus object is 'active'."
    ::= { intSrvFlowEntry  9 }

intSrvFlowPort OBJECT-TYPE
    SYNTAX  Port
    ACCESS  read-write
    STATUS  mandatory
    DESCRIPTION
           "The UDP or TCP port number used  as  a  source
           port  for  this sender in this session.  If the
           IP    protocol    in    use,    specified    by
           intSrvResvFwdProtocol  is  50 (ESP) or 51 (AH),
           this represents a generalized  port  identifier
           (GPI).   A  value of zero indicates that the IP
           protocol in use does not have ports.  This  ob-
           ject  may  not be changed when the value of the
           RowStatus object is 'active'."
    ::= { intSrvFlowEntry  10 }

intSrvFlowFlowId OBJECT-TYPE
    SYNTAX  INTEGER
    ACCESS  read-only
    STATUS  mandatory
    DESCRIPTION
           "The flow ID that  this  sender  is  using,  if
           this  is  an IPv6 session."
    ::= { intSrvFlowEntry  11 }

intSrvFlowInterface OBJECT-TYPE
    SYNTAX  InterfaceIndex
    ACCESS  read-write
    STATUS  mandatory
    DESCRIPTION
           "The ifIndex value of the  interface  on  which
           this reservation exists."
    ::= { intSrvFlowEntry  12 }

intSrvFlowIfAddr OBJECT-TYPE
    SYNTAX  OCTET STRING
    ACCESS  read-write
    STATUS  mandatory
    DESCRIPTION
           "The IP Address on the ifEntry  on  which  this
           reservation  exists.  This is present primarily
           to support those interfaces which layer  multi-
           ple IP Addresses on the interface."
    ::= { intSrvFlowEntry  13 }

intSrvFlowRate OBJECT-TYPE
    SYNTAX  BitRate	-- UNITS bits per second

    ACCESS  read-write
    STATUS  mandatory
    DESCRIPTION
           "The Reserved Rate of the sender's data stream.
           If this is a Controlled Load service flow, this
           rate is derived from the Tspec  rate  parameter
           (r).   If  this  is  a Guaranteed service flow,
           this rate is derived from  the  Rspec  clearing
           rate parameter (R)."
    ::= { intSrvFlowEntry  14 }

intSrvFlowBurst OBJECT-TYPE
    SYNTAX  BurstSize	-- UNITS bytes

    ACCESS  read-write
    STATUS  mandatory
    DESCRIPTION
           "The size of the largest  burst  expected  from
           the sender at a time.


           If this is less than  the  sender's  advertised
           burst  size, the receiver is asking the network
           to provide flow pacing  beyond  what  would  be
           provided  under normal circumstances. Such pac-
           ing is at the network's option."
    ::= { intSrvFlowEntry  15 }

intSrvFlowWeight OBJECT-TYPE
    SYNTAX  INTEGER (-2147483648..2147483647)
    ACCESS  read-write
    STATUS  mandatory
    DESCRIPTION
           "The weight used  to  prioritize  the  traffic.
           Note  that the interpretation of this object is
           implementation-specific,   as   implementations
           vary in their use of weighting procedures."
    ::= { intSrvFlowEntry  16 }

intSrvFlowQueue OBJECT-TYPE
    SYNTAX  INTEGER (-2147483648..2147483647)
    ACCESS  read-write
    STATUS  mandatory
    DESCRIPTION
           "The number of the queue used by this  traffic.
           Note  that the interpretation of this object is
           implementation-specific,   as   implementations
           vary in their use of queue identifiers."
    ::= { intSrvFlowEntry  17 }

intSrvFlowMinTU OBJECT-TYPE
    SYNTAX  MessageSize
    ACCESS  read-write
    STATUS  mandatory
    DESCRIPTION
           "The minimum message size for  this  flow.  The
           policing  algorithm will treat smaller messages
           as though they are this size."
    ::= { intSrvFlowEntry  18 }

intSrvFlowMaxTU OBJECT-TYPE
    SYNTAX  MessageSize
    ACCESS  read-write
    STATUS  mandatory
    DESCRIPTION
           "The maximum datagram size for this  flow  that
           will conform to the traffic specification. This
           value cannot exceed the MTU of the interface."
    ::= { intSrvFlowEntry  19 }

intSrvFlowBestEffort OBJECT-TYPE
    SYNTAX  Counter
    ACCESS  read-only
    STATUS  mandatory
    DESCRIPTION
           "The number of packets that  were  remanded  to
           best effort service."
    ::= { intSrvFlowEntry  20 }

intSrvFlowPoliced OBJECT-TYPE
    SYNTAX  Counter
    ACCESS  read-only
    STATUS  mandatory
    DESCRIPTION
           "The number of packets policed since the incep-
           tion of the flow's service."
    ::= { intSrvFlowEntry  21 }

intSrvFlowDiscard OBJECT-TYPE
    SYNTAX  TruthValue
    ACCESS  read-write
    STATUS  mandatory
    DESCRIPTION
           "If 'true', the flow  is  to  incur  loss  when
           traffic is policed.  If 'false', policed traff-
           ic is treated as best effort traffic."
    DEFVAL  { false }
    ::= { intSrvFlowEntry  22 }

intSrvFlowService OBJECT-TYPE
    SYNTAX  QosService
    ACCESS  read-only
    STATUS  mandatory
    DESCRIPTION
           "The QoS service being applied to this flow."
    ::= { intSrvFlowEntry  23 }

intSrvFlowOrder OBJECT-TYPE
    SYNTAX  INTEGER
    ACCESS  read-write
    STATUS  mandatory
    DESCRIPTION
           "In the event of ambiguity, the order in  which
           the  classifier  should  make  its comparisons.
           The row with intSrvFlowOrder=0 is tried  first,
           and  comparisons  proceed  in  the order of in-
           creasing value.  Non-serial implementations  of
           the classifier should emulate this behavior."
    ::= { intSrvFlowEntry  24 }

intSrvFlowStatus OBJECT-TYPE
    SYNTAX  RowStatus
    ACCESS  read-write
    STATUS  mandatory
    DESCRIPTION
           "'active' for all active  flows.   This  object
           may be used to install static classifier infor-
           mation, delete classifier information,  or  au-
           thorize such."
    ::= { intSrvFlowEntry  25 }

intSrvFlowNewIndex OBJECT-TYPE
    SYNTAX  TestAndIncr
    ACCESS  read-write
    STATUS  mandatory
    DESCRIPTION
           "This  object  is  used  to  assign  values  to
           intSrvFlowNumber  as described in 'Textual Con-
           ventions  for  SNMPv2'.   The  network  manager
           reads  the  object,  and  then writes the value
           back in the SET that creates a new instance  of
           intSrvFlowEntry.   If  the  SET  fails with the
           code 'inconsistentValue', then the process must
           be  repeated; If the SET succeeds, then the ob-
           ject is incremented, and the  new  instance  is
           created according to the manager's directions."
    ::= { intSrvGenObjects  1 }

intSrvGroups OBJECT IDENTIFIER ::= { intSrvConformance  1 }

intSrvCompliances OBJECT IDENTIFIER ::= { intSrvConformance  2 }

intSrvCompliance OBJECT IDENTIFIER ::= { intSrvCompliances  1 }

intSrvIfAttribGroup OBJECT IDENTIFIER ::= { intSrvGroups  1 }

intSrvFlowsGroup OBJECT IDENTIFIER ::= { intSrvGroups  2 }

END
