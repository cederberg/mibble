XYLAN-HEALTH-MIB DEFINITIONS ::= BEGIN

	--  RCSID information

	--  $RCSfile: xylan-health.mib,v $
	--  $Revision: 1.13 $
	--  $Date: 1998/08/27 23:53:45 $
	--  $Author: lsl $


	--  xylan-health.mib
	--  Revision: 1.01
	--  Date: May 8, 1998

	--  Alcatel Internetworking, Inc.
	--  26801 W. Agoura Road
	--  Calabasas, CA 91301
	--  (818) 880-3500
	--  support@ind.alcatel.com

	--  This module provides authoritative definitions for Alcatel Internetworking, Inc.
	--  enterprise-specific health MIB.

	--  This module will be extended, as needed.


	--  Alcatel Internetworking, Inc. reserves the right to make changes in 
	--  specification and other information contained in this document 
	--  without prior notice.  The reader should consult Alcatel Internetworking,
	--  Inc. to determine whether any such changes have been made.
	--  Current MIBs are available from the following URLs:
	--		ftp://ftp.ind.alcatel.com/pub/products/mibs
	--		http://www.ind.alcatel.com

	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1994, Alcatel Internetworking, Inc. All Rights Reserved


	IMPORTS
		OBJECT-TYPE
			FROM RFC-1212
		xylanHealthArch
			FROM XYLAN-BASE-MIB
			;


	--  This MIB module uses the extended OBJECT-TYPE macro as defined
	--  RFC 1212 (but known in the epilog files under RFC1213-SMI...)




	--  groups within the health mib

	healthDeviceInfo	OBJECT IDENTIFIER ::= { xylanHealthArch 1 }
	healthModuleInfo	OBJECT IDENTIFIER ::= { xylanHealthArch 2 }
	healthPortInfo		OBJECT IDENTIFIER ::= { xylanHealthArch 3 }
	healthGroupInfo		OBJECT IDENTIFIER ::= { xylanHealthArch 4 }
	healthControlInfo       OBJECT IDENTIFIER ::= { xylanHealthArch 5 }
	healthThreshInfo       OBJECT IDENTIFIER ::= { xylanHealthArch 6 }
	health2DeviceInfo	OBJECT IDENTIFIER ::= { xylanHealthArch 7 }
	health2ModuleInfo	OBJECT IDENTIFIER ::= { xylanHealthArch 8 }
	health2PortInfo		OBJECT IDENTIFIER ::= { xylanHealthArch 9 }


	--  healthDeviceInfo group. This group contains the device-level
	--  health monitoring information.

	healthDeviceRxData  OBJECT-TYPE
	    SYNTAX  OCTET STRING (SIZE(4))
	    ACCESS  read-only
	    STATUS  mandatory
	    DESCRIPTION
		"Device-level input utilization information.
		 Octet 0: average input utilization over the latest sample period (percent)
		 Octet 1: average input utilization over the latest minute (percent)
		 Octet 2: average input utilization over the latest hour (percent)
		 Octet 3: maximum input utilization over the latest hour (percent)
		 input utilization = total octets input / device capacity."
	    ::= { healthDeviceInfo 1 }

  	healthDeviceRxTimeDelta  OBJECT-TYPE
  	    SYNTAX  INTEGER
  	    ACCESS  read-only
  	    STATUS  mandatory
  	    DESCRIPTION
  		"Time since input usage updated.
		 Units are 1/100 second."
  	    ::= { healthDeviceInfo 2 }


	healthDeviceRxTxData  OBJECT-TYPE
	    SYNTAX  OCTET STRING (SIZE(4))
	    ACCESS  read-only
	    STATUS  mandatory
	    DESCRIPTION
		"Device-level i/o utilization information.
		 Octet 0: average i/o utilization over the latest sample period (percent)
		 Octet 1: average i/o utilization over the latest minute (percent)
		 Octet 2: average i/o utilization over the latest hour (percent)
		 Octet 3: maximum i/o utilization over the latest hour (percent)
		 i/o utilization = (total octets input + total octets output) / device capacity."
	    ::= { healthDeviceInfo 3 }

  	healthDeviceRxTxTimeDelta  OBJECT-TYPE
  	    SYNTAX  INTEGER
  	    ACCESS  read-only
  	    STATUS  mandatory
  	    DESCRIPTION
  		"Time since i/o usage updated.
		 Units are 1/100 second."
  	    ::= { healthDeviceInfo 4 }


	healthDeviceBackplaneData  OBJECT-TYPE
	    SYNTAX  OCTET STRING (SIZE(4))
	    ACCESS  read-only
	    STATUS  mandatory
	    DESCRIPTION
		"Device-level backplane utilization information.
		 Octet 0: average backplane utilization over the latest sample period (percent)
		 Octet 1: average backplane utilization over the latest minute (percent)
		 Octet 2: average backplane utilization over the latest hour (percent)
		 Octet 3: maximum backplane utilization over the latest hour (percent)."
	    ::= { healthDeviceInfo 5 }

  	healthDeviceBackplaneTimeDelta  OBJECT-TYPE
  	    SYNTAX  INTEGER
  	    ACCESS  read-only
  	    STATUS  mandatory
  	    DESCRIPTION
  		"Time since backplane usage updated.
		 Units are 1/100 second."
  	    ::= { healthDeviceInfo 6 }


	healthDeviceCamData  OBJECT-TYPE
	    SYNTAX  OCTET STRING (SIZE(12))
	    ACCESS  read-only
	    STATUS  mandatory
	    DESCRIPTION
		"Device-level CAM utilization information.
		 Octet 0: average MPM CAM utilization over the latest sample period (percent)
		 Octet 1: average MPM CAM utilization over the latest minute (percent)
		 Octet 2: average MPM CAM utilization over the latest hour (percent)
		 Octet 3: maximum MPM CAM utilization over the latest hour (percent)
		 Octet 4: average HRE CAM utilization over the latest minute (percent)
		 Octet 5: average HRE CAM utilization over the latest minute (percent)
		 Octet 6: average HRE CAM utilization over the latest hour (percent)
		 Octet 7: maximum HRE CAM utilization over the latest hour (percent)
		 Octet 8: average HRE collision utilization over the latest minute (percent)
		 Octet 9: average HRE collision utilization over the latest minute (percent)
		 Octet 10: average HRE collision utilization over the latest hour (percent)
		 Octet 11: maximum HRE collision utilization over the latest hour (percent)."
	    ::= { healthDeviceInfo 7 }

  	healthDeviceCamTimeDelta  OBJECT-TYPE
  	    SYNTAX  INTEGER
  	    ACCESS  read-only
  	    STATUS  mandatory
  	    DESCRIPTION
  		"Time since CAM usage updated.
		 Units are 1/100 second."
  	    ::= { healthDeviceInfo 8 }


	healthDeviceMemoryData  OBJECT-TYPE
	    SYNTAX  OCTET STRING (SIZE(12))
	    ACCESS  read-only
	    STATUS  mandatory
	    DESCRIPTION
		"Device-level memory utilization information.
		 Octet 0: average memory utilization over the latest sample period (percent)
		 Octet 1: average memory utilization over the latest minute (percent)
		 Octet 2: average memory utilization over the latest hour (percent)
		 Octet 3: maximum memory utilization over the latest hour (percent)."
	    ::= { healthDeviceInfo 9 }

  	healthDeviceMemoryTimeDelta  OBJECT-TYPE
  	    SYNTAX  INTEGER
  	    ACCESS  read-only
  	    STATUS  mandatory
  	    DESCRIPTION
  		"Time since memory usage updated.
		 Units are 1/100 second."
  	    ::= { healthDeviceInfo 10 }


	healthDeviceCpuData  OBJECT-TYPE
	    SYNTAX  OCTET STRING 
	    ACCESS  read-only
	    STATUS  mandatory
	    DESCRIPTION
		"Device-level cpu utilization information.
		 Octet 0: average cpu #1 utilization over the latest sample period (percent)
		 Octet 1: average cpu #1 utilization over the latest minute (percent)
		 Octet 2: average cpu #1 utilization over the latest hour (percent)
		 Octet 3: maximum cpu #1 utilization over the latest hour (percent)
		 Octet 4: average cpu #2 utilization over the latest sample period (percent)
		 Octet 5: average cpu #2 utilization over the latest minute (percent)
		 Octet 6: average cpu #2 utilization over the latest hour (percent)
		 Octet 7: maximum cpu #2 utilization over the latest hour (percent)
		 Octet 8: average cpu #3 utilization over the latest sample period (percent)
		 Octet 9: average cpu #3 utilization over the latest minute (percent)
		 Octet 10: average cpu #3 utilization over the latest hour (percent)
		 Octet 11: maximum cpu #3 utilization over the latest hour (percent)
		 Octet 12: average cpu #4 utilization over the latest sample period (percent)
		 Octet 13: average cpu #4 utilization over the latest minute (percent)
		 Octet 14: average cpu #4 utilization over the latest hour (percent)
		 Octet 15: maximum cpu #4 utilization over the latest hour (percent)."
	    ::= { healthDeviceInfo 11 }

  	healthDeviceCpuTimeDelta  OBJECT-TYPE
  	    SYNTAX  INTEGER
  	    ACCESS  read-only
  	    STATUS  mandatory
  	    DESCRIPTION
  		"Time since cpu usage updated.
		 Units are 1/100 second."
  	    ::= { healthDeviceInfo 12 }

	healthDeviceNumCpus  OBJECT-TYPE
	    SYNTAX  INTEGER
	    ACCESS  read-only
	    STATUS  mandatory
	    DESCRIPTION
		"Number of CPUs on MPM."
  	    ::= { healthDeviceInfo 13 }

	healthDeviceMemoryTotal  OBJECT-TYPE
	    SYNTAX  INTEGER
	    ACCESS  read-only
	    STATUS  mandatory
	    DESCRIPTION
		"Total memory available (octets)."
  	    ::= { healthDeviceInfo 14 }

	healthDeviceMemoryFree  OBJECT-TYPE
	    SYNTAX  INTEGER
	    ACCESS  read-only
	    STATUS  mandatory
	    DESCRIPTION
		"Total memory free (octets)."
  	    ::= { healthDeviceInfo 15 }

	healthDeviceMpmCamTotal  OBJECT-TYPE
	    SYNTAX  INTEGER
	    ACCESS  read-only
	    STATUS  mandatory
	    DESCRIPTION
		"Total entries in MPM CAM."
  	    ::= { healthDeviceInfo 16 }

	healthDeviceMpmCamFree  OBJECT-TYPE
	    SYNTAX  INTEGER
	    ACCESS  read-only
	    STATUS  mandatory
	    DESCRIPTION
		"Free entries in MPM CAM."
  	    ::= { healthDeviceInfo 17 }

	healthDeviceHreCamTotal  OBJECT-TYPE
	    SYNTAX  INTEGER
	    ACCESS  read-only
	    STATUS  mandatory
	    DESCRIPTION
		"Total entries in HRE CAM."
  	    ::= { healthDeviceInfo 18 }

	healthDeviceHreCamFree  OBJECT-TYPE
	    SYNTAX  INTEGER
	    ACCESS  read-only
	    STATUS  mandatory
	    DESCRIPTION
		"Free entries in HRE CAM."
  	    ::= { healthDeviceInfo 19 }

	healthDeviceTemp  OBJECT-TYPE
	    SYNTAX  INTEGER
	    ACCESS  read-only
	    STATUS  mandatory
	    DESCRIPTION
		"Current temperature of switch in degrees C x 10."
  	    ::= { healthDeviceInfo 20 }

	healthDeviceIPRouteCacheFlushCount  OBJECT-TYPE
	    SYNTAX  INTEGER
	    ACCESS  read-only
	    STATUS  mandatory
	    DESCRIPTION
		"Number of times IP route cache has been flushed."
  	    ::= { healthDeviceInfo 21 }

	healthDeviceIPXRouteCacheFlushCount  OBJECT-TYPE
	    SYNTAX  INTEGER
	    ACCESS  read-only
	    STATUS  mandatory
	    DESCRIPTION
		"Number of times IPX route cache has been flushed."
  	    ::= { healthDeviceInfo 22 }

	healthDeviceMpmRxOverrunCount  OBJECT-TYPE
	    SYNTAX  INTEGER
	    ACCESS  read-only
	    STATUS  mandatory
	    DESCRIPTION
		"Number of MPM receive overruns."
  	    ::= { healthDeviceInfo 23 }

	healthDeviceMpmTxOverrunCount  OBJECT-TYPE
	    SYNTAX  INTEGER
	    ACCESS  read-only
	    STATUS  mandatory
	    DESCRIPTION
		"Number of MPM transmit overruns."
  	    ::= { healthDeviceInfo 24 }

	healthDeviceVccData  OBJECT-TYPE
	    SYNTAX  OCTET STRING (SIZE(4))
	    ACCESS  read-only
	    STATUS  mandatory
	    DESCRIPTION
		"Device-level Vcc utilization information.
		 Octet 0: average Vcc utilization over the latest sample period (percent)
		 Octet 1: average Vcc utilization over the latest minute (percent)
		 Octet 2: average Vcc utilization over the latest hour (percent)
		 Octet 3: maximum Vcc utilization over the latest hour (percent)
		 Vcc utilization = total active Vccs / device Vcc capacity."
	    ::= { healthDeviceInfo 25 }

  	healthDeviceVccTimeDelta  OBJECT-TYPE
  	    SYNTAX  INTEGER
  	    ACCESS  read-only
  	    STATUS  mandatory
  	    DESCRIPTION
  		"Time since Vcc usage updated.
		 Units are 1/100 second."
  	    ::= { healthDeviceInfo 26 }


	healthDeviceTemperatureData  OBJECT-TYPE
	    SYNTAX  OCTET STRING (SIZE(4))
	    ACCESS  read-only
	    STATUS  mandatory
	    DESCRIPTION
		"Device-level temperature information.
		 Octet 0: average temperature over the latest sample period (degrees Centigrade)
		 Octet 1: average temperature over the latest minute (degrees Centigrade)
		 Octet 2: average temperature over the latest hour (degrees Centigrade)
		 Octet 3: maximum temperature over the latest hour (degrees centigrade)."
	    ::= { healthDeviceInfo 27 }

  	healthDeviceTemperatureTimeDelta  OBJECT-TYPE
  	    SYNTAX  INTEGER
  	    ACCESS  read-only
  	    STATUS  mandatory
  	    DESCRIPTION
  		"Time since temperature updated.
		 Units are 1/100 second."
  	    ::= { healthDeviceInfo 28 }


	healthDeviceVpData  OBJECT-TYPE
	    SYNTAX  OCTET STRING (SIZE(4))
	    ACCESS  read-only
	    STATUS  mandatory
	    DESCRIPTION
		"Device-level virtual port utilization information.
		 Octet 0: average virtual port utilization over the latest sample period (percent)
		 Octet 1: average virtual port utilization over the latest minute (percent)
		 Octet 2: average virtual port utilization over the latest hour (percent)
		 Octet 3: maximum virtual port utilization over the latest hour (percent)
		 virtual port utilization = total active virtual ports / device virtual port capacity."
	    ::= { healthDeviceInfo 29 }

  	healthDeviceVpTimeDelta  OBJECT-TYPE
  	    SYNTAX  INTEGER
  	    ACCESS  read-only
  	    STATUS  mandatory
  	    DESCRIPTION
  		"Time since virtual port usage updated.
		 Units are 1/100 second."
  	    ::= { healthDeviceInfo 30 }

	healthDeviceHreCollisionTotal  OBJECT-TYPE
	    SYNTAX  INTEGER
	    ACCESS  read-only
	    STATUS  mandatory
	    DESCRIPTION
		"Total collision entries available in HRE CAM."
  	    ::= { healthDeviceInfo 31 }

	healthDeviceHreCollisionFree  OBJECT-TYPE
	    SYNTAX  INTEGER
	    ACCESS  read-only
	    STATUS  mandatory
	    DESCRIPTION
		"Free collision entries in HRE CAM."
  	    ::= { healthDeviceInfo 32 }

	--  healthModuleInfo group. This group contains the module-level
	--  health monitoring information.

	--  healthModuleTable. This table maintains the per slot
	--  data that is related to a specific installed module
	--  in a slot.

	healthModuleTable  OBJECT-TYPE
	    SYNTAX  SEQUENCE OF HealthModuleEntry
	    ACCESS  not-accessible
	    STATUS  mandatory
	    DESCRIPTION
		"A list of installed modules in this chassis."
	    ::= { healthModuleInfo 1 }

	healthModuleEntry  OBJECT-TYPE
	    SYNTAX  HealthModuleEntry
	    ACCESS  not-accessible
	    STATUS  mandatory
	    DESCRIPTION
		"A module entry containing objects for a module in a specific 'slot'."
	    INDEX { healthModuleSlot }
	    ::= { healthModuleTable 1 }

	HealthModuleEntry ::= SEQUENCE {
	    healthModuleSlot
			INTEGER,
	    healthModuleRxData
			OCTET STRING,
	    healthModuleRxTimeDelta
			INTEGER,
	    healthModuleRxTxData
			OCTET STRING,
	    healthModuleRxTxTimeDelta
			INTEGER,
	    healthModuleBackplaneData
			OCTET STRING,
	    healthModuleBackplaneTimeDelta
			INTEGER,
	    healthModuleCamData
			OCTET STRING,
	    healthModuleCamTimeDelta
			INTEGER,
	    healthModuleCamNumInstalled
			INTEGER,
	    healthModuleCamConfigured
			INTEGER,
	    healthModuleCamAvail
			INTEGER,
	    healthModuleCamAvailNonIntern
			INTEGER,
	    healthModuleCamFree
			INTEGER,
	    healthModuleVccData
			OCTET STRING,
	    healthModuleVccTimeDelta
			INTEGER
	    }

	healthModuleSlot  OBJECT-TYPE
	    SYNTAX  INTEGER
	    ACCESS  read-only
	    STATUS  mandatory
	    DESCRIPTION
		"The (one-based) front slot number within the chassis."
	    ::= { healthModuleEntry 1 }

	healthModuleRxData  OBJECT-TYPE
	    SYNTAX  OCTET STRING (SIZE(4))
	    ACCESS  read-only
	    STATUS  mandatory
	    DESCRIPTION
		"Module-level input utilization information.
		 Octet 0: average input utilization over the latest sample period (percent)
		 Octet 1: average input utilization over the latest minute (percent)
		 Octet 2: average input utilization over the latest hour (percent)
		 Octet 3: maximum input utilization over the latest hour (percent)
		 input utilization = total octets input / module capacity."
	    ::= { healthModuleEntry 2 }

  	healthModuleRxTimeDelta  OBJECT-TYPE
  	    SYNTAX  INTEGER
  	    ACCESS  read-only
  	    STATUS  mandatory
  	    DESCRIPTION
  		"Time since input usage updated.
		 Units are 1/100 second."
  	    ::= { healthModuleEntry 3 }


	healthModuleRxTxData  OBJECT-TYPE
	    SYNTAX  OCTET STRING (SIZE(4))
	    ACCESS  read-only
	    STATUS  mandatory
	    DESCRIPTION
		"Module-level i/o utilization information.
		 Octet 0: average i/o utilization over the latest sample period (percent)
		 Octet 1: average i/o utilization over the latest minute (percent)
		 Octet 2: average i/o utilization over the latest hour (percent)
		 Octet 3: maximum i/o utilization over the latest hour (percent)
		 i/o utilization = (total octets input + total octets output) / module capacity."
	    ::= { healthModuleEntry 4 }

  	healthModuleRxTxTimeDelta  OBJECT-TYPE
  	    SYNTAX  INTEGER
  	    ACCESS  read-only
  	    STATUS  mandatory
  	    DESCRIPTION
  		"Time since i/o usage updated.
		 Units are 1/100 second."
  	    ::= { healthModuleEntry 5 }


	healthModuleBackplaneData  OBJECT-TYPE
	    SYNTAX  OCTET STRING (SIZE(4))
	    ACCESS  read-only
	    STATUS  mandatory
	    DESCRIPTION
		"Module-level backplane utilization information.
		 Octet 0: average backplane utilization over the latest sample period (percent)
		 Octet 1: average backplane utilization over the latest minute (percent)
		 Octet 2: average backplane utilization over the latest hour (percent)
		 Octet 3: maximum backplane utilization over the latest hour (percent)."
	    ::= { healthModuleEntry 6 }

  	healthModuleBackplaneTimeDelta  OBJECT-TYPE
  	    SYNTAX  INTEGER
  	    ACCESS  read-only
  	    STATUS  mandatory
  	    DESCRIPTION
  		"Time since backplane usage updated.
		 Units are 1/100 second."
	    ::= { healthModuleEntry 7 }

	healthModuleCamData  OBJECT-TYPE
	    SYNTAX  OCTET STRING (SIZE(4))
	    ACCESS  read-only
	    STATUS  mandatory
	    DESCRIPTION
		"Module-level CAM utilization information.
		 Octet 0: average CAM utilization over the latest sample period (percent)
		 Octet 1: average CAM utilization over the latest minute (percent)
		 Octet 2: average CAM utilization over the latest hour (percent)
		 Octet 3: maximum CAM utilization over the latest hour (percent)."
	    ::= { healthModuleEntry 8 }


  	healthModuleCamTimeDelta  OBJECT-TYPE
  	    SYNTAX  INTEGER
  	    ACCESS  read-only
  	    STATUS  mandatory
  	    DESCRIPTION
  		"Time since CAM usage updated.
		 Units are 1/100 second."
  	    ::= { healthModuleEntry 9 }

  	healthModuleCamNumInstalled  OBJECT-TYPE
  	    SYNTAX  INTEGER
  	    ACCESS  read-only
  	    STATUS  mandatory
  	    DESCRIPTION
  		"The number of CAMs installed on the device."
  	    ::= { healthModuleEntry 10 }

  	healthModuleCamConfigured  OBJECT-TYPE
  	    SYNTAX  INTEGER
  	    ACCESS  read-only
  	    STATUS  mandatory
  	    DESCRIPTION
  		"The number of CAM entries configured."
  	    ::= { healthModuleEntry 11 }

  	healthModuleCamAvail  OBJECT-TYPE
  	    SYNTAX  INTEGER
  	    ACCESS  read-only
  	    STATUS  mandatory
  	    DESCRIPTION
  		"The number of CAM entries available."
  	    ::= { healthModuleEntry 12 }

  	healthModuleCamAvailNonIntern  OBJECT-TYPE
  	    SYNTAX  INTEGER
  	    ACCESS  read-only
  	    STATUS  mandatory
  	    DESCRIPTION
  		"The number of CAM entries available for caching non-internal 
		 MAC Addresses."
  	    ::= { healthModuleEntry 13 }

  	healthModuleCamFree  OBJECT-TYPE
  	    SYNTAX  INTEGER
  	    ACCESS  read-only
  	    STATUS  mandatory
  	    DESCRIPTION
  		"The number of free CAM entries."
  	    ::= { healthModuleEntry 14 }

	healthModuleVccData  OBJECT-TYPE
	    SYNTAX  OCTET STRING (SIZE(4))
	    ACCESS  read-only
	    STATUS  mandatory
	    DESCRIPTION
		"Module-level Vcc utilization information.
		 Octet 0: average Vcc utilization over the latest sample period (percent)
		 Octet 1: average Vcc utilization over the latest minute (percent)
		 Octet 2: average Vcc utilization over the latest hour (percent)
		 Octet 3: maximum Vcc utilization over the latest hour (percent)
		 Vcc utilization = total active Vccs / module Vcc capacity."
	    ::= { healthModuleEntry 15 }

  	healthModuleVccTimeDelta  OBJECT-TYPE
  	    SYNTAX  INTEGER
  	    ACCESS  read-only
  	    STATUS  mandatory
  	    DESCRIPTION
  		"Time since Vcc usage updated.
		 Units are 1/100 second."
  	    ::= { healthModuleEntry 16 }


	--  healthControl group.  This group contains the variables
	--  which control operation of resource utilization sampling. 
	--  Implementation of this group is mandatory.
	--
        healthSamplingInterval OBJECT-TYPE
              SYNTAX  INTEGER 
              ACCESS  read-write
              STATUS  mandatory
              DESCRIPTION
                 "Time interval between consecutive samples of resources.
		  Units are seconds.  Legal values are:               1,2,3,4,5,6,10,12,15,20,30.
		  Default is 5."
              ::= { healthControlInfo 1 }

        healthSamplingReset OBJECT-TYPE
              SYNTAX  INTEGER 
              ACCESS  write-only
              STATUS  mandatory
              DESCRIPTION
                 "Any set of this variable causes all health counters to reset
		  to zero and a restart of sampling."
              ::= { healthControlInfo 2 }

        healthTrapRepeatInterval OBJECT-TYPE
              SYNTAX  INTEGER 
              ACCESS  read-write
              STATUS  mandatory
              DESCRIPTION
                 "Time interval between repeat of traps for over-threshold resources.
		  Units are minutes.  Setting this object to zero disables repeat traps."
              ::= { healthControlInfo 3 }


	--  healthThreshInfo group.  This group contains the threshold
	--  data. Implementation of this group is mandatory.
	--

	healthThreshDeviceRxLimit  OBJECT-TYPE
 	    SYNTAX  INTEGER  (0..100)
	    ACCESS  read-write
	    STATUS  mandatory
	    DESCRIPTION
  		"Device input threshold value.  Units are percent.  Default is 80."
	    ::= { healthThreshInfo 1 }

	healthThreshDeviceRxTxLimit  OBJECT-TYPE
 	    SYNTAX  INTEGER  (0..100)
	    ACCESS  read-write
	    STATUS  mandatory
	    DESCRIPTION
  		"Device input/output threshold value.  Units are percent.  Default is 80."
	    ::= { healthThreshInfo 2 }

	healthThreshDeviceBackplaneLimit  OBJECT-TYPE
 	    SYNTAX  INTEGER  (0..100)
	    ACCESS  read-write
	    STATUS  mandatory
	    DESCRIPTION
  		"Device backplane threshold value.  Units are percent.  Default is 80."
	    ::= { healthThreshInfo 3 }

	healthThreshDeviceCamLimit  OBJECT-TYPE
 	    SYNTAX  INTEGER  (0..100)
	    ACCESS  read-write
	    STATUS  mandatory
	    DESCRIPTION
  		"Device Cam threshold value.  Units are percent.  Default is 80."
	    ::= { healthThreshInfo 4 }

	healthThreshDeviceMemoryLimit  OBJECT-TYPE
 	    SYNTAX  INTEGER  (0..100)
	    ACCESS  read-write
	    STATUS  mandatory
	    DESCRIPTION
  		"Device memory threshold value.  Units are percent.  Default is 80."
	    ::= { healthThreshInfo 5 }
	    
	healthThreshDeviceCpuLimit  OBJECT-TYPE
 	    SYNTAX  INTEGER  (0..100)
	    ACCESS  read-write
	    STATUS  mandatory
	    DESCRIPTION
  		"Device Cpu threshold value.  Units are percent.  Default is 80."
	    ::= { healthThreshInfo 6 }

	healthThreshDeviceSummary  OBJECT-TYPE
	    SYNTAX  OCTET STRING (SIZE(27))
	    ACCESS  read-only
	    STATUS  mandatory
	    DESCRIPTION
		"Summary of current device thresholds.  
		 Octet 0 contains the device threshold-exceeded flag
			 non-zero if any device threshold exceeded
		 Octet 1 contains the device Rx threshold-exceeded flag
			 non-zero if device Rx threshold exceeded
		 Octet 2 contains the device RxTx threshold-exceeded flag
			 non-zero if device RxTx threshold exceeded
		 Octet 3 contains the device backplane threshold-exceeded flag
			 non-zero if device backplane threshold exceeded
		 Octet 4 contains the device CAM threshold-exceeded flag
			 non-zero if device CAM threshold exceeded
		 Octet 5 contains the device memory threshold-exceeded flag
			 non-zero if device memory threshold exceeded
		 Octet 6 contains the device CPU threshold-exceeded flag
			 non-zero if device memory threshold exceeded
		 Octet 7 contains the device VCC threshold-exceeded flag
			 non-zero if device VCC threshold exceeded
		 All the following values are percentages.
		 Octet 8 contains device Rx threshold
		 Octet 9 contains device Rx usage
		 Octet 10 contains device RxTx threshold
		 Octet 11 contains device RxTx usage
		 Octet 12 contains device backplane threshold
		 Octet 13 contains device backplane usage
		 Octet 14 contains device CAM threshold
		 Octet 15 contains device MPM CAM usage
		 Octet 16 contains device HRE CAM usage
		 Octet 17 contains device memory threshold
		 Octet 18 contains device memory usage
		 Octet 19 contains device CPU threshold
		 Octet 20 contains device CPU#1 usage
		 Octet 21 contains device CPU#2 usage
		 Octet 22 contains device CPU#3 usage
		 Octet 23 contains device CPU#4 usage
		 Octet 24 contains device VCC threshold
		 Octet 25 contains device VCC usage
		 Octet 26 contains device HRE collision usage."
	    ::= { healthThreshInfo 7 }

	healthThreshModuleSummaryTable  OBJECT-TYPE
	    SYNTAX  SEQUENCE OF HealthThreshModuleSummaryEntry
	    ACCESS  not-accessible
	    STATUS  mandatory
	    DESCRIPTION
		"A list of installed modules in this chassis."
	    ::= { healthThreshInfo 8 }

	healthThreshModuleSummaryEntry  OBJECT-TYPE
	    SYNTAX  HealthThreshModuleSummaryEntry
	    ACCESS  not-accessible
	    STATUS  mandatory
	    DESCRIPTION
		"A module entry containing a summary of resource usage in a specific 'slot'."
	    INDEX { healthThreshModuleSummarySlot }
	    ::= { healthThreshModuleSummaryTable 1 }

	HealthThreshModuleSummaryEntry ::= SEQUENCE {
	    healthThreshModuleSummarySlot
			INTEGER,
	    healthThreshModuleSummaryData
			OCTET STRING
        }

	healthThreshModuleSummarySlot  OBJECT-TYPE
	    SYNTAX  INTEGER (1..9)
	    ACCESS  read-only
	    STATUS  mandatory
	    DESCRIPTION
		"The (one-based) front slot number within the chassis."
	    ::= { healthThreshModuleSummaryEntry 1 }

	healthThreshModuleSummaryData  OBJECT-TYPE
	    SYNTAX  OCTET STRING (SIZE(16))
	    ACCESS  read-only
	    STATUS  mandatory
	    DESCRIPTION
		"Summary of current module thresholds.  
		 Octet 0 contains the module threshold-exceeded flag
			 non-zero if any module threshold exceeded
		 Octet 1 contains the module Rx threshold-exceeded flag
			 non-zero if module Rx threshold exceeded
		 Octet 2 contains the module RxTx threshold-exceeded flag
			 non-zero if module RxTx threshold exceeded
		 Octet 3 contains the module backplane threshold-exceeded flag
			 non-zero if module backplane threshold exceeded
		 Octet 4 contains the module VCC threshold-exceeded flag
			 non-zero if module VCC threshold exceeded
		 Octet 5 contains the module CAM threshold-exceeded flag
			 non-zero if module CAM threshold exceeded
		 All the following values are percentages.
		 Octet 6 contains module Rx threshold
		 Octet 7 contains module Rx usage
		 Octet 8 contains module RxTx threshold
		 Octet 9 contains module RxTx usage
		 Octet 10 contains module backplane threshold
		 Octet 11 contains module backplane usage
		 Octet 12 contains module VCC threshold
		 Octet 13 contains module VCC usage
		 Octet 14 contains module CAM threshold
		 Octet 15 contains module CAM usage."
	    ::= { healthThreshModuleSummaryEntry 2 }

	healthThreshDevTrapData  OBJECT-TYPE
	    SYNTAX  OCTET STRING (SIZE(0..21))
	    ACCESS  not-accessible
	    STATUS  mandatory
	    DESCRIPTION
		"Contents of device-level rising/falling threshold trap.
		 The format is as follows:
		 Octet  1: length including this octet (L)
		 Octet  2: number of threshold type/change pairs
		 Octets 3 - L: type/change pairs
			       each pair consists of one octet
			       identifying the threshold type
			       and one octet identifying the change
				    type.
			     Threshold type values:
                             Rx threshold        = 1
                             RxTx threshold      = 2
                             Backplane threshold = 3
                             VCC threshold       = 4
                             HRE CAM threshold   = 5
                             MPM CAM threshold   = 6
                             Memory threshold    = 7
                             CPUn threshold      = 7 + n (1 <= n <= 4)
                             HRE collision threshold   = 12

			     Change type values:
			     falling threshold change   = 1
			     rising threshold change    = 2
			     persistent above threshold = 3
		  Only those thresholds for which an event
		  is detected will be present.

		  This object is not intended to be accessed directly.
		  It is defined for use in device-level rising/falling
		  threshold traps."
	    ::= { healthThreshInfo 9 }

	healthThreshModTrapCount  OBJECT-TYPE
	    SYNTAX  INTEGER
	    ACCESS  not-accessible
	    STATUS  mandatory
	    DESCRIPTION
		"Number of modules with threshold crossing data in
		 module-level rising/falling threshold trap.
		 This object is not intended to be accessed directly.
		 It is defined for use in module-level rising/falling
		 threshold traps."
	    ::= { healthThreshInfo 10 }

	healthThreshModTrapData  OBJECT-TYPE
	    SYNTAX  OCTET STRING (SIZE(0..128))
	    ACCESS  not-accessible
	    STATUS  mandatory
	    DESCRIPTION
		"Contents of module-level rising/falling threshold trap.
		 The format is as follows:
		 Octet  1: length including this octet (L)
		 Octets 2 - L: module threshold trap data

		 Within each module's data, the format is as follows:
		    Octet  1: length including this octet 
		    Octet  2: number of threshold type/change pairs
		    Octet  3: module slot number
		    Octets 4 and following: 
		                  type/change pairs
			          each pair consists of one octet
			          identifying the threshold type
			          and one octet identifying the change
				    type.
			     Threshold type values:
                             Rx threshold        = 1
                             RxTx threshold      = 2
                             Backplane threshold = 3
                             VCC threshold       = 4
                             CAM threshold       = 5

			     Change type values:
			     falling threshold change = 1
			     rising threshold change  = 2
		     Only those thresholds for which a threshold 
		     crossing event is detected will be present.

		  This object is not intended to be accessed directly.
		  It is defined for use in module-level rising/falling
		  threshold traps."
	    ::= { healthThreshInfo 11 }

	healthThreshPortSummaryTable  OBJECT-TYPE
	    SYNTAX  SEQUENCE OF HealthThreshPortSummaryEntry
	    ACCESS  not-accessible
	    STATUS  mandatory
	    DESCRIPTION
		"A list of port in this chassis."
	    ::= { healthThreshInfo 12 }

	healthThreshPortSummaryEntry  OBJECT-TYPE
	    SYNTAX  HealthThreshPortSummaryEntry
	    ACCESS  not-accessible
	    STATUS  mandatory
	    DESCRIPTION
		"A module entry containing a summary of resource usage in a specific 'slot/port'."
	    INDEX { healthThreshPortSummarySlot,
	            healthThreshPortSummaryIF }
	    ::= { healthThreshPortSummaryTable 1 }

	HealthThreshPortSummaryEntry ::= SEQUENCE {
	    healthThreshPortSummarySlot
			INTEGER,
	    healthThreshPortSummaryIF
			INTEGER,
	    healthThreshPortSummaryData
			OCTET STRING
        }

	healthThreshPortSummarySlot  OBJECT-TYPE
	    SYNTAX  INTEGER (1..9)
	    ACCESS  read-only
	    STATUS  mandatory
	    DESCRIPTION
		"The (one-based) front slot number within the chassis."
	    ::= { healthThreshPortSummaryEntry 1 }

	healthThreshPortSummaryIF  OBJECT-TYPE
	    SYNTAX  INTEGER (1..9)
	    ACCESS  read-only
	    STATUS  mandatory
	    DESCRIPTION
		"The on-board interface number."
	    ::= { healthThreshPortSummaryEntry 2 }

	healthThreshPortSummaryData  OBJECT-TYPE
	    SYNTAX  OCTET STRING (SIZE(13))
	    ACCESS  read-only
	    STATUS  mandatory
	    DESCRIPTION
		"Summary of current port thresholds.  
		 Octet 0 contains the port threshold-exceeded flag
			 non-zero if any port threshold exceeded
		 Octet 1 contains the port Rx threshold-exceeded flag
			 non-zero if port Rx threshold exceeded
		 Octet 2 contains the port RxTx threshold-exceeded flag
			 non-zero if port RxTx threshold exceeded
		 Octet 3 contains the port backplane threshold-exceeded flag
			 non-zero if port backplane threshold exceeded
		 Octet 4 contains the port VCC threshold-exceeded flag
			 non-zero if port VCC threshold exceeded
		 All the following values are percentages.
		 Octet  5 contains port Rx threshold
		 Octet  6 contains port Rx usage
		 Octet  7 contains port RxTx threshold
		 Octet  8 contains port RxTx usage
		 Octet  9 contains port backplane threshold
		 Octet 10 contains port backplane usage
		 Octet 11 contains port VCC threshold
		 Octet 12 contains port VCC usage."
	    ::= { healthThreshPortSummaryEntry 3 }

	healthThreshPortTrapSlot  OBJECT-TYPE
	    SYNTAX  INTEGER
	    ACCESS  not-accessible
	    STATUS  mandatory
	    DESCRIPTION
		"Number of the slot with threshold crossing data in
		 port-level rising/falling threshold trap.
		 This object is not intended to be accessed directly.
		 It is defined for use in module-level rising/falling
		 threshold traps."
	    ::= { healthThreshInfo 13 }

	healthThreshPortTrapCount  OBJECT-TYPE
	    SYNTAX  INTEGER
	    ACCESS  not-accessible
	    STATUS  mandatory
	    DESCRIPTION
		"Number of threshold crossing entries in
		 port-level rising/falling threshold trap.
		 This object is not intended to be accessed directly.
		 It is defined for use in port-level rising/falling
		 threshold traps."
	    ::= { healthThreshInfo 14 }

	healthThreshPortTrapData  OBJECT-TYPE
	    SYNTAX  OCTET STRING (SIZE(0..255))
	    ACCESS  not-accessible
	    STATUS  mandatory
	    DESCRIPTION
		"Contents of port-level rising/falling threshold trap.
		 The format is as follows:
		 Octet  1: length including this octet (L)
		 Octets 2 - L: port threshold trap data,
				consisting of threshold crossing
				entries

		 Within each threshold crossing entry, the format is as follows:
		    Octet  1: length including this octet (l)
		    Octet  2: type of threshold crossing 
                              Threshold crossing types are:
                                Rx rising threshold    = 1
                                Rx falling threshold   = 2
                                RxTx rising threshold  = 3
                                RxTx falling threshold = 4
                                Bkpl rising threshold  = 5
                                Bkpl falling threshold = 6
                                Vcc rising threshold   = 7
                                Vcc falling threshold  = 8
		    Octets 3 - l: port bit mask
				  This bit mask is ((N-1)/8)+1
				   octets long, where N is the
				   number of ports on the module.
				  Each port is represented by
				   one bit in the mask.
                                  The bit for port 1 is the
				   leftmost bit in octet 1 of
				   the bit mask.
                                  The bit for port 8 is the
				   rightmost bit in octet 1 of
				   the bit mask.
                                  The bit for port 9 is the
				   leftmost bit in octet 2 of
				   the bit mask, and so on.
		     Only those thresholds for which a threshold 
		     crossing event is detected will be present.

		  This object is not intended to be accessed directly.
		  It is defined for use in port-level rising/falling
		  threshold traps."
	    ::= { healthThreshInfo 15 }

	healthThreshDeviceVccLimit  OBJECT-TYPE
 	    SYNTAX  INTEGER  (0..100)
	    ACCESS  read-write
	    STATUS  mandatory
	    DESCRIPTION
  		"Device VCC threshold value.  Units are percent."
	    ::= { healthThreshInfo 16 }

	healthThreshDeviceTemperatureLimit  OBJECT-TYPE
 	    SYNTAX  INTEGER  (0..100)
	    ACCESS  read-write
	    STATUS  mandatory
	    DESCRIPTION
  		"Device temperature threshold value.  Units are degrees Centigrade."
	    ::= { healthThreshInfo 17 }

	healthThreshDeviceVpLimit  OBJECT-TYPE
 	    SYNTAX  INTEGER  (0..100)
	    ACCESS  read-write
	    STATUS  mandatory
	    DESCRIPTION
  		"Device virtual port threshold value.  Units are percent."
	    ::= { healthThreshInfo 18 }


	--  healthPortInfo group. This group contains the module-level
	--  health monitoring information.

	--  healthPortTable. This table maintains the per port
	--  data that is related to a specific port in a slot.
	--  Implementation of this group is mandantory.
	--  Note that this MIB can NOT be used for row creation 

	healthPortMax  OBJECT-TYPE
	    SYNTAX  OCTET STRING (SIZE(21))
	    ACCESS  read-only
	    STATUS  mandatory
	    DESCRIPTION
		"Maximum port utilization information.
		 Octets 1 - 7:   information for last cycle
		 Octets 8 - 14:  information for last minute
		 Octets 15 - 21: information for last hour
                 Within each group:
		   first octet  = slot
		   second octet = interface
		   third octet  = percentage utlilization
		   fourth through seventh octets = timestamp
		   Timestamp value = octet 4 * 256**3 +
				     octet 5 * 256**2 +
				     octet 6 * 256    +
				     octet 7.
		   Timestamp units are 1/100 second."
	    ::= { healthPortInfo 1 }

	HealthPortUpDownStatus ::= INTEGER {
	    healthPortDn(1),
	    healthPortUp(2)
	}

	healthPortTable  OBJECT-TYPE
	    SYNTAX  SEQUENCE OF HealthPortEntry
	    ACCESS  not-accessible
	    STATUS  mandatory
	    DESCRIPTION
		"A list of Physical Port health instances."
	    ::= { healthPortInfo 2 }

	healthPortEntry  OBJECT-TYPE
	    SYNTAX  HealthPortEntry
	    ACCESS  not-accessible
	    STATUS  mandatory
	    DESCRIPTION
		"A Physical Port health entry."
	    INDEX { healthPortSlot, healthPortIF }
	    ::= { healthPortTable 1 }

	HealthPortEntry ::= SEQUENCE {
	    healthPortSlot
			INTEGER,
	    healthPortIF
			INTEGER,
	    healthPortUpDn
			HealthPortUpDownStatus,
	    healthPortRxData
			OCTET STRING,
	    healthPortRxTimeDelta
			INTEGER,
	    healthPortRxTxData
			OCTET STRING,
	    healthPortRxTxTimeDelta
			INTEGER,
	    healthPortBackplaneData
			OCTET STRING,
	    healthPortBackplaneTimeDelta
			INTEGER,
	    healthPortVccData
			OCTET STRING,
	    healthPortVccTimeDelta
			INTEGER
	    }

	healthPortSlot  OBJECT-TYPE
	    SYNTAX  INTEGER (1..9)
	    ACCESS  read-only
	    STATUS  mandatory
	    DESCRIPTION
		"The physical slot number for this port."
	    ::= { healthPortEntry 1 }

	healthPortIF  OBJECT-TYPE
	    SYNTAX  INTEGER 
	    ACCESS  read-only
	    STATUS  mandatory
	    DESCRIPTION
		"The on-board interface number."
	    ::= { healthPortEntry 2 }

	healthPortUpDn  OBJECT-TYPE
	    SYNTAX  HealthPortUpDownStatus 
	    ACCESS  read-only
	    STATUS  mandatory
	    DESCRIPTION
		"The status of this port."
	    ::= { healthPortEntry 3 }

	healthPortRxData  OBJECT-TYPE
	    SYNTAX  OCTET STRING (SIZE(4))
	    ACCESS  read-only
	    STATUS  mandatory
	    DESCRIPTION
		"Port-level input utilization information.
		 Octet 0: average input utilization over the latest sample period (percent)
		 Octet 1: average input utilization over the latest minute (percent)
		 Octet 2: average input utilization over the latest hour (percent)
		 Octet 3: maximum input utilization over the latest hour (percent)
		 input utilization = total octets input / module capacity."
	    ::= { healthPortEntry 4 }

  	healthPortRxTimeDelta  OBJECT-TYPE
  	    SYNTAX  INTEGER
  	    ACCESS  read-only
  	    STATUS  mandatory
  	    DESCRIPTION
  		"Time since input usage updated.
		 Units are 1/100 second."
  	    ::= { healthPortEntry 5 }


	healthPortRxTxData  OBJECT-TYPE
	    SYNTAX  OCTET STRING (SIZE(4))
	    ACCESS  read-only
	    STATUS  mandatory
	    DESCRIPTION
		"Port-level i/o utilization information.
		 Octet 0: average i/o utilization over the latest sample period (percent)
		 Octet 1: average i/o utilization over the latest minute (percent)
		 Octet 2: average i/o utilization over the latest hour (percent)
		 Octet 3: maximum i/o utilization over the latest hour (percent)
		 i/o utilization = (total octets input + total octets output) / module capacity."
	    ::= { healthPortEntry 6 }

  	healthPortRxTxTimeDelta  OBJECT-TYPE
  	    SYNTAX  INTEGER
  	    ACCESS  read-only
  	    STATUS  mandatory
  	    DESCRIPTION
  		"Time since i/o usage updated.
		 Units are 1/100 second."
  	    ::= { healthPortEntry 7 }


	healthPortBackplaneData  OBJECT-TYPE
	    SYNTAX  OCTET STRING (SIZE(4))
	    ACCESS  read-only
	    STATUS  mandatory
	    DESCRIPTION
		"Port-level backplane utilization information.
		 Octet 0: average backplane utilization over the latest sample period (percent)
		 Octet 1: average backplane utilization over the latest minute (percent)
		 Octet 2: average backplane utilization over the latest hour (percent)
		 Octet 3: maximum backplane utilization over the latest hour (percent)."
	    ::= { healthPortEntry 8 }

  	healthPortBackplaneTimeDelta  OBJECT-TYPE
  	    SYNTAX  INTEGER
  	    ACCESS  read-only
  	    STATUS  mandatory
  	    DESCRIPTION
  		"Time since backplane usage updated.
		 Units are 1/100 second."
	    ::= { healthPortEntry 9 }

	healthPortVccData  OBJECT-TYPE
	    SYNTAX  OCTET STRING (SIZE(4))
	    ACCESS  read-only
	    STATUS  mandatory
	    DESCRIPTION
		"Port-level Vcc utilization information.
		 Octet 0: average Vcc utilization over the latest sample period (percent)
		 Octet 1: average Vcc utilization over the latest minute (percent)
		 Octet 2: average Vcc utilization over the latest hour (percent)
		 Octet 3: maximum Vcc utilization over the latest hour (percent)
		 Vcc utilization = Vccs in use / port Vcc capacity."
	    ::= { healthPortEntry 10 }

  	healthPortVccTimeDelta  OBJECT-TYPE
  	    SYNTAX  INTEGER
  	    ACCESS  read-only
  	    STATUS  mandatory
  	    DESCRIPTION
  		"Time since Vcc usage updated.
		 Units are 1/100 second."
  	    ::= { healthPortEntry 11 }


	--  health2DeviceInfo group. This group contains device-level
	--  health monitoring information.  The objects in thisgroup
	--  permit an alternate way of accessing the information
        --  contained in objects in the healthDeviceInfo group.

	health2DeviceRxLatest  OBJECT-TYPE
	    SYNTAX  INTEGER  (0..100)
	    ACCESS  read-only
	    STATUS  mandatory
	    DESCRIPTION
		"Average device-level input utilization over the
		 latest sample period (percent)."
	    ::= { health2DeviceInfo 1 }

	health2DeviceRx1MinAvg  OBJECT-TYPE
	    SYNTAX  INTEGER  (0..100)
	    ACCESS  read-only
	    STATUS  mandatory
	    DESCRIPTION
		"Average device-level input utilization over the
		 last minute (percent)."
	    ::= { health2DeviceInfo 2 }

	health2DeviceRx1HrAvg  OBJECT-TYPE
	    SYNTAX  INTEGER  (0..100)
	    ACCESS  read-only
	    STATUS  mandatory
	    DESCRIPTION
		"Average device-level input utilization over the
		 last hour (percent)."
	    ::= { health2DeviceInfo 3 }

	health2DeviceRx1HrMax  OBJECT-TYPE
	    SYNTAX  INTEGER  (0..100)
	    ACCESS  read-only
	    STATUS  mandatory
	    DESCRIPTION
		"Maximum device-level input utilization over the
		 last hour (percent)."
	    ::= { health2DeviceInfo 4 }

	health2DeviceRxTxLatest  OBJECT-TYPE
	    SYNTAX  INTEGER  (0..100)
	    ACCESS  read-only
	    STATUS  mandatory
	    DESCRIPTION
		"Average device-level i/o utilization over the
		 latest sample period (percent)."
	    ::= { health2DeviceInfo 5 }

	health2DeviceRxTx1MinAvg  OBJECT-TYPE
	    SYNTAX  INTEGER  (0..100)
	    ACCESS  read-only
	    STATUS  mandatory
	    DESCRIPTION
		"Average device-level i/o utilization over the
		 last minute (percent)."
	    ::= { health2DeviceInfo 6 }

	health2DeviceRxTx1HrAvg  OBJECT-TYPE
	    SYNTAX  INTEGER  (0..100)
	    ACCESS  read-only
	    STATUS  mandatory
	    DESCRIPTION
		"Average device-level i/o utilization over the
		 last hour (percent)."
	    ::= { health2DeviceInfo 7 }

	health2DeviceRxTx1HrMax  OBJECT-TYPE
	    SYNTAX  INTEGER  (0..100)
	    ACCESS  read-only
	    STATUS  mandatory
	    DESCRIPTION
		"Maximum device-level i/o utilization over the
		 last hour (percent)."
	    ::= { health2DeviceInfo 8 }

	health2DeviceBackplaneLatest  OBJECT-TYPE
	    SYNTAX  INTEGER  (0..100)
	    ACCESS  read-only
	    STATUS  mandatory
	    DESCRIPTION
		"Average device-level backplane utilization over the
		 latest sample period (percent)."
	    ::= { health2DeviceInfo 9 }

	health2DeviceBackplane1MinAvg  OBJECT-TYPE
	    SYNTAX  INTEGER  (0..100)
	    ACCESS  read-only
	    STATUS  mandatory
	    DESCRIPTION
		"Average device-level backplane utilization over the
		 last minute (percent)."
	    ::= { health2DeviceInfo 10 }

	health2DeviceBackplane1HrAvg  OBJECT-TYPE
	    SYNTAX  INTEGER  (0..100)
	    ACCESS  read-only
	    STATUS  mandatory
	    DESCRIPTION
		"Average device-level backplane utilization over the
		 last hour (percent)."
	    ::= { health2DeviceInfo 11 }

	health2DeviceBackplane1HrMax  OBJECT-TYPE
	    SYNTAX  INTEGER  (0..100)
	    ACCESS  read-only
	    STATUS  mandatory
	    DESCRIPTION
		"Maximum device-level backplane utilization over the
		 last hour (percent)."
	    ::= { health2DeviceInfo 12 }

	health2DeviceMpmCamLatest  OBJECT-TYPE
	    SYNTAX  INTEGER  (0..100)
	    ACCESS  read-only
	    STATUS  mandatory
	    DESCRIPTION
		"Average MPM CAM utilization over the latest sample 
		 period (percent)."
	    ::= { health2DeviceInfo 13 }

	health2DeviceMpmCam1MinAvg  OBJECT-TYPE
	    SYNTAX  INTEGER  (0..100)
	    ACCESS  read-only
	    STATUS  mandatory
	    DESCRIPTION
		"Average MPM CAM utilization over the last minute
		 (percent)."
	    ::= { health2DeviceInfo 14 }

	health2DeviceMpmCam1HrAvg  OBJECT-TYPE
	    SYNTAX  INTEGER  (0..100)
	    ACCESS  read-only
	    STATUS  mandatory
	    DESCRIPTION
		"Average MPM CAM utilization over the last hour
		 (percent)."
	    ::= { health2DeviceInfo 15 }

	health2DeviceMpmCam1HrMax  OBJECT-TYPE
	    SYNTAX  INTEGER  (0..100)
	    ACCESS  read-only
	    STATUS  mandatory
	    DESCRIPTION
		"Maximum MPM CAM utilization over the last hour
		 (percent)."
	    ::= { health2DeviceInfo 16 }

	health2DeviceHreCamLatest  OBJECT-TYPE
	    SYNTAX  INTEGER  (0..100)
	    ACCESS  read-only
	    STATUS  mandatory
	    DESCRIPTION
		"Average HRE CAM utilization over the latest sample 
		 period (percent)."
	    ::= { health2DeviceInfo 17 }

	health2DeviceHreCam1MinAvg  OBJECT-TYPE
	    SYNTAX  INTEGER  (0..100)
	    ACCESS  read-only
	    STATUS  mandatory
	    DESCRIPTION
		"Average HRE CAM utilization over the last minute
		 (percent)."
	    ::= { health2DeviceInfo 18 }

	health2DeviceHreCam1HrAvg  OBJECT-TYPE
	    SYNTAX  INTEGER  (0..100)
	    ACCESS  read-only
	    STATUS  mandatory
	    DESCRIPTION
		"Average HRE CAM utilization over the last hour
		 (percent)."
	    ::= { health2DeviceInfo 19 }

	health2DeviceHreCam1HrMax  OBJECT-TYPE
	    SYNTAX  INTEGER  (0..100)
	    ACCESS  read-only
	    STATUS  mandatory
	    DESCRIPTION
		"Maximum HRE CAM utilization over the last hour
		 (percent)."
	    ::= { health2DeviceInfo 20 }

	health2DeviceMemoryLatest  OBJECT-TYPE
	    SYNTAX  INTEGER  (0..100)
	    ACCESS  read-only
	    STATUS  mandatory
	    DESCRIPTION
		"Average device-level memory utilization over the
		 latest sample period (percent)."
	    ::= { health2DeviceInfo 21 }

	health2DeviceMemory1MinAvg  OBJECT-TYPE
	    SYNTAX  INTEGER  (0..100)
	    ACCESS  read-only
	    STATUS  mandatory
	    DESCRIPTION
		"Average device-level memory utilization over the
		 last minute (percent)."
	    ::= { health2DeviceInfo 22 }

	health2DeviceMemory1HrAvg  OBJECT-TYPE
	    SYNTAX  INTEGER  (0..100)
	    ACCESS  read-only
	    STATUS  mandatory
	    DESCRIPTION
		"Average device-level memory utilization over the
		 last hour (percent)."
	    ::= { health2DeviceInfo 23 }

	health2DeviceMemory1HrMax  OBJECT-TYPE
	    SYNTAX  INTEGER  (0..100)
	    ACCESS  read-only
	    STATUS  mandatory
	    DESCRIPTION
		"Maximum device-level memory utilization over the
		 last hour (percent)."
	    ::= { health2DeviceInfo 24 }

	health2DeviceNumCpus  OBJECT-TYPE
	    SYNTAX  INTEGER
	    ACCESS  read-only
	    STATUS  mandatory
	    DESCRIPTION
		"Number of CPUs on MPM."
  	    ::= { health2DeviceInfo 25 }

	health2DeviceCpuTable  OBJECT-TYPE
	    SYNTAX  SEQUENCE OF Health2DeviceCpuEntry
	    ACCESS  not-accessible
	    STATUS  mandatory
	    DESCRIPTION
		"A list of device-level CPU utilization data."
	    ::= { health2DeviceInfo 26 }

	health2DeviceCpuEntry  OBJECT-TYPE
	    SYNTAX  Health2DeviceCpuEntry
	    ACCESS  not-accessible
	    STATUS  mandatory
	    DESCRIPTION
		"A device-level CPU utilization entry."
	    INDEX { health2DeviceCpuNum }
	    ::= { health2DeviceCpuTable 1 }

	Health2DeviceCpuEntry ::= SEQUENCE {
	    health2DeviceCpuNum
			INTEGER,
	    health2DeviceCpuLatest
			INTEGER,
	    health2DeviceCpu1MinAvg
			INTEGER,
	    health2DeviceCpu1HrAvg
			INTEGER,
	    health2DeviceCpu1HrMax
			INTEGER
	    }

	health2DeviceCpuNum  OBJECT-TYPE
	    SYNTAX  INTEGER  
	    ACCESS  read-only
	    STATUS  mandatory
	    DESCRIPTION
		"MPM CPU number."
	    ::= { health2DeviceCpuEntry 1 }

	health2DeviceCpuLatest  OBJECT-TYPE
	    SYNTAX  INTEGER  (0..100)
	    ACCESS  read-only
	    STATUS  mandatory
	    DESCRIPTION
		"Average device-level CPU utilization over the
		 latest sample period (percent)."
	    ::= { health2DeviceCpuEntry 2 }

	health2DeviceCpu1MinAvg  OBJECT-TYPE
	    SYNTAX  INTEGER  (0..100)
	    ACCESS  read-only
	    STATUS  mandatory
	    DESCRIPTION
		"Average device-level CPU utilization over the
		 last minute (percent)."
	    ::= { health2DeviceCpuEntry 3 }

	health2DeviceCpu1HrAvg  OBJECT-TYPE
	    SYNTAX  INTEGER  (0..100)
	    ACCESS  read-only
	    STATUS  mandatory
	    DESCRIPTION
		"Average device-level CPU utilization over the
		 last hour (percent)."
	    ::= { health2DeviceCpuEntry 4 }

	health2DeviceCpu1HrMax  OBJECT-TYPE
	    SYNTAX  INTEGER  (0..100)
	    ACCESS  read-only
	    STATUS  mandatory
	    DESCRIPTION
		"Maximum device-level CPU utilization over the
		 last hour (percent)."
	    ::= { health2DeviceCpuEntry 5 }

	health2DeviceVccLatest  OBJECT-TYPE
	    SYNTAX  INTEGER  (0..100)
	    ACCESS  read-only
	    STATUS  mandatory
	    DESCRIPTION
		"Average device-level VCC utilization over the
		 latest sample period (percent)."
	    ::= { health2DeviceInfo 27 }

	health2DeviceVcc1MinAvg  OBJECT-TYPE
	    SYNTAX  INTEGER  (0..100)
	    ACCESS  read-only
	    STATUS  mandatory
	    DESCRIPTION
		"Average device-level VCC utilization over the
		 last minute (percent)."
	    ::= { health2DeviceInfo 28 }

	health2DeviceVcc1HrAvg  OBJECT-TYPE
	    SYNTAX  INTEGER  (0..100)
	    ACCESS  read-only
	    STATUS  mandatory
	    DESCRIPTION
		"Average device-level VCC utilization over the
		 last hour (percent)."
	    ::= { health2DeviceInfo 29 }

	health2DeviceVcc1HrMax  OBJECT-TYPE
	    SYNTAX  INTEGER  (0..100)
	    ACCESS  read-only
	    STATUS  mandatory
	    DESCRIPTION
		"Maximum device-level VCC utilization over the
		 last hour (percent)."
	    ::= { health2DeviceInfo 30 }


	health2DeviceTemperatureLatest  OBJECT-TYPE
	    SYNTAX  INTEGER  (0..100)
	    ACCESS  read-only
	    STATUS  mandatory
	    DESCRIPTION
		"Average device temperature over the latest sample period (degrees Centigrade)."
	    ::= { health2DeviceInfo 31 }

	health2DeviceTemperature1MinAvg  OBJECT-TYPE
	    SYNTAX  INTEGER  (0..100)
	    ACCESS  read-only
	    STATUS  mandatory
	    DESCRIPTION
		"Average device temperature over the last minute (degrees Centigrade)."
	    ::= { health2DeviceInfo 32 }

	health2DeviceTemperature1HrAvg  OBJECT-TYPE
	    SYNTAX  INTEGER  (0..100)
	    ACCESS  read-only
	    STATUS  mandatory
	    DESCRIPTION
		"Average device temperature over the last hour (degrees centigrade)."
	    ::= { health2DeviceInfo 33 }

	health2DeviceTemperature1HrMax  OBJECT-TYPE
	    SYNTAX  INTEGER  (0..100)
	    ACCESS  read-only
	    STATUS  mandatory
	    DESCRIPTION
		"Maximum device temperature over the last hour (degrees Centigrade)."
	    ::= { health2DeviceInfo 34 }

	health2DeviceVpLatest  OBJECT-TYPE
	    SYNTAX  INTEGER  (0..100)
	    ACCESS  read-only
	    STATUS  mandatory
	    DESCRIPTION
		"Average device-level virtual port utilization over the
		 latest sample period (percent)."
	    ::= { health2DeviceInfo 35 }

	health2DeviceVp1MinAvg  OBJECT-TYPE
	    SYNTAX  INTEGER  (0..100)
	    ACCESS  read-only
	    STATUS  mandatory
	    DESCRIPTION
		"Average device-level virtual port utilization over the
		 last minute (percent)."
	    ::= { health2DeviceInfo 36 }

	health2DeviceVp1HrAvg  OBJECT-TYPE
	    SYNTAX  INTEGER  (0..100)
	    ACCESS  read-only
	    STATUS  mandatory
	    DESCRIPTION
		"Average device-level virtual port utilization over the
		 last hour (percent)."
	    ::= { health2DeviceInfo 37 }

	health2DeviceVp1HrMax  OBJECT-TYPE
	    SYNTAX  INTEGER  (0..100)
	    ACCESS  read-only
	    STATUS  mandatory
	    DESCRIPTION
		"Maximum device-level virtual port utilization over the
		 last hour (percent)."
	    ::= { health2DeviceInfo 38 }

	health2DeviceHreCollisionLatest  OBJECT-TYPE
	    SYNTAX  INTEGER  (0..100)
	    ACCESS  read-only
	    STATUS  mandatory
	    DESCRIPTION
		"Average HRE Collision utilization over the latest sample 
		 period (percent)."
	    ::= { health2DeviceInfo 39 }

	health2DeviceHreCollision1MinAvg  OBJECT-TYPE
	    SYNTAX  INTEGER  (0..100)
	    ACCESS  read-only
	    STATUS  mandatory
	    DESCRIPTION
		"Average HRE Collision utilization over the last minute
		 (percent)."
	    ::= { health2DeviceInfo 40 }

	health2DeviceHreCollision1HrAvg  OBJECT-TYPE
	    SYNTAX  INTEGER  (0..100)
	    ACCESS  read-only
	    STATUS  mandatory
	    DESCRIPTION
		"Average HRE Collision utilization over the last hour
		 (percent)."
	    ::= { health2DeviceInfo 41 }

	health2DeviceHreCollision1HrMax  OBJECT-TYPE
	    SYNTAX  INTEGER  (0..100)
	    ACCESS  read-only
	    STATUS  mandatory
	    DESCRIPTION
		"Maximum HRE Collision utilization over the last hour
		 (percent)."
	    ::= { health2DeviceInfo 42 }

	--  health2ModuleInfo group. This group contains module-level
	--  health monitoring information.


	--  health2ModuleTable. This table maintains the per slot
	--  data that is related to a specific installed module
	--  in a slot.
        --  This table allows access to the utilization percentages
	--   found in health2ModuleTable via INTEGERs.


	health2ModuleTable  OBJECT-TYPE
	    SYNTAX  SEQUENCE OF Health2ModuleEntry
	    ACCESS  not-accessible
	    STATUS  mandatory
	    DESCRIPTION
		"A list of installed modules in this chassis."
	    ::= { health2ModuleInfo 1 }

	health2ModuleEntry  OBJECT-TYPE
	    SYNTAX  Health2ModuleEntry
	    ACCESS  not-accessible
	    STATUS  mandatory
	    DESCRIPTION
		"A module entry containing objects for a module in a specific 'slot'."
	    INDEX { health2ModuleSlot }
	    ::= { health2ModuleTable 1 }

	Health2ModuleEntry ::= SEQUENCE {
	    health2ModuleSlot
			INTEGER,
	    health2ModuleRxLatest
			INTEGER,
	    health2ModuleRx1MinAvg
			INTEGER,
	    health2ModuleRx1HrAvg
			INTEGER,
	    health2ModuleRx1HrMax
			INTEGER,
	    health2ModuleRxTxLatest
			INTEGER,
	    health2ModuleRxTx1MinAvg
			INTEGER,
	    health2ModuleRxTx1HrAvg
			INTEGER,
	    health2ModuleRxTx1HrMax
			INTEGER,
	    health2ModuleBackplaneLatest
			INTEGER,
	    health2ModuleBackplane1MinAvg
			INTEGER,
	    health2ModuleBackplane1HrAvg
			INTEGER,
	    health2ModuleBackplane1HrMax
			INTEGER,
	    health2ModuleCamLatest
			INTEGER,
	    health2ModuleCam1MinAvg
			INTEGER,
	    health2ModuleCam1HrAvg
			INTEGER,
	    health2ModuleCam1HrMax
			INTEGER,
	    health2ModuleVccLatest
			INTEGER,
	    health2ModuleVcc1MinAvg
			INTEGER,
	    health2ModuleVcc1HrAvg
			INTEGER,
	    health2ModuleVcc1HrMax
			INTEGER
	    }

	health2ModuleSlot  OBJECT-TYPE
	    SYNTAX  INTEGER
	    ACCESS  read-only
	    STATUS  mandatory
	    DESCRIPTION
		"The (one-based) front slot number within the chassis."
	    ::= { health2ModuleEntry 1 }

	health2ModuleRxLatest  OBJECT-TYPE
	    SYNTAX  INTEGER (0..100)
	    ACCESS  read-only
	    STATUS  mandatory
	    DESCRIPTION
		"Average module-level input utilization over the 
		 latest sample period (percent)."
	    ::= { health2ModuleEntry 2 }

	health2ModuleRx1MinAvg  OBJECT-TYPE
	    SYNTAX  INTEGER (0..100)
	    ACCESS  read-only
	    STATUS  mandatory
	    DESCRIPTION
		"Average module-level input utilization over the 
		 last minute (percent)."
	    ::= { health2ModuleEntry 3 }

	health2ModuleRx1HrAvg  OBJECT-TYPE
	    SYNTAX  INTEGER (0..100)
	    ACCESS  read-only
	    STATUS  mandatory
	    DESCRIPTION
		"Average module-level input utilization over the 
		 last hour (percent)."
	    ::= { health2ModuleEntry 4 }

	health2ModuleRx1HrMax  OBJECT-TYPE
	    SYNTAX  INTEGER (0..100)
	    ACCESS  read-only
	    STATUS  mandatory
	    DESCRIPTION
		"Maximum module-level input utilization over the 
		 last hour (percent)."
	    ::= { health2ModuleEntry 5 }

	health2ModuleRxTxLatest  OBJECT-TYPE
	    SYNTAX  INTEGER (0..100)
	    ACCESS  read-only
	    STATUS  mandatory
	    DESCRIPTION
		"Average module-level i/o utilization over the 
		 latest sample period (percent)."
	    ::= { health2ModuleEntry 6 }

	health2ModuleRxTx1MinAvg  OBJECT-TYPE
	    SYNTAX  INTEGER (0..100)
	    ACCESS  read-only
	    STATUS  mandatory
	    DESCRIPTION
		"Average module-level i/o utilization over the 
		 last minute (percent)."
	    ::= { health2ModuleEntry 7 }

	health2ModuleRxTx1HrAvg  OBJECT-TYPE
	    SYNTAX  INTEGER (0..100)
	    ACCESS  read-only
	    STATUS  mandatory
	    DESCRIPTION
		"Average module-level i/o utilization over the 
		 last hour (percent)."
	    ::= { health2ModuleEntry 8 }

	health2ModuleRxTx1HrMax  OBJECT-TYPE
	    SYNTAX  INTEGER (0..100)
	    ACCESS  read-only
	    STATUS  mandatory
	    DESCRIPTION
		"Maximum module-level i/o utilization over the 
		 last hour (percent)."
	    ::= { health2ModuleEntry 9 }


	health2ModuleBackplaneLatest  OBJECT-TYPE
	    SYNTAX  INTEGER (0..100)
	    ACCESS  read-only
	    STATUS  mandatory
	    DESCRIPTION
		"Average module-level backplane utilization over the 
		 latest sample period (percent)."
	    ::= { health2ModuleEntry 10 }

	health2ModuleBackplane1MinAvg  OBJECT-TYPE
	    SYNTAX  INTEGER (0..100)
	    ACCESS  read-only
	    STATUS  mandatory
	    DESCRIPTION
		"Average module-level backplane utilization over the 
		 last minute (percent)."
	    ::= { health2ModuleEntry 11 }

	health2ModuleBackplane1HrAvg  OBJECT-TYPE
	    SYNTAX  INTEGER (0..100)
	    ACCESS  read-only
	    STATUS  mandatory
	    DESCRIPTION
		"Average module-level backplane utilization over the 
		 last hour (percent)."
	    ::= { health2ModuleEntry 12 }

	health2ModuleBackplane1HrMax  OBJECT-TYPE
	    SYNTAX  INTEGER (0..100)
	    ACCESS  read-only
	    STATUS  mandatory
	    DESCRIPTION
		"Maximum module-level backplane utilization over the 
		 last hour (percent)."
	    ::= { health2ModuleEntry 13 }

	health2ModuleCamLatest  OBJECT-TYPE
	    SYNTAX  INTEGER (0..100)
	    ACCESS  read-only
	    STATUS  mandatory
	    DESCRIPTION
		"Average module-level CAM utilization over the 
		 latest sample period (percent)."
	    ::= { health2ModuleEntry 14 }

	health2ModuleCam1MinAvg  OBJECT-TYPE
	    SYNTAX  INTEGER (0..100)
	    ACCESS  read-only
	    STATUS  mandatory
	    DESCRIPTION
		"Average module-level CAM utilization over the 
		 last minute (percent)."
	    ::= { health2ModuleEntry 15 }

	health2ModuleCam1HrAvg  OBJECT-TYPE
	    SYNTAX  INTEGER (0..100)
	    ACCESS  read-only
	    STATUS  mandatory
	    DESCRIPTION
		"Average module-level CAM utilization over the 
		 last hour (percent)."
	    ::= { health2ModuleEntry 16 }

	health2ModuleCam1HrMax  OBJECT-TYPE
	    SYNTAX  INTEGER (0..100)
	    ACCESS  read-only
	    STATUS  mandatory
	    DESCRIPTION
		"Maximum module-level CAM utilization over the 
		 last hour (percent)."
	    ::= { health2ModuleEntry 17 }

	health2ModuleVccLatest  OBJECT-TYPE
	    SYNTAX  INTEGER (0..100)
	    ACCESS  read-only
	    STATUS  mandatory
	    DESCRIPTION
		"Average module-level VCC utilization over the 
		 latest sample period (percent)."
	    ::= { health2ModuleEntry 18 }

	health2ModuleVcc1MinAvg  OBJECT-TYPE
	    SYNTAX  INTEGER (0..100)
	    ACCESS  read-only
	    STATUS  mandatory
	    DESCRIPTION
		"Average module-level VCC utilization over the 
		 last minute (percent)."
	    ::= { health2ModuleEntry 19 }

	health2ModuleVcc1HrAvg  OBJECT-TYPE
	    SYNTAX  INTEGER (0..100)
	    ACCESS  read-only
	    STATUS  mandatory
	    DESCRIPTION
		"Average module-level VCC utilization over the 
		 last hour (percent)."
	    ::= { health2ModuleEntry 20 }

	health2ModuleVcc1HrMax  OBJECT-TYPE
	    SYNTAX  INTEGER (0..100)
	    ACCESS  read-only
	    STATUS  mandatory
	    DESCRIPTION
		"Maximum module-level VCC utilization over the 
		 last hour (percent)."
	    ::= { health2ModuleEntry 21 }

	health2PortTable  OBJECT-TYPE
	    SYNTAX  SEQUENCE OF Health2PortEntry
	    ACCESS  not-accessible
	    STATUS  mandatory
	    DESCRIPTION
		"A list of Physical Port health instances."
	    ::= { health2PortInfo 1 }

	health2PortEntry  OBJECT-TYPE
	    SYNTAX  Health2PortEntry
	    ACCESS  not-accessible
	    STATUS  mandatory
	    DESCRIPTION
		"A Physical Port health entry."
	    INDEX { health2PortSlot, health2PortIF }
	    ::= { health2PortTable 1 }

	Health2PortEntry ::= SEQUENCE {
	    health2PortSlot
			INTEGER,
	    health2PortIF
			INTEGER,
	    health2PortRxLatest
			INTEGER,
	    health2PortRx1MinAvg
			INTEGER,
	    health2PortRx1HrAvg
			INTEGER,
	    health2PortRx1HrMax
			INTEGER,
	    health2PortRxTxLatest
			INTEGER,
	    health2PortRxTx1MinAvg
			INTEGER,
	    health2PortRxTx1HrAvg
			INTEGER,
	    health2PortRxTx1HrMax
			INTEGER,
	    health2PortBackplaneLatest
			INTEGER,
	    health2PortBackplane1MinAvg
			INTEGER,
	    health2PortBackplane1HrAvg
			INTEGER,
	    health2PortBackplane1HrMax
			INTEGER,
	    health2PortVccLatest
			INTEGER,
	    health2PortVcc1MinAvg
			INTEGER,
	    health2PortVcc1HrAvg
			INTEGER,
	    health2PortVcc1HrMax
			INTEGER
	    }

	health2PortSlot  OBJECT-TYPE
	    SYNTAX  INTEGER (1..9)
	    ACCESS  read-only
	    STATUS  mandatory
	    DESCRIPTION
		"The physical slot number for this port."
	    ::= { health2PortEntry 1 }

	health2PortIF  OBJECT-TYPE
	    SYNTAX  INTEGER 
	    ACCESS  read-only
	    STATUS  mandatory
	    DESCRIPTION
		"The on-board interface number."
	    ::= { health2PortEntry 2 }

	health2PortRxLatest  OBJECT-TYPE
	    SYNTAX  INTEGER (0..100)
	    ACCESS  read-only
	    STATUS  mandatory
	    DESCRIPTION
		"Average port-level input utilization over the 
		 latest sample period (percent)."
	    ::= { health2PortEntry 3 }

	health2PortRx1MinAvg  OBJECT-TYPE
	    SYNTAX  INTEGER (0..100)
	    ACCESS  read-only
	    STATUS  mandatory
	    DESCRIPTION
		"Average port-level input utilization over the 
		 last minute (percent)."
	    ::= { health2PortEntry 4 }

	health2PortRx1HrAvg  OBJECT-TYPE
	    SYNTAX  INTEGER (0..100)
	    ACCESS  read-only
	    STATUS  mandatory
	    DESCRIPTION
		"Average port-level input utilization over the 
		 last hour (percent)."
	    ::= { health2PortEntry 5 }

	health2PortRx1HrMax  OBJECT-TYPE
	    SYNTAX  INTEGER (0..100)
	    ACCESS  read-only
	    STATUS  mandatory
	    DESCRIPTION
		"Maximum port-level input utilization over the 
		 last hour (percent)."
	    ::= { health2PortEntry 6 }

	health2PortRxTxLatest  OBJECT-TYPE
	    SYNTAX  INTEGER (0..100)
	    ACCESS  read-only
	    STATUS  mandatory
	    DESCRIPTION
		"Average port-level i/o utilization over the 
		 latest sample period (percent)."
	    ::= { health2PortEntry 7 }

	health2PortRxTx1MinAvg  OBJECT-TYPE
	    SYNTAX  INTEGER (0..100)
	    ACCESS  read-only
	    STATUS  mandatory
	    DESCRIPTION
		"Average port-level i/o utilization over the 
		 last minute (percent)."
	    ::= { health2PortEntry 8 }

	health2PortRxTx1HrAvg  OBJECT-TYPE
	    SYNTAX  INTEGER (0..100)
	    ACCESS  read-only
	    STATUS  mandatory
	    DESCRIPTION
		"Average port-level i/o utilization over the 
		 last hour (percent)."
	    ::= { health2PortEntry 9 }

	health2PortRxTx1HrMax  OBJECT-TYPE
	    SYNTAX  INTEGER (0..100)
	    ACCESS  read-only
	    STATUS  mandatory
	    DESCRIPTION
		"Maximum port-level i/o utilization over the 
		 last hour (percent)."
	    ::= { health2PortEntry 10 }

	health2PortBackplaneLatest  OBJECT-TYPE
	    SYNTAX  INTEGER (0..100)
	    ACCESS  read-only
	    STATUS  mandatory
	    DESCRIPTION
		"Average port-level backplane utilization over the 
		 latest sample period (percent)."
	    ::= { health2PortEntry 11 }

	health2PortBackplane1MinAvg  OBJECT-TYPE
	    SYNTAX  INTEGER (0..100)
	    ACCESS  read-only
	    STATUS  mandatory
	    DESCRIPTION
		"Average port-level backplane utilization over the 
		 last minute (percent)."
	    ::= { health2PortEntry 12 }

	health2PortBackplane1HrAvg  OBJECT-TYPE
	    SYNTAX  INTEGER (0..100)
	    ACCESS  read-only
	    STATUS  mandatory
	    DESCRIPTION
		"Average port-level backplane utilization over the 
		 last hour (percent)."
	    ::= { health2PortEntry 13 }

	health2PortBackplane1HrMax  OBJECT-TYPE
	    SYNTAX  INTEGER (0..100)
	    ACCESS  read-only
	    STATUS  mandatory
	    DESCRIPTION
		"Maximum port-level backplane utilization over the 
		 last hour (percent)."
	    ::= { health2PortEntry 14 }

	health2PortVccLatest  OBJECT-TYPE
	    SYNTAX  INTEGER (0..100)
	    ACCESS  read-only
	    STATUS  mandatory
	    DESCRIPTION
		"Average port-level VCC utilization over the 
		 latest sample period (percent)."
	    ::= { health2PortEntry 15 }

	health2PortVcc1MinAvg  OBJECT-TYPE
	    SYNTAX  INTEGER (0..100)
	    ACCESS  read-only
	    STATUS  mandatory
	    DESCRIPTION
		"Average port-level VCC utilization over the 
		 last minute (percent)."
	    ::= { health2PortEntry 16 }

	health2PortVcc1HrAvg  OBJECT-TYPE
	    SYNTAX  INTEGER (0..100)
	    ACCESS  read-only
	    STATUS  mandatory
	    DESCRIPTION
		"Average port-level VCC utilization over the 
		 last hour (percent)."
	    ::= { health2PortEntry 17 }

	health2PortVcc1HrMax  OBJECT-TYPE
	    SYNTAX  INTEGER (0..100)
	    ACCESS  read-only
	    STATUS  mandatory
	    DESCRIPTION
		"Maximum port-level VCC utilization over the 
		 last hour (percent)."
	    ::= { health2PortEntry 18 }

	END
