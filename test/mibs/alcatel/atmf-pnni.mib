PNNI-MIB DEFINITIONS ::= BEGIN

-- The following imports have been modified by Xylan
--
--      IMPORTS
--              MODULE-IDENTITY, OBJECT-TYPE, OBJECT-IDENTITY,
--              Counter32, Gauge32, Integer32, enterprises
--                      FROM SNMPv2-SMI
--              TEXTUAL-CONVENTION, RowStatus, DisplayString,
--              TimeStamp, TruthValue
--                      FROM SNMPv2-TC
--              InterfaceIndex, ifIndex
--                      FROM IF-MIB
--              AtmTrafficDescrParamIndex
--                      FROM ATM-MIB
--              MODULE-COMPLIANCE, OBJECT-GROUP
--                      FROM SNMPv2-CONF;

        IMPORTS
                MODULE-IDENTITY, OBJECT-TYPE,
                Counter32, Gauge32, Integer32, Unsigned32, zeroDotZero
                        FROM SNMPv2-SMI
                TEXTUAL-CONVENTION, RowStatus, DisplayString,
                TimeStamp, TruthValue
                        FROM SNMPv2-TC
		atmfPnni
			FROM XYLAN-BASE-MIB
                ifIndex FROM RFC1213-MIB
                MODULE-COMPLIANCE, OBJECT-GROUP
                        FROM SNMPv2-CONF;

pnniMIB MODULE-IDENTITY
        LAST-UPDATED    "9705010000Z"
        ORGANIZATION    "The ATM Forum"
        CONTACT-INFO
            "The ATM Forum
             2570 West El Camino Real, Suite 304
             Mountain View, CA 94040-1313 USA
             Phone: +1 415-949-6700
             Fax:   +1 415-949-6705
             info@atmforum.com"
        DESCRIPTION
            "The MIB module for managing ATM Forum PNNI routing."
        REVISION        "9705010000Z"
        DESCRIPTION
            "Updated version of the PNNI MIB released with the PNNI
             V1.0 Errata and PICS (af-pnni-0081.000)."
        REVISION        "9602270000Z"
        DESCRIPTION
            "Initial version of the MIB for monitoring and controlling
             PNNI routing."
        ::= { atmfPnni 1 }

-- The object identifier subtree for ATM Forum PNNI MIBs

-- These were removed and placed in xylan.mib
-- atmForum        OBJECT IDENTIFIER ::= { enterprises 353 }
-- atmForumNetworkManagement       OBJECT IDENTIFIER ::= { atmForum 5 }
-- atmfPnni        OBJECT IDENTIFIER ::= { atmForumNetworkManagement 4 }

-- These were added by Xylan
AtmTrafficDescrParamIndex ::= INTEGER
InterfaceIndex ::= INTEGER


pnniMIBObjects OBJECT IDENTIFIER ::= { pnniMIB 1 }


--    Unsigned32 ::= TEXTUAL-CONVENTION
--        STATUS        current
--        DESCRIPTION
--            "This definition, which is in compliance with RFC 1902, is a
--             temporary inclusion in the PNNI MIB until such time as MIB
--             compilers are upgraded and thereby can accept references to
--             the new definitions in RFC 1902."
--        REFERENCE
--            "RFC 1902"
--        SYNTAX        Gauge32


    PnniAtmAddr ::= TEXTUAL-CONVENTION
        STATUS        current
        DESCRIPTION
            "The ATM address used by the network entity.  The address
             types are: no address (0 octets), and NSAP (20 octets)."
        REFERENCE
            "ATM Forum PNNI 1.0 Section 5.2"
        SYNTAX        OCTET STRING (SIZE(0|20))


    PnniNodeIndex ::= TEXTUAL-CONVENTION
        STATUS        current
        DESCRIPTION
            "An index that identifies a logical PNNI entity within the
             managed system.

             The distinguished value zero indicates the null instance or
             no instance in the PnniNodeCfgParentNodeIndex.  In all
             other cases, the distinguished value zero indicates a
             logical entity within the switching system that manages
             routes only over non-PNNI interfaces.

             By default, only the node identified by node index one is
             created, and all PNNI interfaces are associated with that
             node."
        SYNTAX        Integer32 (0..65535)


    PnniNodeId ::= TEXTUAL-CONVENTION
        STATUS        current
        DESCRIPTION
            "A PNNI node ID - this is used to identify the logical PNNI
             node."
        REFERENCE
            "ATM Forum PNNI 1.0 Section 5.3.3"
        SYNTAX        OCTET STRING (SIZE(22))


    PnniPortId ::= TEXTUAL-CONVENTION
        STATUS        current
        DESCRIPTION
            "A PNNI port ID - this is used to identify a point of
             attachment of a logical link to a given logical node.

             The values 0 and 0xffffffff have special meanings in
             certain contexts and do not identify a specific port.

             The distinguished value 0 indicates that no port is
             specified."
        REFERENCE
            "ATM Forum PNNI 1.0 Section 5.3.4"
        SYNTAX        Unsigned32


    PnniAggrToken ::= TEXTUAL-CONVENTION
        STATUS        current
        DESCRIPTION
            "A PNNI aggregation token - this is used to determine which
             links to a given neighbor node are to be aggregated and
             advertised as a single logical link."
        REFERENCE
            "ATM Forum PNNI 1.0 Section 5.3.5"
        SYNTAX        Unsigned32


    PnniPeerGroupId ::= TEXTUAL-CONVENTION
        STATUS        current
        DESCRIPTION
            "A PNNI peer group ID."
        REFERENCE
            "ATM Forum PNNI 1.0 Section 5.3.2"
        SYNTAX        OCTET STRING (SIZE(14))


    PnniLevel ::= TEXTUAL-CONVENTION
        STATUS        current
        DESCRIPTION
            "A PNNI routing level indicator."
        REFERENCE
            "ATM Forum PNNI 1.0 Section 5.3.1"
        SYNTAX        Integer32 (0..104)


    PnniSvccRccIndex ::= TEXTUAL-CONVENTION
        STATUS        current
        DESCRIPTION
            "The value of this object identifies the SVCC-based RCC for
             which the entry contains management information."
        SYNTAX        Integer32


    AtmAddrPrefix ::= TEXTUAL-CONVENTION
        STATUS        current
        DESCRIPTION
            "A prefix of one or more ATM End System Addresses.  The
             significant portion of a prefix is padded with zeros on the
             right to fill 19 octets."
        REFERENCE
            "ATM Forum PNNI 1.0 Section 5.2"
        SYNTAX        OCTET STRING (SIZE(19))


    PnniPrefixLength ::= TEXTUAL-CONVENTION
        STATUS        current
        DESCRIPTION
            "The number of bits that are significant in an ATM address
             prefix used by PNNI."
        REFERENCE
            "ATM Forum PNNI 1.0 Section 5.2"
        SYNTAX        Integer32 (0..152)


    PnniMetricsTag ::= TEXTUAL-CONVENTION
        STATUS        current
        DESCRIPTION
            "An index into the pnniMetricsTable.  The suffix tag is used
             to indicate that there may be many related entries in the
             table further discriminated by other index terms.  The
             distinguished value zero indicates that no metrics are
             associated with the described entity."
        SYNTAX        Integer32 (0..2147483647)


    ServiceCategory ::= TEXTUAL-CONVENTION
        STATUS        current
        DESCRIPTION
            "Indicates the service category."
        REFERENCE
            "ATM Forum Traffic Management 4.0 Section 2"
        SYNTAX        INTEGER { other(1),
                                cbr(2),
                                rtVbr(3),
                                nrtVbr(4),
                                abr(5),
                                ubr(6) }


    ClpType ::= TEXTUAL-CONVENTION
        STATUS        current
        DESCRIPTION
            "Indicates the CLP type of a traffic stream."
        SYNTAX        INTEGER { clpEqual0(1), clpEqual0Or1(2) }


    TnsType ::= TEXTUAL-CONVENTION
        STATUS        current
        DESCRIPTION
            "Indicates the type of network identification of a
             specified transit network."
        REFERENCE
            "ATM Forum UNI Signalling 4.0 Section 2 4.5.22/Q.2931"
        SYNTAX        INTEGER { nationalNetworkIdentification(2),
                                other(8) }


    TnsPlan ::= TEXTUAL-CONVENTION
        STATUS        current
        DESCRIPTION
            "Indicates the network identification plan of a
             specified transit network."
        REFERENCE
            "ATM Forum UNI Signalling 4.0 Section 2 4.5.22/Q.2931"
        SYNTAX        INTEGER { carrierIdentificationCode(1),
                                other(16) }

    PnniVersion ::= TEXTUAL-CONVENTION
        STATUS        current
        DESCRIPTION
            "Indicates a version of the PNNI protocol."
        REFERENCE
            "ATM Forum PNNI 1.0 Section 5.6.1"
        SYNTAX        INTEGER { unsupported(1), version1point0(2) }


    PnniHelloState ::= TEXTUAL-CONVENTION
        STATUS        current
        DESCRIPTION
            "The state of an instance of the PNNI Hello State machine."
        REFERENCE
            "ATM Forum PNNI 1.0 Section 5.6.2.1.2"
        SYNTAX        INTEGER {
                                notApplicable(1),
                                down(2),
                                attempt(3),
                                oneWayInside(4),
                                twoWayInside(5),
                                oneWayOutside(6),
                                twoWayOutside(7),
                                commonOutside(8)
                                }

-- Removed by Xylan
--    zeroDotZero   OBJECT-IDENTITY
--        STATUS        current
--        DESCRIPTION
--            "A value used for null identifiers.
--
--             This definition, which is in compliance with RFC 1902, is a
--             temporary inclusion in the PNNI MIB until such time as MIB
--             compilers are upgraded and thereby can accept references to
--             the new definitions in RFC 1902."
--        REFERENCE
--            "RFC 1902"
--        ::= { 0 0 }


-- the base group

pnniBaseGroup OBJECT IDENTIFIER ::= { pnniMIBObjects 1 }

pnniHighestVersion OBJECT-TYPE
        SYNTAX        PnniVersion
        MAX-ACCESS    read-only
        STATUS        current
        DESCRIPTION
            "The highest version of the PNNI protocol that the
             software in this switching system is capable of executing."
        REFERENCE
            "ATM Forum PNNI 1.0 Section 5.6.1"
        ::= { pnniBaseGroup 1 }

pnniLowestVersion OBJECT-TYPE
        SYNTAX        PnniVersion
        MAX-ACCESS    read-only
        STATUS        current
        DESCRIPTION
            "The lowest version of the PNNI Protocol that the
             software in this switching system is capable of executing."
        REFERENCE
            "ATM Forum PNNI 1.0 Section 5.6.1"
        ::= { pnniBaseGroup 2 }

pnniDtlCountOriginator OBJECT-TYPE
        SYNTAX        Counter32
        MAX-ACCESS    read-only
        STATUS        current
        DESCRIPTION
            "The total number of DTL stacks that this switching system
             has originated as the DTLOriginator and placed into
             signalling messages. This includes the initial DTL stacks
             computed by this system as well as any alternate route
             (second, third choice etc.) DTL stacks computed by this
             switching system in response to crankbacks."
        ::= { pnniBaseGroup 3 }

pnniDtlCountBorder OBJECT-TYPE
        SYNTAX        Counter32
        MAX-ACCESS    read-only
        STATUS        current
        DESCRIPTION
            "The number of partial DTL stacks that this switching system
             has added into signalling messages as an entry border node.
             This includes the initial partial DTL stacks computed by
             this system as well as any alternate route (second, third
             choice etc.) partial DTL stacks computed by this switching
             system in response to crankbacks."
        ::= { pnniBaseGroup 4 }

pnniCrankbackCountOriginator OBJECT-TYPE
        SYNTAX        Counter32
        MAX-ACCESS    read-only
        STATUS        current
        DESCRIPTION
            "The count of the total number of connection setup messages
             including DTL stacks originated by this switching system
             that have cranked back to this switching system at all
             levels of the hierarchy."
        ::= { pnniBaseGroup 5 }

pnniCrankbackCountBorder OBJECT-TYPE
        SYNTAX        Counter32
        MAX-ACCESS    read-only
        STATUS        current
        DESCRIPTION
            "The count of the total number of connection setup messages
             including DTLs added by this switching system as an entry
             border node that have cranked back to this switching system
             at all levels of the hierarchy. This count does not include
             Crankbacks for which this switching system was not the
             crankback destination, only those crankbacks that were
             directed to this switching system are counted here."
        ::= { pnniBaseGroup 6 }

pnniAltRouteCountOriginator OBJECT-TYPE
        SYNTAX        Counter32
        MAX-ACCESS    read-only
        STATUS        current
        DESCRIPTION
            "The total number of alternate DTL stacks that this
             switching system has computed and placed into
             signalling messages as the DTLOriginator."
        ::= { pnniBaseGroup 7 }

pnniAltRouteCountBorder OBJECT-TYPE
        SYNTAX        Counter32
        MAX-ACCESS    read-only
        STATUS        current
        DESCRIPTION
            "The total number of alternate partial DTL stacks that this
             switching system has computed and placed into signalling
             messages as an entry border node."
        ::= { pnniBaseGroup 8 }

pnniRouteFailCountOriginator OBJECT-TYPE
        SYNTAX        Counter32
        MAX-ACCESS    read-only
        STATUS        current
        DESCRIPTION
            "The total number of times where the switching system failed
             to compute a viable DTL stack as the DTLOriginator for some
             call.  It indicates the number of times a call was cleared
             from this switching system due to originator routing
             failure."
        ::= { pnniBaseGroup 9 }

pnniRouteFailCountBorder OBJECT-TYPE
        SYNTAX        Counter32
        MAX-ACCESS    read-only
        STATUS        current
        DESCRIPTION
            "The total number of times where the switching system failed
             to compute a viable partial DTL stack as an entry border
             node for some call.  It indicates the number of times a
             call was either cleared or cranked back from this switching
             system due to border routing failure."
        ::= { pnniBaseGroup 10 }

pnniRouteFailUnreachableOriginator OBJECT-TYPE
        SYNTAX        Counter32
        MAX-ACCESS    read-only
        STATUS        current
        DESCRIPTION
            "The total number of times where the switching system failed
             to compute a viable DTL stack as the DTLOriginator because
             the destination was unreachable, i.e., those calls that are
             cleared with cause #2 `specified transit network
             unreachable' or cause #3 `destination unreachable' in the
             cause IE."
        ::= { pnniBaseGroup 11 }

pnniRouteFailUnreachableBorder OBJECT-TYPE
        SYNTAX        Counter32
        MAX-ACCESS    read-only
        STATUS        current
        DESCRIPTION
            "The total number of times where the switching system failed
             to compute a viable partial DTL stack as an entry border
             node because the target of the path calculation was
             unreachable, i.e., those calls that are cleared or cranked
             back with cause #2 `specified transit network unreachable'
             or cause #3 `destination unreachable' in the cause IE."
        ::= { pnniBaseGroup 12 }


-- node table

pnniNodeTable OBJECT-TYPE
        SYNTAX        SEQUENCE OF PnniNodeEntry
        MAX-ACCESS    not-accessible
        STATUS        current
        DESCRIPTION
            "The pnniNodeTable collects attributes that affect the
             operation of a PNNI logical node.

             There is a single row in this table for each PNNI peer
             group that the managed system is expected or eligible
             to become a member of."
        REFERENCE
            "ATM Forum PNNI 1.0 Annex F"
        ::= { pnniMIBObjects 2 }

pnniNodeEntry OBJECT-TYPE
        SYNTAX        PnniNodeEntry
        MAX-ACCESS    not-accessible
        STATUS        current
        DESCRIPTION
            "An entry in the table, containing information about a PNNI
             logical node in this switching system."
        REFERENCE
            "ATM Forum PNNI 1.0 Annex F"
        INDEX         { pnniNodeIndex }
        ::= { pnniNodeTable 1 }

PnniNodeEntry ::=
        SEQUENCE {
                pnniNodeIndex           PnniNodeIndex,
                pnniNodeLevel           PnniLevel,
                pnniNodeId              PnniNodeId,
                pnniNodeLowest          TruthValue,
                pnniNodeAdminStatus     INTEGER,
                pnniNodeOperStatus      INTEGER,
                pnniNodeDomainName      DisplayString,
                pnniNodeAtmAddress      PnniAtmAddr,
                pnniNodePeerGroupId     PnniPeerGroupId,
                pnniNodeRestrictedTransit       TruthValue,
                pnniNodeComplexRep      TruthValue,
                pnniNodeRestrictedBranching     TruthValue,
                pnniNodeDatabaseOverload        TruthValue,
                pnniNodePtses           Gauge32,
                pnniNodeRowStatus       RowStatus
                }

pnniNodeIndex OBJECT-TYPE
        SYNTAX        PnniNodeIndex
        MAX-ACCESS    not-accessible
        STATUS        current
        DESCRIPTION
            "A value assigned to a node in this switching system that
             uniquely identifies it in the MIB."
        ::= { pnniNodeEntry 1 }

pnniNodeLevel OBJECT-TYPE
        SYNTAX        PnniLevel
        MAX-ACCESS    read-create
        STATUS        current
        DESCRIPTION
            "The level of PNNI hierarchy at which this node exists. This
             attribute is used to determine the default node ID and the
             default peer group ID for this node. This object may only
             be written when pnniNodeAdminStatus has the value down."
        REFERENCE
            "ATM Forum PNNI 1.0 Section 5.3.1, Annex F"
        DEFVAL { 96 }
        ::= { pnniNodeEntry 2 }

pnniNodeId OBJECT-TYPE
        SYNTAX        PnniNodeId
        MAX-ACCESS    read-create
        STATUS        current
        DESCRIPTION
            "The value the switching system is using to represent
             itself as this node. This object may only be written when
             pnniNodeAdminStatus has the value down.

             If pnniNodeLowest is true, then the default node ID takes
             the form defined in Section 5.3.3 for lowest level nodes,
             with the first octet equal to pnniNodeLevel, the second
             octet equal to 160, and the last 20 octets equal to
             pnniNodeAtmAddress.

             If pnniNodeLowest is false, then the default
             node ID takes the form defined in Section 5.3.3 for logical
             group nodes, with the first octet equal to pnniNodeLevel,
             the next fourteen octets equal to the value of
             pnniNodePeerGroupId for the child node whose election as
             PGL causes this LGN to be instantiated, the next six octets
             equal to the ESI of pnniNodeAtmAddress, and the last octet
             equal to zero."
        REFERENCE
            "ATM Forum PNNI 1.0 Section 5.3.3, Annex F"
        ::= { pnniNodeEntry 3 }

pnniNodeLowest OBJECT-TYPE
        SYNTAX        TruthValue
        MAX-ACCESS    read-create
        STATUS        current
        DESCRIPTION
            "Indicates whether this node acts as a lowest level node or
             whether this node is a logical group node that becomes
             active when one of the other nodes in this switching system
             becomes a peer group leader.  The value 'false' must not be
             used with nodes that are not PGL/LGN capable.

             This object may only be
             written when pnniNodeAdminStatus has the value down."
        DEFVAL { true }
        ::= { pnniNodeEntry 4 }

pnniNodeAdminStatus OBJECT-TYPE
        SYNTAX        INTEGER { up(1), down(2) }
        MAX-ACCESS    read-create
        STATUS        current
        DESCRIPTION
            "Indicates whether the administrative status of the node is
             up (the node is allowed to become active) or down (the node
             is forced to be inactive).

             When pnniNodeAdminStatus is down, then pnniNodeOperStatus
             must also be down."
        DEFVAL { up }
        ::= { pnniNodeEntry 5 }

pnniNodeOperStatus OBJECT-TYPE
        SYNTAX        INTEGER { up(1), down(2) }
        MAX-ACCESS    read-only
        STATUS        current
        DESCRIPTION
            "Indicates whether the node is active or whether the node
             has yet to become operational.  When the value is down, all
             state has been cleared from the node and the node is not
             communicating with any of its neighbor nodes."
        ::= { pnniNodeEntry 6 }

pnniNodeDomainName OBJECT-TYPE
        SYNTAX        DisplayString
        MAX-ACCESS    read-create
        STATUS        current
        DESCRIPTION
            "The name of the PNNI routing
             domain in which this node participates.  All lowest-level
             PNNI nodes with the same pnniNodeDomainName are presumed to
             be connected."
        DEFVAL { "" }
        ::= { pnniNodeEntry 7 }

pnniNodeAtmAddress OBJECT-TYPE
        SYNTAX        PnniAtmAddr
        MAX-ACCESS    read-create
        STATUS        current
        DESCRIPTION
            "This node's ATM End System Address.  Remote systems wishing
             to exchange PNNI protocol packets with this node should
             direct packets or calls to this address.

             This attribute may only be written when pnniNodeAdminStatus
             has the value down."
        REFERENCE
            "ATM Forum PNNI 1.0 Section 5.2.2"
        ::= { pnniNodeEntry 8 }

pnniNodePeerGroupId OBJECT-TYPE
        SYNTAX        PnniPeerGroupId
        MAX-ACCESS    read-create
        STATUS        current
        DESCRIPTION
            "The Peer Group Identifier of the peer group that the given
             node is to become a member of.

             The default value of this attribute has the first octet
             equal to pnniNodeLevel, the next pnniNodeLevel bits equal
             to the pnniNodeLevel bits starting from the third octet of
             pnniNodeId, and the remainder padded with zeros.

             This object may only be written when pnniNodeAdminStatus
             has the value down."
        REFERENCE
            "ATM Forum PNNI 1.0 Section 5.3.2, Annex F"
        ::= { pnniNodeEntry 9 }

pnniNodeRestrictedTransit OBJECT-TYPE
        SYNTAX        TruthValue
        MAX-ACCESS    read-create
        STATUS        current
        DESCRIPTION
            "Specifies whether the node is restricted to not allowing
             support of SVCs transiting this node.  This attribute
             determines the setting of the restricted transit bit in the
             nodal information group originated by this node."
        REFERENCE
            "ATM Forum PNNI 1.0 Section 5.8.1.2.3"
        DEFVAL { false }
        ::= { pnniNodeEntry 10 }

pnniNodeComplexRep OBJECT-TYPE
        SYNTAX        TruthValue
        MAX-ACCESS    read-create
        STATUS        current
        DESCRIPTION
            "Specifies whether this node uses the complex node
             representation.  A value of `true' indicates that the
             complex node representation is used, whereas a value of
             `false' indicates that the simple node representation is
             used.  This attribute determines the setting of the nodal
             representation bit in the nodal information group
             originated by this node."
        REFERENCE
            "ATM Forum PNNI 1.0 Section 5.8.1.2.3"
        ::= { pnniNodeEntry 11 }

pnniNodeRestrictedBranching  OBJECT-TYPE
        SYNTAX        TruthValue
        MAX-ACCESS    read-only
        STATUS        current
        DESCRIPTION
            "Indicates whether the node is able to support additional
             point-to-multipoint branches.  A value of 'false' indicates
             that additional branches can be supported, and a value of
             'true' indicates that additional branches cannot be
             supported.  This attribute reflects the setting of the
             restricted branching bit in the nodal information group
             originated by this node."
        REFERENCE
            "ATM Forum PNNI 1.0 Section 5.8.1.2.3"
        ::= { pnniNodeEntry 12}

pnniNodeDatabaseOverload OBJECT-TYPE
        SYNTAX        TruthValue
        MAX-ACCESS    read-only
        STATUS        current
        DESCRIPTION
            "Specifies whether the node is currently operating in
             topology database overload state.  This attribute has the
             same value as the Non-transit for PGL Election bit in the
             nodal information group originated by this node."
        REFERENCE
            "ATM Forum PNNI 1.0 Section 5.8.1.2.3"
        ::= { pnniNodeEntry 13 }

pnniNodePtses OBJECT-TYPE
        SYNTAX        Gauge32
        MAX-ACCESS    read-only
        STATUS        current
        DESCRIPTION
            "Gauges the total number of PTSEs currently in this
             node's topology database(s)."
        ::= { pnniNodeEntry 14 }

pnniNodeRowStatus OBJECT-TYPE
        SYNTAX        RowStatus
        MAX-ACCESS    read-create
        STATUS        current
        DESCRIPTION
            "To create, delete, activate and de-activate a Node."
        ::= { pnniNodeEntry 15 }


-- PGL election table

pnniNodePglTable OBJECT-TYPE
        SYNTAX        SEQUENCE OF PnniNodePglEntry
        MAX-ACCESS    not-accessible
        STATUS        current
        DESCRIPTION
            "Peer group leader election information for a PNNI node in
             this switching system."
        REFERENCE
            "ATM Forum PNNI 1.0 Section 5.10.1"
        ::= { pnniMIBObjects 3 }

pnniNodePglEntry OBJECT-TYPE
        SYNTAX        PnniNodePglEntry
        MAX-ACCESS    not-accessible
        STATUS        current
        DESCRIPTION
            "An entry in the table, containing PGL election information
             of a PNNI logical node in this switching system."
        REFERENCE
            "ATM Forum PNNI 1.0 Section 5.10.1"
        AUGMENTS      { pnniNodeEntry }
        ::= { pnniNodePglTable 1 }

PnniNodePglEntry ::=
        SEQUENCE {
                pnniNodePglLeadershipPriority   INTEGER,
                pnniNodeCfgParentNodeIndex      PnniNodeIndex,
                pnniNodePglInitTime             Integer32,
                pnniNodePglOverrideDelay        Integer32,
                pnniNodePglReelectTime          Integer32,
                pnniNodePglState                INTEGER,
                pnniNodePreferredPgl            PnniNodeId,
                pnniNodePeerGroupLeader         PnniNodeId,
                pnniNodePglTimeStamp            TimeStamp,
                pnniNodeActiveParentNodeId      PnniNodeId
                }

pnniNodePglLeadershipPriority OBJECT-TYPE
        SYNTAX        INTEGER (0..205)
        MAX-ACCESS    read-create
        STATUS        current
        DESCRIPTION
            "The Leadership priority value this node should advertise in
             its nodal information group for the given peer group.  Only
             the value zero can be used with nodes that are not PGL/LGN
             capable.  If there is no configured parent node index or no
             corresponding entry in the pnniNodeTable, then the
             advertised leadership priority is zero regardless of this
             value."
        REFERENCE
            "ATM Forum PNNI 1.0 Section 5.10.1.2"
        DEFVAL { 0 }
        ::= { pnniNodePglEntry 1 }

pnniNodeCfgParentNodeIndex OBJECT-TYPE
        SYNTAX        PnniNodeIndex
        MAX-ACCESS    read-create
        STATUS        current
        DESCRIPTION
            "The local node index used to identify the node that will
             represent this peer group at the next higher level of
             hierarchy, if this node becomes peer group leader.  The
             value 0 indicates that there is no parent node."
        REFERENCE
            "ATM Forum PNNI 1.0 Annex F"
        DEFVAL { 0 }
        ::= { pnniNodePglEntry 2 }

pnniNodePglInitTime OBJECT-TYPE
        SYNTAX        Integer32
        UNITS         "seconds"
        MAX-ACCESS    read-create
        STATUS        current
        DESCRIPTION
            "The amount of time in seconds this node will delay
             advertising its choice of preferred PGL after having
             initialized operation and reached the full state with at
             least one neighbor in the peer group."
        REFERENCE
            "ATM Forum PNNI 1.0 Annex G PGLInitTime"
        DEFVAL  { 15 }
        ::= { pnniNodePglEntry 3 }

pnniNodePglOverrideDelay OBJECT-TYPE
        SYNTAX        Integer32
        UNITS         "seconds"
        MAX-ACCESS    read-create
        STATUS        current
        DESCRIPTION
            "The amount of time in seconds a node will wait for itself
             to be declared the preferred PGL by unanimous agreement
             among its peers.  In the absence of unanimous agreement
             this will be the amount of time that will pass before this
             node considers a two thirds majority as sufficient
             agreement to declare itself peer group leader, abandoning
             the attempt to get unanimous agreement."
        REFERENCE
            "ATM Forum PNNI 1.0 Annex G OverrideDelay"
        DEFVAL  { 30 }
        ::= { pnniNodePglEntry 4 }

pnniNodePglReelectTime OBJECT-TYPE
        SYNTAX        Integer32
        UNITS         "seconds"
        MAX-ACCESS    read-create
        STATUS        current
        DESCRIPTION
            "The amount of time in seconds after losing connectivity to
             the current peer group leader, that this node will wait
             before re-starting the process of electing a new peer group
             leader."
        REFERENCE
            "ATM Forum PNNI 1.0 Annex G ReElectionInterval"
        DEFVAL  { 15 }
        ::= { pnniNodePglEntry 5 }

pnniNodePglState OBJECT-TYPE
        SYNTAX        INTEGER {
                                starting(1),
                                awaiting(2),
                                awaitingFull(3),
                                initialDelay(4),
                                calculating(5),
                                awaitUnanimity(6),
                                operPgl(7),
                                operNotPgl(8),
                                hungElection(9),
                                awaitReElection(10)
                                }
        MAX-ACCESS    read-only
        STATUS        current
        DESCRIPTION
            "Indicates the state that this node is in with respect to
             the Peer Group Leader election that takes place in the
             node's peer group. The values are enumerated in the Peer
             Group Leader State Machine."
        REFERENCE
            "ATM Forum PNNI 1.0 Section 5.10.1.1.2"
        ::= { pnniNodePglEntry 6 }

pnniNodePreferredPgl OBJECT-TYPE
        SYNTAX        PnniNodeId
        MAX-ACCESS    read-only
        STATUS        current
        DESCRIPTION
            "The Node ID of
             the node which the local node believes should be or become
             the peer group leader.  This is also the value the local
             node is currently advertising in the `Preferred Peer Group
             Leader Node ID' field of its nodal information group within
             the given peer group.  If a Preferred PGL has not been
             chosen, this attribute's value is set to (all) zero(s)."
        REFERENCE
            "ATM Forum PNNI 1.0 Section 5.10.1.1.6"
        ::= { pnniNodePglEntry 7 }

pnniNodePeerGroupLeader OBJECT-TYPE
        SYNTAX        PnniNodeId
        MAX-ACCESS    read-only
        STATUS        current
        DESCRIPTION
            "The Node Identifier of the node which is currently
             operating as peer group leader of the peer group this node
             belongs to. If a PGL has not been elected, this attribute's
             value is set to (all) zero(s)."
        ::= { pnniNodePglEntry 8 }

pnniNodePglTimeStamp OBJECT-TYPE
        SYNTAX        TimeStamp
        MAX-ACCESS    read-only
        STATUS        current
        DESCRIPTION
            "The time at which the current Peer Group Leader established
             itself."
        ::= { pnniNodePglEntry 9 }

pnniNodeActiveParentNodeId OBJECT-TYPE
        SYNTAX        PnniNodeId
        MAX-ACCESS    read-only
        STATUS        current
        DESCRIPTION
            "The Node Identifier value being used by the Peer Group
             Leader to represent this peer group at the next higher
             level of the hierarchy. If this node is at the highest
             level of the hierarchy or if no PGL has yet been elected
             the PNNI Protocol Entity sets the value of this attribute
             to (all) zero(s)."
        ::= { pnniNodePglEntry 10 }


-- initial timer values table

pnniNodeTimerTable OBJECT-TYPE
        SYNTAX        SEQUENCE OF PnniNodeTimerEntry
        MAX-ACCESS    not-accessible
        STATUS        current
        DESCRIPTION
            "A table of initial PNNI timer values and significant
             change thresholds."
        ::= { pnniMIBObjects 4 }

pnniNodeTimerEntry OBJECT-TYPE
        SYNTAX        PnniNodeTimerEntry
        MAX-ACCESS    not-accessible
        STATUS        current
        DESCRIPTION
            "An entry in the table, containing initial PNNI timer values
             and significant change thresholds of a PNNI logical node in
             this switching system."
        AUGMENTS      { pnniNodeEntry }
        ::= { pnniNodeTimerTable 1 }

PnniNodeTimerEntry ::=
        SEQUENCE {
                pnniNodePtseHolddown            Integer32,
                pnniNodeHelloHolddown           Integer32,
                pnniNodeHelloInterval           Integer32,
                pnniNodeHelloInactivityFactor   Integer32,
                pnniNodeHlinkInact              Integer32,
                pnniNodePtseRefreshInterval     Integer32,
                pnniNodePtseLifetimeFactor      INTEGER,
                pnniNodeRxmtInterval            Integer32,
                pnniNodePeerDelayedAckInterval  Integer32,
                pnniNodeAvcrPm                  INTEGER,
                pnniNodeAvcrMt                  INTEGER,
                pnniNodeCdvPm                   INTEGER,
                pnniNodeCtdPm                   INTEGER
                }

pnniNodePtseHolddown OBJECT-TYPE
        SYNTAX        Integer32
        UNITS         "100 milliseconds"
        MAX-ACCESS    read-create
        STATUS        current
        DESCRIPTION
            "The initial value for the PTSE hold down timer that will be
             used by the given node to limit the rate at which it can
             re-originate PTSEs. It must be a positive non-zero number."
        REFERENCE
            "ATM Forum PNNI 1.0 Annex G MinPTSEInterval"
        DEFVAL { 10 }
        ::= { pnniNodeTimerEntry 1 }

pnniNodeHelloHolddown OBJECT-TYPE
        SYNTAX        Integer32
        UNITS         "100 milliseconds"
        MAX-ACCESS    read-create
        STATUS        current
        DESCRIPTION
            "The initial value for the Hello hold down timer that will
             be used by the given node to limit the rate at which it
             sends Hellos. It must be a positive non-zero number."
        REFERENCE
            "ATM Forum PNNI 1.0 Annex G MinHelloInterval"
        DEFVAL { 10 }
        ::= { pnniNodeTimerEntry 2 }

pnniNodeHelloInterval OBJECT-TYPE
        SYNTAX        Integer32
        UNITS         "seconds"
        MAX-ACCESS    read-create
        STATUS        current
        DESCRIPTION
            "The initial value for the Hello Timer.
             In the absence of triggered Hellos, this node will send one
             Hello packet on each of its ports on this interval."
        REFERENCE
            "ATM Forum PNNI 1.0 Annex G HelloInterval"
        DEFVAL { 15 }
        ::= { pnniNodeTimerEntry 3 }

pnniNodeHelloInactivityFactor OBJECT-TYPE
        SYNTAX        Integer32
        MAX-ACCESS    read-create
        STATUS        current
        DESCRIPTION
            "The value for the Hello Inactivity factor that this
             node will use to determine when a neighbor has gone down."
        REFERENCE
            "ATM Forum PNNI 1.0 Annex G InactivityFactor"
        DEFVAL { 5 }
        ::= { pnniNodeTimerEntry 4 }

pnniNodeHlinkInact OBJECT-TYPE
        SYNTAX        Integer32
        UNITS         "seconds"
        MAX-ACCESS    read-create
        STATUS        current
        DESCRIPTION
            "The amount of time a node will continue to
             advertise a horizontal (logical) link for which it has
             not received and processed a LGN Horizontal Link
             information group."
        REFERENCE
            "ATM Forum PNNI 1.0 Annex G HorizontalLinkInactivityTime"
        DEFVAL { 120 }
        ::= { pnniNodeTimerEntry 5 }

pnniNodePtseRefreshInterval OBJECT-TYPE
        SYNTAX        Integer32
        UNITS         "seconds"
        MAX-ACCESS    read-create
        STATUS        current
        DESCRIPTION
            "The initial value for the Refresh timer that this node will
             use to drive (re-)origination of PTSEs in the absence of
             triggered updates."
        REFERENCE
            "ATM Forum PNNI 1.0 Annex G PTSERefreshInterval"
        DEFVAL  { 1800 }
        ::= { pnniNodeTimerEntry 6 }

pnniNodePtseLifetimeFactor OBJECT-TYPE
        SYNTAX        INTEGER (101..1000)
        UNITS         "percent"
        MAX-ACCESS    read-create
        STATUS        current
        DESCRIPTION
            "The value for the lifetime multiplier, expressed as a
             percentage.  The result of multiplying the
             pnniNodePtseRefreshInterval attribute value by this
             attribute value is used as the initial lifetime that this
             node places into self-originated PTSEs."
        REFERENCE
            "ATM Forum PNNI 1.0 Annex G PTSELifetimeFactor"
        DEFVAL  { 200 }
        ::= { pnniNodeTimerEntry 7 }

pnniNodeRxmtInterval OBJECT-TYPE
        SYNTAX        Integer32
        UNITS         "seconds"
        MAX-ACCESS    read-create
        STATUS        current
        DESCRIPTION
            "The period between retransmissions of unacknowledged
             Database Summary packets, PTSE Request packets, and PTSPs."
        REFERENCE
            "ATM Forum PNNI 1.0 Annex G DSRxmtInterval,
             RequestRxmtInterval, PTSERetransmissionInterval"
        DEFVAL { 5 }
        ::= { pnniNodeTimerEntry 8 }

pnniNodePeerDelayedAckInterval OBJECT-TYPE
        SYNTAX        Integer32
        UNITS         "100 milliseconds"
        MAX-ACCESS    read-create
        STATUS        current
        DESCRIPTION
            "The minimum amount of time between transmissions of
             delayed PTSE acknowledgement packets."
        REFERENCE
            "ATM Forum PNNI 1.0 Annex G PeerDelayedAckInterval,
             Appendix G"
        DEFVAL { 10 }
        ::= { pnniNodeTimerEntry 9 }

pnniNodeAvcrPm OBJECT-TYPE
        SYNTAX        INTEGER (1..99)
        UNITS         "percent"
        MAX-ACCESS    read-create
        STATUS        current
        DESCRIPTION
            "The proportional multiplier used in the algorithms that
             determine significant change for AvCR parameters, expressed
             as a percentage."
        REFERENCE
            "ATM Forum PNNI 1.0 Section 5.8.5.2.5.4, Annex G AvCR_PM"
        DEFVAL  { 50 }
        ::= { pnniNodeTimerEntry 10 }

pnniNodeAvcrMt OBJECT-TYPE
        SYNTAX        INTEGER (1..99)
        UNITS         "percent"
        MAX-ACCESS    read-create
        STATUS        current
        DESCRIPTION
            "The minimum threshold used in the algorithms that determine
             significant change for AvCR parameters, expressed as a
             percentage."
        REFERENCE
            "ATM Forum PNNI 1.0 Section 5.8.5.2.5.4, Annex G AvCR_mT"
        DEFVAL  { 3 }
        ::= { pnniNodeTimerEntry 11 }

pnniNodeCdvPm OBJECT-TYPE
        SYNTAX        INTEGER (1..99)
        UNITS         "percent"
        MAX-ACCESS    read-create
        STATUS        current
        DESCRIPTION
            "The proportional multiplier used in the algorithms that
             determine significant change for CDV metrics, expressed as
             a percentage."
        REFERENCE
            "ATM Forum PNNI 1.0 Section 5.8.5.2.5.6, Annex G CDV_PM"
        DEFVAL  { 25 }
        ::= { pnniNodeTimerEntry 12 }

pnniNodeCtdPm OBJECT-TYPE
        SYNTAX        INTEGER (1..99)
        UNITS         "percent"
        MAX-ACCESS    read-create
        STATUS        current
        DESCRIPTION
            "The proportional multiplier used in the algorithms that
             determine significant change for CTD metrics, expressed as
             a percentage."
        REFERENCE
            "ATM Forum PNNI 1.0 Section 5.8.5.2.5.5, Annex G maxCTD_PM"
        DEFVAL  { 50 }
        ::= { pnniNodeTimerEntry 13 }


-- nodal SVCC-based RCC variables table

pnniNodeSvccTable OBJECT-TYPE
        SYNTAX        SEQUENCE OF PnniNodeSvccEntry
        MAX-ACCESS    not-accessible
        STATUS        current
        DESCRIPTION
            "A table of variables related to SVCC-based routing control
             channels."
        REFERENCE
            "ATM Forum PNNI 1.0 Section 5.5"
        ::= { pnniMIBObjects 5 }

pnniNodeSvccEntry OBJECT-TYPE
        SYNTAX        PnniNodeSvccEntry
        MAX-ACCESS    not-accessible
        STATUS        current
        DESCRIPTION
            "An entry in the table, containing SVCC-based RCC variables
             of a PNNI logical node in this switching system."
        REFERENCE
            "ATM Forum PNNI 1.0 Section 5.5"
        AUGMENTS      { pnniNodeEntry }
        ::= { pnniNodeSvccTable 1 }

PnniNodeSvccEntry ::=
        SEQUENCE {
                pnniNodeSvccInitTime                    Integer32,
                pnniNodeSvccRetryTime                   Integer32,
                pnniNodeSvccCallingIntegrityTime        Integer32,
                pnniNodeSvccCalledIntegrityTime         Integer32,
           pnniNodeSvccTrafficDescriptorIndex  AtmTrafficDescrParamIndex
                }

pnniNodeSvccInitTime OBJECT-TYPE
        SYNTAX        Integer32
        UNITS         "seconds"
        MAX-ACCESS    read-create
        STATUS        current
        DESCRIPTION
            "The amount of time this node will delay initiating
             establishment of an SVCC to a neighbor with a numerically
             lower ATM address, after determining that such an SVCC
             should be established."
        REFERENCE
            "ATM Forum PNNI 1.0 Annex G InitialLGNSVCTimeout"
        DEFVAL { 4 }
        ::= { pnniNodeSvccEntry 1 }

pnniNodeSvccRetryTime OBJECT-TYPE
        SYNTAX        Integer32
        UNITS         "seconds"
        MAX-ACCESS    read-create
        STATUS        current
        DESCRIPTION
            "The amount of time this node will delay after an apparently
             still necessary and viable SVCC-based RCC is unexpectedly
             torn down, before attempting to re-establish it."
        REFERENCE
            "ATM Forum PNNI 1.0 Annex G RetryLGNSVCTimeout"
        DEFVAL { 30 }
        ::= { pnniNodeSvccEntry 2 }

pnniNodeSvccCallingIntegrityTime OBJECT-TYPE
        SYNTAX        Integer32
        UNITS         "seconds"
        MAX-ACCESS    read-create
        STATUS        current
        DESCRIPTION
            "The amount of time this node will wait for an SVCC, which
             it has initiated establishment of as the calling party, to
             become fully established before giving up and tearing it
             down."
        REFERENCE
            "ATM Forum PNNI 1.0 Annex G SVCCallingIntegrityTime"
        DEFVAL { 35 }
        ::= { pnniNodeSvccEntry 3 }

pnniNodeSvccCalledIntegrityTime OBJECT-TYPE
        SYNTAX        Integer32
        UNITS         "seconds"
        MAX-ACCESS    read-create
        STATUS        current
        DESCRIPTION
            "The amount of time this node will wait for an SVCC, which
             it has decided to accept as the called party, to become
             fully established before giving up and tearing it down."
        REFERENCE
            "ATM Forum PNNI 1.0 Annex G SVCCalledIntegrityTime"
        DEFVAL { 50 }
        ::= { pnniNodeSvccEntry 4 }

pnniNodeSvccTrafficDescriptorIndex OBJECT-TYPE
        SYNTAX        AtmTrafficDescrParamIndex
        MAX-ACCESS    read-create
        STATUS        current
        DESCRIPTION
            "An index into the atmTrafficDescrParamTable defined in
             RFC 1695.  This traffic descriptor is used when
             establishing switched virtual channels for use as
             SVCC-based RCCs to/from PNNI logical group nodes."
        REFERENCE
            "ATM Forum PNNI 1.0 Section 5.5.2, Annex G
             RCCMaximumBurstSize, RCCPeakCellRate,
             RCCSustainableCellRate"
        ::= { pnniNodeSvccEntry 5 }


-- scope mapping table

pnniScopeMappingTable OBJECT-TYPE
        SYNTAX        SEQUENCE OF PnniScopeMappingEntry
        MAX-ACCESS    not-accessible
        STATUS        current
        DESCRIPTION
            "The pnniScopeTable contains the mappings of membership and
             connection scope from organizational scope values (used at
             UNI interfaces) to PNNI scope (i.e. in terms of PNNI
             routing level indicators)."
        REFERENCE
            "ATM Forum PNNI 1.0 Section 5.3.6"
        ::= { pnniMIBObjects 6 }

pnniScopeMappingEntry OBJECT-TYPE
        SYNTAX        PnniScopeMappingEntry
        MAX-ACCESS    not-accessible
        STATUS        current
        DESCRIPTION
            "An entry in the table, containing scope mapping information
             for a PNNI logical node in this switching system."
        REFERENCE
            "ATM Forum PNNI 1.0 Section 5.3.6"
        AUGMENTS      { pnniNodeEntry }
        ::= { pnniScopeMappingTable 1 }

PnniScopeMappingEntry ::=
        SEQUENCE {
                pnniScopeLocalNetwork           PnniLevel,
                pnniScopeLocalNetworkPlusOne    PnniLevel,
                pnniScopeLocalNetworkPlusTwo    PnniLevel,
                pnniScopeSiteMinusOne           PnniLevel,
                pnniScopeIntraSite              PnniLevel,
                pnniScopeSitePlusOne            PnniLevel,
                pnniScopeOrganizationMinusOne   PnniLevel,
                pnniScopeIntraOrganization      PnniLevel,
                pnniScopeOrganizationPlusOne    PnniLevel,
                pnniScopeCommunityMinusOne      PnniLevel,
                pnniScopeIntraCommunity         PnniLevel,
                pnniScopeCommunityPlusOne       PnniLevel,
                pnniScopeRegional               PnniLevel,
                pnniScopeInterRegional          PnniLevel,
                pnniScopeGlobal                 PnniLevel
                }

pnniScopeLocalNetwork OBJECT-TYPE
        SYNTAX        PnniLevel
        MAX-ACCESS    read-create
        STATUS        current
        DESCRIPTION
            "The highest level of PNNI hierarchy (i.e. smallest PNNI
             routing level) that lies within the organizational scope
             value localNetwork(1)."
        DEFVAL { 96 }
        ::= { pnniScopeMappingEntry 1 }

pnniScopeLocalNetworkPlusOne OBJECT-TYPE
        SYNTAX        PnniLevel
        MAX-ACCESS    read-create
        STATUS        current
        DESCRIPTION
            "The highest level of PNNI hierarchy (i.e. smallest PNNI
             routing level) that lies within the organizational scope
             value localNetworkPlusOne(2)."
        DEFVAL { 96 }
        ::= { pnniScopeMappingEntry 2 }

pnniScopeLocalNetworkPlusTwo OBJECT-TYPE
        SYNTAX        PnniLevel
        MAX-ACCESS    read-create
        STATUS        current
        DESCRIPTION
            "The highest level of PNNI hierarchy (i.e. smallest PNNI
             routing level) that lies within the organizational scope
             value localNetworkPlusTwo(3)."
        DEFVAL { 96 }
        ::= { pnniScopeMappingEntry 3 }

pnniScopeSiteMinusOne OBJECT-TYPE
        SYNTAX        PnniLevel
        MAX-ACCESS    read-create
        STATUS        current
        DESCRIPTION
            "The highest level of PNNI hierarchy  (i.e. smallest PNNI
             routing level) that lies within the organizational scope
             value siteMinusOne(4)."
        DEFVAL { 80 }
        ::= { pnniScopeMappingEntry 4 }

pnniScopeIntraSite OBJECT-TYPE
        SYNTAX        PnniLevel
        MAX-ACCESS    read-create
        STATUS        current
        DESCRIPTION
            "The highest level of PNNI hierarchy (i.e. smallest PNNI
             routing level) that lies within the organizational scope
             value intraSite(5)."
        DEFVAL { 80 }
        ::= { pnniScopeMappingEntry 5 }

pnniScopeSitePlusOne OBJECT-TYPE
        SYNTAX        PnniLevel
        MAX-ACCESS    read-create
        STATUS        current
        DESCRIPTION
            "The highest level of PNNI hierarchy (i.e. smallest PNNI
             routing level) that lies within the organizational scope
             value sitePlusOne(6)."
        DEFVAL { 72 }
        ::= { pnniScopeMappingEntry 6 }

pnniScopeOrganizationMinusOne OBJECT-TYPE
        SYNTAX        PnniLevel
        MAX-ACCESS    read-create
        STATUS        current
        DESCRIPTION
            "The highest level of PNNI hierarchy (i.e. smallest PNNI
             routing level) that lies within the organizational scope
             value organizationMinusOne(7)."
        DEFVAL { 72 }
        ::= { pnniScopeMappingEntry 7 }

pnniScopeIntraOrganization OBJECT-TYPE
        SYNTAX        PnniLevel
        MAX-ACCESS    read-create
        STATUS        current
        DESCRIPTION
            "The highest level of PNNI hierarchy (i.e. smallest PNNI
             routing level) that lies within the organizational scope
             value intraOrganization(8)."
        DEFVAL { 64 }
        ::= { pnniScopeMappingEntry 8 }

pnniScopeOrganizationPlusOne OBJECT-TYPE
        SYNTAX        PnniLevel
        MAX-ACCESS    read-create
        STATUS        current
        DESCRIPTION
            "The highest level of PNNI hierarchy (i.e. smallest PNNI
             routing level) that lies within the organizational scope
             value organizationPlusOne(9)."
        DEFVAL { 64 }
        ::= { pnniScopeMappingEntry 9 }

pnniScopeCommunityMinusOne OBJECT-TYPE
        SYNTAX        PnniLevel
        MAX-ACCESS    read-create
        STATUS        current
        DESCRIPTION
            "The highest level of PNNI hierarchy (i.e. smallest PNNI
             routing level) that lies within the organizational scope
             value communityMinusOne(10)."
        DEFVAL { 64 }
        ::= { pnniScopeMappingEntry 10 }

pnniScopeIntraCommunity OBJECT-TYPE
        SYNTAX        PnniLevel
        MAX-ACCESS    read-create
        STATUS        current
        DESCRIPTION
            "The highest level of PNNI hierarchy (i.e. smallest PNNI
             routing level) that lies within the organizational scope
             value intraCommunity(11)."
        DEFVAL { 48 }
        ::= { pnniScopeMappingEntry 11 }

pnniScopeCommunityPlusOne OBJECT-TYPE
        SYNTAX        PnniLevel
        MAX-ACCESS    read-create
        STATUS        current
        DESCRIPTION
            "The highest level of PNNI hierarchy (i.e. smallest PNNI
             routing level) that lies within the organizational scope
             value communityPlusOne(12)."
        DEFVAL { 48 }
        ::= { pnniScopeMappingEntry 12 }

pnniScopeRegional OBJECT-TYPE
        SYNTAX        PnniLevel
        MAX-ACCESS    read-create
        STATUS        current
        DESCRIPTION
            "The highest level of PNNI hierarchy (i.e. smallest PNNI
             routing level) that lies within the organizational scope
             value regional(13)."
        DEFVAL { 32 }
        ::= { pnniScopeMappingEntry 13 }

pnniScopeInterRegional OBJECT-TYPE
        SYNTAX        PnniLevel
        MAX-ACCESS    read-create
        STATUS        current
        DESCRIPTION
            "The highest level of PNNI hierarchy (i.e. smallest PNNI
             routing level) that lies within the organizational scope
             value interRegional(14)."
        DEFVAL { 32 }
        ::= { pnniScopeMappingEntry 14 }

pnniScopeGlobal OBJECT-TYPE
        SYNTAX        PnniLevel
        MAX-ACCESS    read-create
        STATUS        current
        DESCRIPTION
            "The highest level of PNNI hierarchy (i.e. smallest PNNI
             routing level) that lies within the organizational scope
             value global(15)."
        DEFVAL { 0 }
        ::= { pnniScopeMappingEntry 15 }


-- Deprecated summary advertising table

pnniSummaryTable OBJECT-TYPE
        SYNTAX        SEQUENCE OF PnniSummaryEntry
        MAX-ACCESS    not-accessible
        STATUS        deprecated
        DESCRIPTION
            "A list of the summary address prefixes that may be
             advertised by the specified logical PNNI entity."
        REFERENCE
            "ATM Forum PNNI 1.0 Section 5.9.2"
        ::= { pnniMIBObjects 7 }
pnniSummaryEntry OBJECT-TYPE
        SYNTAX        PnniSummaryEntry
        MAX-ACCESS    not-accessible
        STATUS        deprecated
        DESCRIPTION
            "An entry in the table, containing summary address prefix
             information in this switching system."
        REFERENCE
            "ATM Forum PNNI 1.0 Section 5.9.2"
        INDEX         { pnniNodeIndex,
                        pnniSummaryAddress,
                        pnniSummaryPrefixLength }
        ::= { pnniSummaryTable 1 }

PnniSummaryEntry ::=
        SEQUENCE {
                pnniSummaryAddress              AtmAddrPrefix,
                pnniSummaryPrefixLength         PnniPrefixLength,
                pnniSummaryType                 INTEGER,
                pnniSummarySuppress             TruthValue,
                pnniSummaryState                INTEGER,
                pnniSummaryRowStatus            RowStatus
        }

pnniSummaryAddress OBJECT-TYPE
        SYNTAX        AtmAddrPrefix
        MAX-ACCESS    not-accessible
        STATUS        deprecated
        DESCRIPTION
            "The ATM End System Address prefix for the summary."
        ::= { pnniSummaryEntry 1 }

pnniSummaryPrefixLength OBJECT-TYPE
        SYNTAX        PnniPrefixLength
        MAX-ACCESS    not-accessible
        STATUS        deprecated
        DESCRIPTION
            "The prefix length for the summary."
        ::= { pnniSummaryEntry 2 }

pnniSummaryType OBJECT-TYPE
        SYNTAX        INTEGER { internal(1), exterior(2) }
        MAX-ACCESS    read-create
        STATUS        deprecated
        DESCRIPTION
            "The type (e.g. internal or exterior) of summary being
                        described."
        DEFVAL { internal }
        ::= { pnniSummaryEntry 3 }

pnniSummarySuppress OBJECT-TYPE
        SYNTAX        TruthValue
        MAX-ACCESS    read-create
        STATUS        deprecated
        DESCRIPTION
            "Determines what is done with addresses that are being
             summarized by the instance. The default value (e.g. false)
             will indicate that the summary should propagate into the
             peer group. Network Management will be able to set the
             value of this attribute to `suppress' (e.g. true), which
             suppresses the summary and any reachable addresses it
             summarizes from being advertised into the peer group."
        DEFVAL { false }
        ::= { pnniSummaryEntry 4 }

pnniSummaryState OBJECT-TYPE
        SYNTAX        INTEGER {
                                advertising(1),
                                suppressing(2),
                                inactive(3)
                                }
        MAX-ACCESS    read-only
        STATUS        deprecated
        DESCRIPTION
            "Indicates whether the summary is currently being advertised
             by the node within the local switching system into its peer
             group."
        ::= { pnniSummaryEntry 5 }

pnniSummaryRowStatus OBJECT-TYPE
        SYNTAX        RowStatus
        MAX-ACCESS    read-create
        STATUS        deprecated
        DESCRIPTION
            "To create, delete, activate and de-activate a summary."
        ::= { pnniSummaryEntry 6 }

-- Summary address table

pnniSummaryAddressTable OBJECT-TYPE
        SYNTAX        SEQUENCE OF PnniSummaryAddressEntry
        MAX-ACCESS    not-accessible
        STATUS        current
        DESCRIPTION
            "A list of the summary address prefixes that may be 
             advertised by the specified logical PNNI entity."
        REFERENCE
            "ATM Forum PNNI 1.0 Section 5.9.2"
        ::= { pnniMIBObjects 20 }

pnniSummaryAddressEntry OBJECT-TYPE
        SYNTAX        PnniSummaryAddressEntry
        MAX-ACCESS    not-accessible
        STATUS        current
        DESCRIPTION
            "An entry in the table, containing summary address prefix
             information in this switching system."
        REFERENCE
            "ATM Forum PNNI 1.0 Section 5.9.2"
        INDEX         { pnniNodeIndex,
                                pnniSummaryAddressType,  
                                pnniSummaryAddressAddress,
                                pnniSummaryAddressPrefixLength }
        ::= { pnniSummaryAddressTable 1 }

PnniSummaryAddressEntry ::=
        SEQUENCE {
	  pnniSummaryAddressType                      INTEGER,
                pnniSummaryAddressAddress             AtmAddrPrefix,
                pnniSummaryAddressPrefixLength        PnniPrefixLength,
                pnniSummaryAddressSuppress            TruthValue,
                pnniSummaryAddressState               INTEGER,
                pnniSummaryAddressRowStatus           RowStatus
        }

pnniSummaryAddressType OBJECT-TYPE
        SYNTAX         INTEGER { internal(1), exterior(2) }
        MAX-ACCESS     not-accessible 
        STATUS         current
        DESCRIPTION
            "The type (e.g. internal or exterior) of summary being
                        described."
        ::= { pnniSummaryAddressEntry 1 }

pnniSummaryAddressAddress OBJECT-TYPE
        SYNTAX        AtmAddrPrefix
        MAX-ACCESS    not-accessible
        STATUS        current
        DESCRIPTION
            "The ATM End System Address prefix for the summary."
        ::= { pnniSummaryAddressEntry 2 }

pnniSummaryAddressPrefixLength OBJECT-TYPE
        SYNTAX        PnniPrefixLength
        MAX-ACCESS    not-accessible
        STATUS        current
        DESCRIPTION
            "The prefix length for the summary."
        ::= { pnniSummaryAddressEntry 3 }

pnniSummaryAddressSuppress OBJECT-TYPE
        SYNTAX        TruthValue
        MAX-ACCESS    read-create
        STATUS        current
        DESCRIPTION
            "Determines what is done with addresses that are being
             summarized by the instance. The default value (e.g. false)
             will indicate that the summary should propagate into the
             peer group. Network Management will be able to set the
             value of this attribute to `suppress' (e.g. true), which
             suppresses the summary and any reachable addresses it
             summarizes from being advertised into the peer group."
        DEFVAL { false }
        ::= { pnniSummaryAddressEntry 4 }

pnniSummaryAddressState OBJECT-TYPE
        SYNTAX        INTEGER {
                                advertising(1),
                                suppressing(2),
                                inactive(3)
                                }
        MAX-ACCESS    read-only
        STATUS        current
        DESCRIPTION
            "Indicates whether the summary is currently being advertised
             by the node within the local switching system into its peer
             group."
        ::= { pnniSummaryAddressEntry 5 }

pnniSummaryAddressRowStatus OBJECT-TYPE
        SYNTAX        RowStatus
        MAX-ACCESS    read-create
        STATUS        current
        DESCRIPTION
            "To create, delete, activate and de-activate a summary."
        ::= { pnniSummaryAddressEntry 6 }

-- Interface table

pnniIfTable OBJECT-TYPE
        SYNTAX        SEQUENCE OF PnniIfEntry
        MAX-ACCESS    not-accessible
        STATUS        current
        DESCRIPTION
            "The pnniIfTable contains the attributes necessary to
             configure a physical interface on a switching system which
             is capable of being used for PNNI routing.  Interfaces may
             represent physical connection points (i.e. copper/fiber
             connection points) or VPCs which have been configured for
             PNNI's use.  Each interface is attached to a specific
             lowest-level node within the switching system.

             An ifIndex is used as the instance ID to uniquely identify
             the interface on the local switching system. This index has
             the same value as the ifIndex object defined in RFC 1573
             for the same interface, since this table correlates with
             the ifTable in RFC 1573.

             One row in this table is created by the managed system for
             each row in the ifTable that has an ifType of atm(37) or
             atmLogical(80)."
        ::= { pnniMIBObjects 8 }

pnniIfEntry OBJECT-TYPE
        SYNTAX        PnniIfEntry
        MAX-ACCESS    not-accessible
        STATUS        current
        DESCRIPTION
            "An entry in the table, containing PNNI specific interface
             information in this switching system."
        INDEX         { ifIndex }
        ::= { pnniIfTable 1 }

PnniIfEntry ::=
        SEQUENCE {
                pnniIfNodeIndex         PnniNodeIndex,
                pnniIfPortId            PnniPortId,
                pnniIfAggrToken         PnniAggrToken,
                pnniIfVPCapability      TruthValue,
                pnniIfAdmWeightCbr      Unsigned32,
                pnniIfAdmWeightRtVbr    Unsigned32,
                pnniIfAdmWeightNrtVbr   Unsigned32,
                pnniIfAdmWeightAbr      Unsigned32,
                pnniIfAdmWeightUbr      Unsigned32,
                pnniIfRccServiceCategory    ServiceCategory,
                pnniIfRccTrafficDescrIndex  AtmTrafficDescrParamIndex
                }

pnniIfNodeIndex OBJECT-TYPE
        SYNTAX        PnniNodeIndex (1..65535)
        MAX-ACCESS    read-write
        STATUS        current
        DESCRIPTION
            "Identifies the node within the switching system that the
             interface is directly attached to.  The value zero is not 
             a valid value."
        DEFVAL { 1 }
        ::= { pnniIfEntry 1 }

pnniIfPortId OBJECT-TYPE
        SYNTAX        PnniPortId
        MAX-ACCESS    read-only
        STATUS        current
        DESCRIPTION
            "The Port Identifier of the port as selected by the PNNI
             protocol entity for the given interface.  This value has
             meaning only within the context of the node to which the
             port is attached.  The distinguished value zero indicates
             that no PNNI Port Identifier has been assigned for this
             interface (for example, this value may be used when the
             interface is not running PNNI)."
        REFERENCE
            "ATM Forum PNNI 1.0 Section 5.3.4"
        ::= { pnniIfEntry 2 }

pnniIfAggrToken OBJECT-TYPE
        SYNTAX        PnniAggrToken
        MAX-ACCESS    read-write
        STATUS        current
        DESCRIPTION
            "The configured aggregation token for this interface.  The
             aggregation token controls what other links the link
             associated with this interface will be aggregated together
             with."
        REFERENCE
            "ATM Forum PNNI 1.0 Sections 5.3.5, 5.10.3.1"
        DEFVAL { 0 }
        ::= { pnniIfEntry 3 }

pnniIfVPCapability OBJECT-TYPE
        SYNTAX        TruthValue
        MAX-ACCESS    read-write
        STATUS        current
        DESCRIPTION
            "Indicates whether the interface is capable of having VPCs
             established within it or not.

             This object may only have the value `true' for physical ATM
             interfaces, i.e. those with an ifType of atm(37)."
        REFERENCE
            "ATM Forum PNNI 1.0 Section 5.14.9.1 Table 5-34"
        ::= { pnniIfEntry 4 }

pnniIfAdmWeightCbr OBJECT-TYPE
        SYNTAX        Unsigned32 (1..16777215)
        MAX-ACCESS    read-write
        STATUS        current
        DESCRIPTION
            "The administrative weight of this interface for the
             constant bit rate service category."
        REFERENCE
            "ATM Forum PNNI 1.0 Section 5.8.1.1.3.4"
        DEFVAL { 5040 }
        ::= { pnniIfEntry 5 }

pnniIfAdmWeightRtVbr OBJECT-TYPE
        SYNTAX        Unsigned32 (1..16777215)
        MAX-ACCESS    read-write
        STATUS        current
        DESCRIPTION
            "The administrative weight of this interface for the
             real-time variable bit rate service category."
        REFERENCE
            "ATM Forum PNNI 1.0 Section 5.8.1.1.3.4"
        DEFVAL { 5040 }
        ::= { pnniIfEntry 6 }

pnniIfAdmWeightNrtVbr OBJECT-TYPE
        SYNTAX        Unsigned32 (1..16777215)
        MAX-ACCESS    read-write
        STATUS        current
        DESCRIPTION
            "The administrative weight of this interface for the
             non-real-time variable bit rate service category."
        REFERENCE
            "ATM Forum PNNI 1.0 Section 5.8.1.1.3.4"
        DEFVAL { 5040 }
        ::= { pnniIfEntry 7 }

pnniIfAdmWeightAbr OBJECT-TYPE
        SYNTAX        Unsigned32 (1..16777215)
        MAX-ACCESS    read-write
        STATUS        current
        DESCRIPTION
            "The administrative weight of this interface for the
             available bit rate service category."
        REFERENCE
            "ATM Forum PNNI 1.0 Section 5.8.1.1.3.4"
        DEFVAL { 5040 }
        ::= { pnniIfEntry 8 }

pnniIfAdmWeightUbr OBJECT-TYPE
        SYNTAX        Unsigned32 (1..16777215)
        MAX-ACCESS    read-write
        STATUS        current
        DESCRIPTION
            "The administrative weight of this interface for the
             unspecified bit rate service category."
        REFERENCE
            "ATM Forum PNNI 1.0 Section 5.8.1.1.3.4"
        DEFVAL { 5040 }
        ::= { pnniIfEntry 9 }

pnniIfRccServiceCategory OBJECT-TYPE
        SYNTAX        ServiceCategory
        MAX-ACCESS    read-write
        STATUS        current
        DESCRIPTION
            "The service category used for the PNNI routing control
             channel (VCI=18) on this interface."
        REFERENCE
            "ATM Forum PNNI 1.0 Sections 5.5.2, 5.5.3"
        ::= { pnniIfEntry 10 }

pnniIfRccTrafficDescrIndex OBJECT-TYPE
        SYNTAX        AtmTrafficDescrParamIndex
        MAX-ACCESS    read-write
        STATUS        current
        DESCRIPTION
            "The traffic descriptor index referring to the entry in the
             atmTrafficDescrParamTable defined in RFC 1695 that
             specifies the traffic allocation for the PNNI routing
             control channel (VCI=18) on this interface."
        REFERENCE
            "ATM Forum PNNI 1.0 Sections 5.5.2, 5.5.3, Annex G
             RCCMaximumBurstSize, RCCPeakCellRate,
             RCCSustainableCellRate"
        ::= { pnniIfEntry 11 }


-- link table

pnniLinkTable OBJECT-TYPE
        SYNTAX        SEQUENCE OF PnniLinkEntry
        MAX-ACCESS    not-accessible
        STATUS        current
        DESCRIPTION
            "This table contains the attributes necessary to describe
             the operation of logical links attached to the local
             switching system and the relationship with the neighbor
             nodes on the other end of the links.  Links are attached to
             a specific node within the switching system.  A
             concatenation of the Node Index of the node within the
             local switching system and the port ID are used as the
             instance ID to uniquely identify the link.  Links may
             represent horizontal links between lowest level neighboring
             peers, outside links, uplinks, or horizontal links to/from
             LGNs.

             The entire pnniLink object is read-only, reflecting the
             fact that this information is discovered dynamically by the
             PNNI protocol rather than configured."
        REFERENCE
            "ATM Forum PNNI 1.0 Section 5.6"
        ::= { pnniMIBObjects 9 }

pnniLinkEntry OBJECT-TYPE
        SYNTAX        PnniLinkEntry
        MAX-ACCESS    not-accessible
        STATUS        current
        DESCRIPTION
            "An entry in the table, containing information about a link
             attached to a PNNI logical node in this switching system."
        REFERENCE
            "ATM Forum PNNI 1.0 Section 5.6"
        INDEX         { pnniNodeIndex,
                        pnniLinkPortId }
        ::= { pnniLinkTable 1 }

PnniLinkEntry ::=
        SEQUENCE {
                pnniLinkPortId          PnniPortId,
                pnniLinkType            INTEGER,
                pnniLinkVersion         PnniVersion,
                pnniLinkHelloState      PnniHelloState,
                pnniLinkRemoteNodeId    PnniNodeId,
                pnniLinkRemotePortId    PnniPortId,
                pnniLinkDerivedAggrToken        PnniAggrToken,
                pnniLinkUpnodeId        PnniNodeId,
                pnniLinkUpnodeAtmAddress        PnniAtmAddr,
                pnniLinkCommonPeerGroupId       PnniPeerGroupId,
                pnniLinkIfIndex         InterfaceIndex,
                pnniLinkSvccRccIndex    PnniSvccRccIndex,
                pnniLinkRcvHellos       Counter32,
                pnniLinkXmtHellos       Counter32
                }

pnniLinkPortId OBJECT-TYPE
        SYNTAX        PnniPortId
        MAX-ACCESS    not-accessible
        STATUS        current
        DESCRIPTION
            "The Port Identifier of the link as selected by the local
             node.  This value has meaning only within the context of
             the node to which the port is attached."
        ::= { pnniLinkEntry 1 }

pnniLinkType OBJECT-TYPE
        SYNTAX        INTEGER {
                                unknown(1),
                                lowestLevelHorizontalLink(2),
                                horizontalLinkToFromLgn(3),
                                lowestLevelOutsideLink(4),
                                uplink(5),
                                outsideLinkAndUplink(6)
                                }
        MAX-ACCESS    read-only
        STATUS        current
        DESCRIPTION
            "Indicates the type of link being described."
        ::= { pnniLinkEntry 2 }

pnniLinkVersion OBJECT-TYPE
        SYNTAX        PnniVersion
        MAX-ACCESS    read-only
        STATUS        current
        DESCRIPTION
            "For horizontal and outside links between lowest-level nodes
             and for links of unknown type, this attribute indicates the
             version of PNNI routing protocol used to exchange
             information over this link.  If communication with the
             neighbor node has not yet been established, then the
             Version is set to `unknown'.  For uplinks (where the
             port ID is not also used for the underlying outside link)
             or links to/from LGNs, the Version is set to `unknown'."
        ::= { pnniLinkEntry 3 }

pnniLinkHelloState OBJECT-TYPE
        SYNTAX        PnniHelloState
        MAX-ACCESS    read-only
        STATUS        current
        DESCRIPTION
            "For horizontal and outside links between lowest-level nodes
             and for links of unknown type, this attribute indicates the
             state of the Hello protocol exchange over this link.  For
             links to/from LGNs, this attribute indicates the state of
             the corresponding LGN Horizontal Link Hello State Machine.
             For uplinks (where the port ID is not also used for the
             underlying outside link), this attribute is set to
             notApplicable."
        REFERENCE
            "ATM Forum PNNI 1.0 Section 5.6.2.1.2"
        ::= { pnniLinkEntry 4 }

pnniLinkRemoteNodeId OBJECT-TYPE
        SYNTAX        PnniNodeId
        MAX-ACCESS    read-only
        STATUS        current
        DESCRIPTION
            "Indicates the node identifier of the remote (neighboring)
             node on the other end of the link.  If the pnniLinkType is
             `outside link and uplink', this is the node identifier of
             the lowest-level neighbor node on the other end of the
             outside link.  If the remote node ID is unknown or if the
             pnniLinkType is `uplink', this attribute is set to all
             zeros."
        ::= { pnniLinkEntry 5 }

pnniLinkRemotePortId OBJECT-TYPE
        SYNTAX        PnniPortId
        MAX-ACCESS    read-only
        STATUS        current
        DESCRIPTION
            "Indicates the port identifier of the port at the remote end
             of the link as assigned by the remote node.  If the
             pnniLinkType is `outside link and uplink', this is the port
             identifier assigned by the lowest-level neighbor node to
             identify the outside link.  If the remote port ID is
             unknown or if the pnniLinkType is `uplink', this attribute
             is set to zero."
        ::= { pnniLinkEntry 6 }

pnniLinkDerivedAggrToken OBJECT-TYPE
        SYNTAX        PnniAggrToken
        MAX-ACCESS    read-only
        STATUS        current
        DESCRIPTION
            "Indicates the derived aggregation token value used on this
             link.  For horizontal links between lowest-level nodes and
             when the link type is not yet known, this attribute takes
             the value of zero."
        REFERENCE
            "ATM Forum PNNI 1.0 Section 5.10.3.1"
        ::= { pnniLinkEntry 7 }

pnniLinkUpnodeId OBJECT-TYPE
        SYNTAX        PnniNodeId
        MAX-ACCESS    read-only
        STATUS        current
        DESCRIPTION
            "For outside links and uplinks, this attribute contains the
             Node Identifier of the upnode (the neighbor node's identity
             at the level of the common peer group).  When the upnode
             has not yet been identified, this attribute is set to zero.
             For horizontal links or when the link type is not yet
             known, this attribute is set to zero."
        ::= { pnniLinkEntry 8 }

pnniLinkUpnodeAtmAddress OBJECT-TYPE
        SYNTAX        PnniAtmAddr
        MAX-ACCESS    read-only
        STATUS        current
        DESCRIPTION
            "For outside links and uplinks, this attribute contains the
             ATM End System Address used to establish connections to the
             upnode.  When the upnode has not yet been identified, this
             attribute is set to zero.  For horizontal links or when the
             link type is not yet known, this attribute is set to zero."
        ::= { pnniLinkEntry 9 }

pnniLinkCommonPeerGroupId OBJECT-TYPE
        SYNTAX        PnniPeerGroupId
        MAX-ACCESS    read-only
        STATUS        current
        DESCRIPTION
            "For outside links and uplinks, this attribute contains the
             peer group identifier of the lowest level common Peer Group
             in the ancestry of the neighboring node and the node within
             the local switching system.  The value of this attribute
             takes on a value determined by the Hello exchange of
             hierarchical information that occurs between the two
             lowest-level border nodes.  When the common peer group has
             not yet been identified, this attribute is set to zero.
             For horizontal links or when the link type is not yet
             known, this attribute is set to all zeros."
        ::= { pnniLinkEntry 10 }

pnniLinkIfIndex OBJECT-TYPE
        SYNTAX        InterfaceIndex
        MAX-ACCESS    read-only
        STATUS        current
        DESCRIPTION
            "For horizontal and outside links between lowest-level nodes
             and for links of unknown type, this attribute identifies
             the interface to which the logical link corresponds.

             For all other cases, the value of this object is zero."
        ::= { pnniLinkEntry 11 }

pnniLinkSvccRccIndex OBJECT-TYPE
        SYNTAX        PnniSvccRccIndex
        MAX-ACCESS    read-only
        STATUS        current
        DESCRIPTION
            "For horizontal links to/from LGNs, this attribute
             identifies the SVCC-based RCC used to exchange information
             with the neighboring peer logical group node.  If the
             pnniLinkType is not `horizontal link to/from LGN', this
             attribute shall take the value of zero."
        ::= { pnniLinkEntry 12 }

pnniLinkRcvHellos OBJECT-TYPE
        SYNTAX        Counter32
        MAX-ACCESS    read-only
        STATUS        current
        DESCRIPTION
            "For horizontal and outside links between lowest-level nodes
             and for links of unknown type, this attribute contains a
             count of the number of Hello Packets received over this
             link.  If the pnniLinkType is `horizontal link to/from LGN'
             or `uplink', this attribute is set to zero."
        ::= { pnniLinkEntry 13 }

pnniLinkXmtHellos OBJECT-TYPE
        SYNTAX        Counter32
        MAX-ACCESS    read-only
        STATUS        current
        DESCRIPTION
            "For horizontal and outside links between lowest-level nodes
             and for links of unknown type, this attribute contains a
             count of the number of Hello Packets transmitted over this
             link.  If the pnniLinkType is `horizontal link to/from LGN'
             or `uplink', this attribute is set to zero."
        ::= { pnniLinkEntry 14 }


-- neighboring peer table

pnniNbrPeerTable OBJECT-TYPE
        SYNTAX        SEQUENCE OF PnniNbrPeerEntry
        MAX-ACCESS    not-accessible
        STATUS        current
        DESCRIPTION
            "The pnniNbrPeer Object contains all the attributes
             necessary to describe the relationship a node in this
             switching system has with a neighboring node within the
             same peer group.  A concatenation of the Node Identifier of
             the node within the local switching system and the
             neighboring peer's Node Identifier is used to form the
             instance ID for this object.

             The entire pnniNbrPeer object is read-only, reflecting the
             fact that neighboring peers are discovered dynamically by
             the PNNI protocol rather than configured."
        REFERENCE
            "ATM Forum PNNI 1.0 Sections 5.7, 5.8"
        ::= { pnniMIBObjects 10 }

pnniNbrPeerEntry OBJECT-TYPE
        SYNTAX        PnniNbrPeerEntry
        MAX-ACCESS    not-accessible
        STATUS        current
        DESCRIPTION
            "An entry in the table, containing information about this
             node's relationship with a neighboring peer node."
        REFERENCE
            "ATM Forum PNNI 1.0 Sections 5.7, 5.8"
        INDEX         { pnniNodeIndex,
                        pnniNbrPeerRemoteNodeId }
        ::= { pnniNbrPeerTable 1 }

PnniNbrPeerEntry ::=
        SEQUENCE {
                pnniNbrPeerRemoteNodeId         PnniNodeId,
                pnniNbrPeerState                INTEGER,
                pnniNbrPeerSvccRccIndex         PnniSvccRccIndex,
                pnniNbrPeerPortCount            Gauge32,
                pnniNbrPeerRcvDbSums            Counter32,
                pnniNbrPeerXmtDbSums            Counter32,
                pnniNbrPeerRcvPtsps             Counter32,
                pnniNbrPeerXmtPtsps             Counter32,
                pnniNbrPeerRcvPtseReqs          Counter32,
                pnniNbrPeerXmtPtseReqs          Counter32,
                pnniNbrPeerRcvPtseAcks          Counter32,
                pnniNbrPeerXmtPtseAcks          Counter32
                }

pnniNbrPeerRemoteNodeId OBJECT-TYPE
        SYNTAX        PnniNodeId
        MAX-ACCESS    not-accessible
        STATUS        current
        DESCRIPTION
            "The Node Identifier of the neighboring peer node."
        ::= { pnniNbrPeerEntry 1 }

pnniNbrPeerState OBJECT-TYPE
        SYNTAX        INTEGER {
                                npdown(1),
                                negotiating(2),
                                exchanging(3),
                                loading(4),
                                full(5)
                                }
        MAX-ACCESS    read-only
        STATUS        current
        DESCRIPTION
            "Indicates the state of this node's Neighboring Peer State
             Machine associated with pnniNbrPeerRemoteNodeId."
        REFERENCE
            "ATM Forum PNNI 1.0 Section 5.7.2"
        ::= { pnniNbrPeerEntry 2 }

pnniNbrPeerSvccRccIndex OBJECT-TYPE
        SYNTAX        PnniSvccRccIndex
        MAX-ACCESS    read-only
        STATUS        current
        DESCRIPTION
            "Identifies the SVCC-based RCC being used to communicate
             with the neighboring peer if one exists.  If both the local
             node and the neighboring peer node are lowest-level nodes,
             this attribute is set to zero."
        ::= { pnniNbrPeerEntry 3 }

pnniNbrPeerPortCount OBJECT-TYPE
        SYNTAX        Gauge32
        MAX-ACCESS    read-only
        STATUS        current
        DESCRIPTION
            "A count of the total number of ports that connect to the
             neighboring peer.  If the neighboring peer only
             communicates via an SVCC-based RCC, the value of this
             attribute is set to zero.  Otherwise it is set to the total
             number of ports to the neighboring peer in the Hello state
             2-WayInside."
        ::= { pnniNbrPeerEntry 4 }

pnniNbrPeerRcvDbSums OBJECT-TYPE
        SYNTAX        Counter32
        MAX-ACCESS    read-only
        STATUS        current
        DESCRIPTION
            "A count of the number of Database Summary Packets received
             from the neighboring peer."
        ::= { pnniNbrPeerEntry 5 }

pnniNbrPeerXmtDbSums OBJECT-TYPE
        SYNTAX        Counter32
        MAX-ACCESS    read-only
        STATUS        current
        DESCRIPTION
            "A count of the number of Database Summary Packets
             transmitted to the neighboring peer."
        ::= { pnniNbrPeerEntry 6 }

pnniNbrPeerRcvPtsps OBJECT-TYPE
        SYNTAX        Counter32
        MAX-ACCESS    read-only
        STATUS        current
        DESCRIPTION
            "A count of the number of PTSPs received from the
             neighboring peer."
        ::= { pnniNbrPeerEntry 7 }

pnniNbrPeerXmtPtsps OBJECT-TYPE
        SYNTAX        Counter32
        MAX-ACCESS    read-only
        STATUS        current
        DESCRIPTION
            "A count of the number of PTSPs (re)transmitted to the
             neighboring peer."
        ::= { pnniNbrPeerEntry 8 }

pnniNbrPeerRcvPtseReqs OBJECT-TYPE
        SYNTAX        Counter32
        MAX-ACCESS    read-only
        STATUS        current
        DESCRIPTION
            "A count of the number of PTSE Request packets received from
             the neighboring peer."
        ::= { pnniNbrPeerEntry 9 }

pnniNbrPeerXmtPtseReqs OBJECT-TYPE
        SYNTAX        Counter32
        MAX-ACCESS    read-only
        STATUS        current
        DESCRIPTION
            "A count of the number of PTSE Request packets transmitted
             to the neighboring peer."
        ::= { pnniNbrPeerEntry 10 }

pnniNbrPeerRcvPtseAcks OBJECT-TYPE
        SYNTAX        Counter32
        MAX-ACCESS    read-only
        STATUS        current
        DESCRIPTION
            "A count of the number of PTSE Ack packets received from the
             neighboring peer."
        ::= { pnniNbrPeerEntry 11 }

pnniNbrPeerXmtPtseAcks OBJECT-TYPE
        SYNTAX        Counter32
        MAX-ACCESS    read-only
        STATUS        current
        DESCRIPTION
            "A count of the number of PTSE Ack packets transmitted to
             the neighboring peer."
        ::= { pnniNbrPeerEntry 12 }


-- neighboring peer port table

pnniNbrPeerPortTable OBJECT-TYPE
        SYNTAX        SEQUENCE OF PnniNbrPeerPortEntry
        MAX-ACCESS    not-accessible
        STATUS        current
        DESCRIPTION
            "A table of all ports in Hello state 2-Way Inside to a given
             neighboring peer node.  A concatenation of the Node Index
             of the node within the local switching system, the
             neighbor's Node Identifier and the Interface Index of the
             port being described forms the instance ID for this object.
             This object is only used for lowest-level nodes."
        REFERENCE
            "ATM Forum PNNI 1.0 Section 5.7.1 Port ID List"
        ::= { pnniMIBObjects 11 }

pnniNbrPeerPortEntry OBJECT-TYPE
        SYNTAX        PnniNbrPeerPortEntry
        MAX-ACCESS    not-accessible
        STATUS        current
        DESCRIPTION
            "An entry in the table, containing information about a port
             in the Hello state 2-Way Inside from a PNNI logical node in
             this switching system to a neighboring peer node."
        INDEX         { pnniNodeIndex,
                        pnniNbrPeerRemoteNodeId,
                        pnniNbrPeerPortId
                         }
        ::= { pnniNbrPeerPortTable 1 }

PnniNbrPeerPortEntry ::=
        SEQUENCE {
                pnniNbrPeerPortId               PnniPortId,
                pnniNbrPeerPortFloodStatus      TruthValue
               }

pnniNbrPeerPortId OBJECT-TYPE
        SYNTAX        PnniPortId
        MAX-ACCESS    not-accessible
        STATUS        current
        DESCRIPTION
            "The port ID of a port to the neighboring peer that is in
             the Hello state 2-Way Inside."
        ::= { pnniNbrPeerPortEntry 1 }

pnniNbrPeerPortFloodStatus OBJECT-TYPE
        SYNTAX        TruthValue
        MAX-ACCESS    read-only
        STATUS        current
        DESCRIPTION
            "Indicates whether the port is being used for transmission
             of flooding and database synchronization information to the
             neighboring peer."
        ::= { pnniNbrPeerPortEntry 2 }


-- pnni SVCC-based routing control channel table

pnniSvccRccTable OBJECT-TYPE
        SYNTAX        SEQUENCE OF PnniSvccRccEntry
        MAX-ACCESS    not-accessible
        STATUS        current
        DESCRIPTION
            "A table containing the attributes necessary to analyze the
             operation of the PNNI protocol on SVCC-based Routing
             Control Channels. This entire object is read-only,
             reflecting the fact that SVCC-based RCCs are established
             dynamically during operation of the PNNI protocol rather
             than configured."
        REFERENCE
            "ATM Forum PNNI 1.0 Sections 5.5.6, 5.6.3.1"
        ::= { pnniMIBObjects 12 }

pnniSvccRccEntry OBJECT-TYPE
        SYNTAX        PnniSvccRccEntry
        MAX-ACCESS    not-accessible
        STATUS        current
        DESCRIPTION
            "An entry in the table, containing information about an
             SVCC-based RCC from a PNNI logical node in this switching
             system."
        REFERENCE
            "ATM Forum PNNI 1.0 Sections 5.5.6, 5.6.3.1"
        INDEX         { pnniNodeIndex,
                        pnniSvccRccIndex }
        ::= { pnniSvccRccTable 1 }

PnniSvccRccEntry ::=
        SEQUENCE {
                pnniSvccRccIndex            PnniSvccRccIndex,
                pnniSvccRccVersion          PnniVersion,
                pnniSvccRccHelloState       PnniHelloState,
                pnniSvccRccRemoteNodeId     PnniNodeId,
                pnniSvccRccRemoteAtmAddress     PnniAtmAddr,
                pnniSvccRccRcvHellos        Counter32,
                pnniSvccRccXmtHellos        Counter32,
                pnniSvccRccIfIndex          InterfaceIndex,
                pnniSvccRccVpi              INTEGER,
                pnniSvccRccVci              INTEGER
                }

pnniSvccRccIndex OBJECT-TYPE
        SYNTAX        PnniSvccRccIndex
        MAX-ACCESS    not-accessible
        STATUS        current
        DESCRIPTION
            "An index into the node's tables of SVCC-based RCCs."
        ::= { pnniSvccRccEntry 1 }

pnniSvccRccVersion OBJECT-TYPE
        SYNTAX        PnniVersion
        MAX-ACCESS    read-only
        STATUS        current
        DESCRIPTION
            "The version of the PNNI routing protocol used to exchange
             information with the neighbor node."
        ::= { pnniSvccRccEntry 2 }

pnniSvccRccHelloState OBJECT-TYPE
        SYNTAX        PnniHelloState
        MAX-ACCESS    read-only
        STATUS        current
        DESCRIPTION
            "The state of the Hello protocol exchange over the
             SVCC-based RCC.

             Note: the Down state indicates that the SVCC
             establishment is in progress."
        ::= { pnniSvccRccEntry 3 }

pnniSvccRccRemoteNodeId OBJECT-TYPE
        SYNTAX        PnniNodeId
        MAX-ACCESS    read-only
        STATUS        current
        DESCRIPTION
            "The remote node at which the SVCC-based RCC terminates."
        ::= { pnniSvccRccEntry 4 }

pnniSvccRccRemoteAtmAddress OBJECT-TYPE
        SYNTAX        PnniAtmAddr
        MAX-ACCESS    read-only
        STATUS        current
        DESCRIPTION
            "The ATM End System Address to which SVCC establishment is
             attempted."
        ::= { pnniSvccRccEntry 5 }

pnniSvccRccRcvHellos OBJECT-TYPE
        SYNTAX        Counter32
        MAX-ACCESS    read-only
        STATUS        current
        DESCRIPTION
            "A count of the number of Hello Packets received over this
             SVCC-based RCC."
        ::= { pnniSvccRccEntry 6 }

pnniSvccRccXmtHellos OBJECT-TYPE
        SYNTAX        Counter32
        MAX-ACCESS    read-only
        STATUS        current
        DESCRIPTION
            "A count of the number of Hello Packets transmitted over
             this SVCC-based RCC."
        ::= { pnniSvccRccEntry 7 }

pnniSvccRccIfIndex OBJECT-TYPE
        SYNTAX        InterfaceIndex
        MAX-ACCESS    read-only
        STATUS        current
        DESCRIPTION
            "The interface from which the SVCC-based RCC leaves the
             switching system.  If the SVCC-based RCC has not yet been
             established, then this attribute takes the value of zero."
        ::= { pnniSvccRccEntry 8 }

pnniSvccRccVpi OBJECT-TYPE
        SYNTAX        INTEGER (0..4095)
        MAX-ACCESS    read-only
        STATUS        current
        DESCRIPTION
            "The VPI used at the interface from which the SVCC-based RCC
             leaves the switching system.  If the SVCC-based RCC has not
             yet been established, then this attribute takes the value
             of zero "
        ::= { pnniSvccRccEntry 9 }

pnniSvccRccVci OBJECT-TYPE
        SYNTAX        INTEGER (0..65535)
        MAX-ACCESS    read-only
        STATUS        current
        DESCRIPTION
            "The VCI used at the interface from which the SVCC-based RCC
             leaves the switching system.  If the SVCC-based RCC has not
             yet been established, then this attribute takes the value
             of zero "
        ::= { pnniSvccRccEntry 10 }


-- PTSE table

pnniPtseTable OBJECT-TYPE
        SYNTAX        SEQUENCE OF PnniPtseEntry
        MAX-ACCESS    not-accessible
        STATUS        current
        DESCRIPTION
            "The pnniPtse object contains the attributes that describe
             the most recent instances of PTSEs in a node's topology
             database.  A concatenation of the Node Identifier of the
             local node that received the PTSE, the originating Node's
             Node Identifier and the PTSE Identifier are used to form
             the instance ID for an instance of this object."
        REFERENCE
            "ATM Forum PNNI 1.0 Section 5.8.2"
        ::= { pnniMIBObjects 13 }

pnniPtseEntry OBJECT-TYPE
        SYNTAX        PnniPtseEntry
        MAX-ACCESS    not-accessible
        STATUS        current
        DESCRIPTION
            "An entry in the table, containing information about a PTSE
             in the topology database of a PNNI logical node in this
             switching system."
        REFERENCE
            "ATM Forum PNNI 1.0 Section 5.8.2"
        INDEX         { pnniNodeIndex,
                        pnniPtseOriginatingNodeId,
                        pnniPtseId }
        ::= { pnniPtseTable 1 }

PnniPtseEntry ::=
        SEQUENCE {
                pnniPtseOriginatingNodeId       PnniNodeId,
                pnniPtseId                      Unsigned32,
                pnniPtseType                    INTEGER,
                pnniPtseSequenceNum             Unsigned32,
                pnniPtseChecksum                Unsigned32,
                pnniPtseLifeTime                Unsigned32,
                pnniPtseInfo                    OCTET STRING
                }

pnniPtseOriginatingNodeId OBJECT-TYPE
        SYNTAX        PnniNodeId
        MAX-ACCESS    not-accessible
        STATUS        current
        DESCRIPTION
            "The Node Identifier of the node that originated the PTSE."
        ::= { pnniPtseEntry 1 }

pnniPtseId OBJECT-TYPE
        SYNTAX        Unsigned32
        MAX-ACCESS    not-accessible
        STATUS        current
        DESCRIPTION
            "The value of the PTSE Identifier assigned to the PTSE by
             its originator."
        ::= { pnniPtseEntry 2 }

pnniPtseType OBJECT-TYPE
        SYNTAX        INTEGER  {
                                other(1),
                                nodalStateParameters(96),
                                nodalInformation(97),
                                internalReachableAddresses(224),
                                exteriorReachableAddresses(256),
                                horizontalLinks(288),
                                uplinks(289)
                                }
        MAX-ACCESS    read-only
        STATUS        current
        DESCRIPTION
            "The type of information contained in the PTSE."
        ::= { pnniPtseEntry 3 }

pnniPtseSequenceNum OBJECT-TYPE
        SYNTAX        Unsigned32
        MAX-ACCESS    read-only
        STATUS        current
        DESCRIPTION
            "The sequence number of the instance of the PTSE as it
             appears in the local topology database."
        ::= { pnniPtseEntry 4 }

pnniPtseChecksum OBJECT-TYPE
        SYNTAX        Unsigned32 (0..65535)
        MAX-ACCESS    read-only
        STATUS        current
        DESCRIPTION
            "The value of the PTSE checksum as it appears in the local
             topology database."
        ::= { pnniPtseEntry 5 }

pnniPtseLifeTime OBJECT-TYPE
        SYNTAX        Unsigned32 (0..65535)
        UNITS         "seconds"
        MAX-ACCESS    read-only
        STATUS        current
        DESCRIPTION
            "The value of the remaining lifetime for the given PTSE as
             it appears in the local topology database."
        ::= { pnniPtseEntry 6 }

pnniPtseInfo OBJECT-TYPE
        SYNTAX        OCTET STRING (SIZE(0..65535))
        MAX-ACCESS    read-only
        STATUS        current
        DESCRIPTION
            "An unformatted hexadecimal dump of the PTSE contents in
             full.

             Note: If the size of the PTSE contents is larger than the
             maximum size of SNMP packets then this is truncated."
        ::= { pnniPtseEntry 7 }


-- pnni map table

pnniMapTable OBJECT-TYPE
        SYNTAX        SEQUENCE OF PnniMapEntry
        MAX-ACCESS    not-accessible
        STATUS        current
        DESCRIPTION
            "A table containing attributes necessary to find and analyze
             the operation of all links and nodes within the PNNI
             hierarchy, as seen from the perspective of a local node.
             An instance of a pnniMap Object describes a link in terms
             of a node at one end of the link.  Normally there will be
             two instances of the pnniMap object in the MIB for each
             horizontal link. The two instances provide information for
             Network management to map port identifiers from the nodes
             at both ends to the link between them.  A concatenation of
             the Local Node Index, Originating Node Identifier and
             Originating Port Identifier are used to form the instance
             ID for this object.

             This entire object is read-only, reflecting the fact that
             the map is discovered dynamically during operation of the
             PNNI protocol rather than configured."
        ::= { pnniMIBObjects 14 }

pnniMapEntry OBJECT-TYPE
        SYNTAX        PnniMapEntry
        MAX-ACCESS    not-accessible
        STATUS        current
        DESCRIPTION
            "An entry in the table, containing connectivity information
             about a node or link in the PNNI routing domain, as seen
             from the perspective of a PNNI logical node in this
             switching system."
        INDEX         { pnniNodeIndex,
                        pnniMapOriginatingNodeId,
                        pnniMapOriginatingPortId,
                        pnniMapIndex }
        ::= { pnniMapTable 1 }

PnniMapEntry ::=
        SEQUENCE {
                pnniMapOriginatingNodeId        PnniNodeId,
                pnniMapOriginatingPortId        PnniPortId,
                pnniMapIndex                    INTEGER,
                pnniMapType                     INTEGER,
                pnniMapPeerGroupId              PnniPeerGroupId,
                pnniMapAggrToken                PnniAggrToken,
                pnniMapRemoteNodeId             PnniNodeId,
                pnniMapRemotePortId             PnniPortId,
                pnniMapVPCapability             TruthValue,
                pnniMapPtseId                   Unsigned32,
                pnniMapMetricsTag               PnniMetricsTag
                }

pnniMapOriginatingNodeId OBJECT-TYPE
        SYNTAX        PnniNodeId
        MAX-ACCESS    not-accessible
        STATUS        current
        DESCRIPTION
            "The node identifier of the node whose connectivity within
             itself or to other nodes is being described."
        ::= { pnniMapEntry 1 }

pnniMapOriginatingPortId OBJECT-TYPE
        SYNTAX        PnniPortId
        MAX-ACCESS    not-accessible
        STATUS        current
        DESCRIPTION
            "The port identifier of the port as assigned by the
             originating node, to which the port is attached."
        ::= { pnniMapEntry 2 }

pnniMapIndex OBJECT-TYPE
        SYNTAX        INTEGER (0..65535)
        MAX-ACCESS    not-accessible
        STATUS        current
        DESCRIPTION
            "An index into the set of link and nodal connectivity
             associated with the originating node and port.  This index
             is needed since there may be multiple entries for nodal
             connectivity from a specific node and port pair, in
             addition to any entry for a horizontal link or uplink."
        ::= { pnniMapEntry 3 }

pnniMapType OBJECT-TYPE
        SYNTAX        INTEGER {
                                horizontalLink(1),
                                uplink(2),
                                node(3)
                                }
        MAX-ACCESS    read-only
        STATUS        current
        DESCRIPTION
            "The type of PNNI entity being described by this entry in
             the table."
        ::= { pnniMapEntry 4 }

pnniMapPeerGroupId OBJECT-TYPE
        SYNTAX        PnniPeerGroupId
        MAX-ACCESS    read-only
        STATUS        current
        DESCRIPTION
            "Identifies the peer group of the originating node."
        ::= { pnniMapEntry 5 }

pnniMapAggrToken OBJECT-TYPE
        SYNTAX        PnniAggrToken
        MAX-ACCESS    read-only
        STATUS        current
        DESCRIPTION
            "For horizontal links to/from LGNs and for uplinks, this
             attribute contains the derived aggregation token value for
             this link.  For nodes and for horizontal links between
             lowest-level nodes, this attribute is set to zero."
        ::= { pnniMapEntry 6 }

pnniMapRemoteNodeId OBJECT-TYPE
        SYNTAX        PnniNodeId
        MAX-ACCESS    read-only
        STATUS        current
        DESCRIPTION
            "For horizontal links and uplinks, this attribute contains
             the node identifier of the node at the other end of the
             link from the originating node.  If unknown, the PNNI
             protocol entity sets this attribute's value to (all)
             zero(s).  For nodes, this attribute's value is set to (all)
             zero(s)."
        ::= { pnniMapEntry 7 }

pnniMapRemotePortId OBJECT-TYPE
        SYNTAX        PnniPortId
        MAX-ACCESS    read-only
        STATUS        current
        DESCRIPTION
            "For horizontal links and uplinks, this attribute contains
             the port identifier of the port at the remote end of the
             link as assigned by the remote node.  If unknown, the PNNI
             protocol entity sets this attribute's value to zero.

             For nodes, this attribute contains the port identifier of
             the port at the other end of the spoke or bypass from the
             originating port.  When the originating port ID is zero, a
             value of zero indicates the default radius.  When the
             originating port ID is non-zero, a value of zero indicates
             the nodal nucleus."
        ::= { pnniMapEntry 8 }

pnniMapVPCapability OBJECT-TYPE
        SYNTAX        TruthValue
        MAX-ACCESS    read-only
        STATUS        current
        DESCRIPTION
            "Indicates whether VPCs
             can be established across the PNNI entity being described
             by this entry in the pnniMapTable."
        ::= { pnniMapEntry 9 }

pnniMapPtseId OBJECT-TYPE
        SYNTAX        Unsigned32
        MAX-ACCESS    read-only
        STATUS        current
        DESCRIPTION
            "The value of the PTSE Identifier for the PTSE being
             originated by the originating node which contains the
             information group(s) describing the PNNI entity."
        ::= { pnniMapEntry 10 }

pnniMapMetricsTag OBJECT-TYPE
        SYNTAX        PnniMetricsTag
        MAX-ACCESS    read-only
        STATUS        current
        DESCRIPTION
            "An arbitrary integer that is used to associate a set of
             traffic parameters that are always advertised together.
             Within this set, the parameters are distinguished by the
             service categories and direction to which a set of
             parameters apply.  This value is used as an index into
             the pnniMetricsTable.  The distinguished value zero
             indicates that no metrics are associated with the link or
             nodal connectivity."
        ::= { pnniMapEntry 11 }


-- nodal map table

pnniMapNodeTable OBJECT-TYPE
        SYNTAX        SEQUENCE OF PnniMapNodeEntry
        MAX-ACCESS    not-accessible
        STATUS        current
        DESCRIPTION
            "A list of nodes as seen from the perspective of a local
             node.  The pnniMapNodeTable contains all information
             learned by the local node from nodal information PTSEs.
             This entire object is read-only, reflecting the fact that
             the map is discovered dynamically during operation of the
             PNNI protocol rather than configured."
        ::= { pnniMIBObjects 15 }

pnniMapNodeEntry OBJECT-TYPE
        SYNTAX        PnniMapNodeEntry
        MAX-ACCESS    not-accessible
        STATUS        current
        DESCRIPTION
            "An entry in the table, containing information about a node
             in the PNNI routing domain, as seen from the perspective of
             a logical node in this switching system."
        INDEX         { pnniNodeIndex,
                        pnniMapNodeId }
        ::= { pnniMapNodeTable 1 }

PnniMapNodeEntry ::=
        SEQUENCE {
                pnniMapNodeId                   PnniNodeId,
                pnniMapNodePeerGroupId          PnniPeerGroupId,
                pnniMapNodeAtmAddress           PnniAtmAddr,
                pnniMapNodeRestrictedTransit    TruthValue,
                pnniMapNodeComplexRep           TruthValue,
                pnniMapNodeRestrictedBranching  TruthValue,
                pnniMapNodeDatabaseOverload     TruthValue,
                pnniMapNodeIAmLeader            TruthValue,
                pnniMapNodeLeadershipPriority   INTEGER,
                pnniMapNodePreferredPgl         PnniNodeId,
                pnniMapNodeParentNodeId         PnniNodeId,
                pnniMapNodeParentAtmAddress     PnniAtmAddr,
                pnniMapNodeParentPeerGroupId    PnniPeerGroupId,
                pnniMapNodeParentPglNodeId      PnniNodeId
                }

pnniMapNodeId OBJECT-TYPE
        SYNTAX        PnniNodeId
        MAX-ACCESS    not-accessible
        STATUS        current
        DESCRIPTION
            "Identifies the node whose nodal information is being
             described."
        ::= { pnniMapNodeEntry 1 }

pnniMapNodePeerGroupId OBJECT-TYPE
        SYNTAX        PnniPeerGroupId
        MAX-ACCESS    read-only
        STATUS        current
        DESCRIPTION
            "Identifies the peer group of the originating node."
        ::= { pnniMapNodeEntry 2 }

pnniMapNodeAtmAddress OBJECT-TYPE
        SYNTAX        PnniAtmAddr
        MAX-ACCESS    read-only
        STATUS        current
        DESCRIPTION
            "The ATM End System Address of the originating node."
        ::= { pnniMapNodeEntry 3 }

pnniMapNodeRestrictedTransit OBJECT-TYPE
        SYNTAX        TruthValue
        MAX-ACCESS    read-only
        STATUS        current
        DESCRIPTION
            "Indicates whether the originating node is restricted to
             only allow support of SVCs originating or terminating at
             this node.  A value of `true' indicates that the transit
             capabilities are restricted, i.e., transit connections are
             not allowed, whereas a value of `false' indicates that
             transit connections are allowed.  This attribute reflects
             the setting of the restricted transit bit received in the
             nodal information PTSE of the originating node."
        ::= { pnniMapNodeEntry 4 }

pnniMapNodeComplexRep OBJECT-TYPE
        SYNTAX        TruthValue
        MAX-ACCESS    read-only
        STATUS        current
        DESCRIPTION
            "Indicates whether the originating node uses the complex
             node representation.  If the value is `true', the spokes
             and bypasses that make up the complex node representation
             should be found in the pnniMapTable.  This attribute
             reflects the setting of the nodal representation bit
             received in the nodal information PTSE of the originating
             node."
        ::= { pnniMapNodeEntry 5 }

pnniMapNodeRestrictedBranching  OBJECT-TYPE
        SYNTAX      TruthValue
        MAX-ACCESS  read-only
        STATUS      current
        DESCRIPTION
            "Indicates whether the originating node is able to support
             additional branches.  If the value is 'false', then it can
             support additional branches.  This attribute reflects the
             setting of the restricted branching bit received in the
             nodal information PTSE of the originating node."
        ::= { pnniMapNodeEntry 6 }

pnniMapNodeDatabaseOverload OBJECT-TYPE
        SYNTAX        TruthValue
        MAX-ACCESS    read-only
        STATUS        current
        DESCRIPTION
            "Indicates whether the originating node is currently
             operating in topology database overload state.  This
             attribute has the same value as the Non-transit for PGL
             Election bit in the nodal information group originated by
             this node."
        ::= { pnniMapNodeEntry 7 }

pnniMapNodeIAmLeader OBJECT-TYPE
        SYNTAX        TruthValue
        MAX-ACCESS    read-only
        STATUS        current
        DESCRIPTION
            "Indicates whether the originating node claims to be peer
             group leader of its peer group.  This attribute reflects
             the setting of the 'I am Leader' bit received in the nodal
             information PTSE of the originating node."
        ::= { pnniMapNodeEntry 8 }

pnniMapNodeLeadershipPriority OBJECT-TYPE
        SYNTAX        INTEGER (0..255)
        MAX-ACCESS    read-only
        STATUS        current
        DESCRIPTION
            "The Leadership priority value advertised by the originating
             node."
        ::= { pnniMapNodeEntry 9 }

pnniMapNodePreferredPgl OBJECT-TYPE
        SYNTAX        PnniNodeId
        MAX-ACCESS    read-only
        STATUS        current
        DESCRIPTION
            "Identifies the node which the originating node believes
             should be or is peer group leader of its peer group.  If
             the originating node has not chosen a Preferred PGL, this
             attribute's value is set to (all) zero(s)."
        ::= { pnniMapNodeEntry 10 }

pnniMapNodeParentNodeId OBJECT-TYPE
        SYNTAX        PnniNodeId
        MAX-ACCESS    read-only
        STATUS        current
        DESCRIPTION
            "When the originating node is a peer group leader, indicates
             the node ID of the parent LGN.  If the originating node is
             not peer group leader of its peer group, this attribute's
             value is set to (all) zero(s)."
        ::= { pnniMapNodeEntry 11 }

pnniMapNodeParentAtmAddress OBJECT-TYPE
        SYNTAX        PnniAtmAddr
        MAX-ACCESS    read-only
        STATUS        current
        DESCRIPTION
            "When the originating node is a peer group leader, indicates
             the ATM address of the parent LGN.  If the originating node
             is not peer group leader of its peer group, this
             attribute's value is set to (all) zero(s)."
        ::= { pnniMapNodeEntry 12 }

pnniMapNodeParentPeerGroupId OBJECT-TYPE
        SYNTAX        PnniPeerGroupId
        MAX-ACCESS    read-only
        STATUS        current
        DESCRIPTION
            "When the originating node is a peer group leader, indicates
             the node's parent peer group ID.  If the originating node
             is not peer group leader of its peer group, this
             attribute's value is set to (all) zero(s)."
        ::= { pnniMapNodeEntry 13 }

pnniMapNodeParentPglNodeId OBJECT-TYPE
        SYNTAX        PnniNodeId
        MAX-ACCESS    read-only
        STATUS        current
        DESCRIPTION
            "When the originating node is a peer group leader,
             identifies the node elected as peer group leader of the
             parent peer group.  If the originating node is not peer
             group leader of its peer group, this attribute's value is
             set to (all) zero(s)."
        ::= { pnniMapNodeEntry 14 }


-- address map table

pnniMapAddrTable OBJECT-TYPE
        SYNTAX        SEQUENCE OF PnniMapAddrEntry
        MAX-ACCESS    not-accessible
        STATUS        current
        DESCRIPTION
            "The pnniMapAddr MIB Object contains a list of all reachable
             addresses from each node visible to the local node.  The
             Local Node Index, Advertising Node ID, Advertised Port ID,
             Reachable Address, and Address prefix length are combined
             to form an instance ID for this object.  The entire object
             is read-only, reflecting the fact that reachable addresses
             are discovered during dynamic operation of the PNNI
             protocol rather than configured."
        ::= { pnniMIBObjects 16 }

pnniMapAddrEntry OBJECT-TYPE
        SYNTAX        PnniMapAddrEntry
        MAX-ACCESS    not-accessible
        STATUS        current
        DESCRIPTION
            "An entry in the table, containing information about an
             address prefix reachable from a node in the PNNI routing
             domain, as seen from the perspective of a PNNI logical node
             in this switching system."
        INDEX         { pnniNodeIndex,
                        pnniMapAddrAdvertisingNodeId,
                        pnniMapAddrAdvertisedPortId,
                        pnniMapAddrIndex }
        ::= { pnniMapAddrTable 1 }

PnniMapAddrEntry ::=
        SEQUENCE {
                pnniMapAddrAdvertisingNodeId    PnniNodeId,
                pnniMapAddrAdvertisedPortId     PnniPortId,
                pnniMapAddrIndex                INTEGER,
                pnniMapAddrAddress              AtmAddrPrefix,
                pnniMapAddrPrefixLength         PnniPrefixLength
                }

pnniMapAddrAdvertisingNodeId OBJECT-TYPE
        SYNTAX        PnniNodeId
        MAX-ACCESS    not-accessible
        STATUS        current
        DESCRIPTION
            "The node ID of a node advertising reachability to the
             address prefix."
        ::= { pnniMapAddrEntry 1 }

pnniMapAddrAdvertisedPortId OBJECT-TYPE
        SYNTAX        PnniPortId
        MAX-ACCESS    not-accessible
        STATUS        current
        DESCRIPTION
            "The port identifier used from the advertising node to reach
             the given address prefix."
        ::= { pnniMapAddrEntry 2 }

pnniMapAddrIndex OBJECT-TYPE
        SYNTAX        INTEGER (1..2147483647)
        MAX-ACCESS    not-accessible
        STATUS        current
        DESCRIPTION
            "An arbitrary index that is used to enumerate all of the
             addresses advertised by the specified node."
        ::= { pnniMapAddrEntry 3 }

pnniMapAddrAddress OBJECT-TYPE
        SYNTAX        AtmAddrPrefix
        MAX-ACCESS    read-only
        STATUS        current
        DESCRIPTION
            "The value of the ATM End System Address prefix."
        ::= { pnniMapAddrEntry 4 }

pnniMapAddrPrefixLength OBJECT-TYPE
        SYNTAX        PnniPrefixLength
        MAX-ACCESS    read-only
        STATUS        current
        DESCRIPTION
            "The Prefix length to be applied to the ATM End System
             Address prefix."
        ::= { pnniMapAddrEntry 5 }


-- TNS map table

pnniMapTnsTable OBJECT-TYPE
        SYNTAX        SEQUENCE OF PnniMapTnsEntry
        MAX-ACCESS    not-accessible
        STATUS        current
        DESCRIPTION
            "A list of all reachable transit networks from each node
             visible to the local node.  The Local Node Index,
             Advertising Node ID, Advertised Port ID, Transit Network
             Type, Transit Network Plan, and Transit Network ID are
             combined to form an instance ID for this object. The entire
             object is read-only, reflecting the fact that reachable
             transit networks are discovered during dynamic operation of
             the PNNI protocol rather than configured."
        ::= { pnniMIBObjects 17 }

pnniMapTnsEntry OBJECT-TYPE
        SYNTAX        PnniMapTnsEntry
        MAX-ACCESS    not-accessible
        STATUS        current
        DESCRIPTION
            "An entry in the table, containing information about a
             transit network reachable from a node in the PNNI routing
             domain, as seen from the perspective of a PNNI logical node
             in this switching system."
        INDEX         { pnniNodeIndex,
                        pnniMapTnsAdvertisingNodeId,
                        pnniMapTnsAdvertisedPortId,
                        pnniMapTnsType,
                        pnniMapTnsPlan,
                        pnniMapTnsId }
        ::= { pnniMapTnsTable 1 }

PnniMapTnsEntry ::=
        SEQUENCE {
                pnniMapTnsAdvertisingNodeId     PnniNodeId,
                pnniMapTnsAdvertisedPortId      PnniPortId,
                pnniMapTnsType                  TnsType,
                pnniMapTnsPlan                  TnsPlan,
                pnniMapTnsId                    DisplayString
                }

pnniMapTnsAdvertisingNodeId OBJECT-TYPE
        SYNTAX        PnniNodeId
        MAX-ACCESS    not-accessible
        STATUS        current
        DESCRIPTION
            "The node ID of a node advertising reachability to the
             transit network."
        ::= { pnniMapTnsEntry 1 }

pnniMapTnsAdvertisedPortId OBJECT-TYPE
        SYNTAX        PnniPortId
        MAX-ACCESS    not-accessible
        STATUS        current
        DESCRIPTION
            "The port identifier used from the advertising node to reach
             the given transit network."
        ::= { pnniMapTnsEntry 2 }

pnniMapTnsType OBJECT-TYPE
        SYNTAX        TnsType
        MAX-ACCESS    not-accessible
        STATUS        current
        DESCRIPTION
            "The type of network identification used for this transit
             network."
        ::= { pnniMapTnsEntry 3 }

pnniMapTnsPlan OBJECT-TYPE
        SYNTAX        TnsPlan
        MAX-ACCESS    not-accessible
        STATUS        current
        DESCRIPTION
            "The network identification plan according to which network
             identification has been assigned."
        ::= { pnniMapTnsEntry 4 }

pnniMapTnsId OBJECT-TYPE
        SYNTAX        DisplayString
        MAX-ACCESS    read-only
        STATUS        current
        DESCRIPTION
            "The value of the transit network identifier."
        ::= { pnniMapTnsEntry 5 }



-- pnni metrics table

pnniMetricsTable OBJECT-TYPE
        SYNTAX        SEQUENCE OF PnniMetricsEntry
        MAX-ACCESS    not-accessible
        STATUS        current
        DESCRIPTION
            "This entity's table of PNNI parameters either associated
             with a PNNI entity or for the connectivity between a PNNI
             node and a reachable address or transit network."
        REFERENCE
            "ATM Forum PNNI 1.0 Section 5.8.1.1.3"
        ::= { pnniMIBObjects 18 }

pnniMetricsEntry OBJECT-TYPE
        SYNTAX        PnniMetricsEntry
        MAX-ACCESS    not-accessible
        STATUS        current
        DESCRIPTION
            "A set of parameters that applies to the connectivity from a
             certain node and port to another node or port or to one or
             more reachable address prefixes and/or transit networks,
             for one (or more) particular service category(s).  Note
             that there can be multiple sets of parameters with the same
             tag, in which case all sets apply to the specified
             connectivity."
        REFERENCE
            "ATM Forum PNNI 1.0 Section 5.8.1.1.3"
        INDEX         { pnniNodeIndex,
                        pnniMetricsTag,
                        pnniMetricsDirection,
                        pnniMetricsIndex }
        ::= { pnniMetricsTable 1 }

PnniMetricsEntry ::=
        SEQUENCE {
                pnniMetricsTag          PnniMetricsTag,
                pnniMetricsDirection    INTEGER,
                pnniMetricsIndex        Integer32,
                pnniMetricsClasses      INTEGER,
                pnniMetricsGcacClp      ClpType,
                pnniMetricsAdminWeight  Unsigned32,
                pnniMetrics1            Unsigned32,
                pnniMetrics2            Unsigned32,
                pnniMetrics3            Unsigned32,
                pnniMetrics4            Unsigned32,
                pnniMetrics5            Unsigned32,
                pnniMetrics6            Unsigned32,
                pnniMetrics7            Unsigned32,
                pnniMetrics8            Unsigned32,
                pnniMetricsRowStatus    RowStatus
                }


pnniMetricsTag OBJECT-TYPE
        SYNTAX        PnniMetricsTag (1..2147483647)
        MAX-ACCESS    not-accessible
        STATUS        current
        DESCRIPTION
            "An arbitrary integer that is used to associate a set of
             traffic parameters that are always advertised together.
             Within this set, the parameters are distinguished by the
             service categories and direction to which a set of
             parameters apply."
        ::= { pnniMetricsEntry 1 }


pnniMetricsDirection OBJECT-TYPE
        SYNTAX        INTEGER { incoming(1), outgoing(2) }
        MAX-ACCESS    not-accessible
        STATUS        current
        DESCRIPTION
            "The direction, with respect to the advertising node, in
             which the parameters in this entry apply."
        ::= { pnniMetricsEntry 2 }


pnniMetricsIndex OBJECT-TYPE
        SYNTAX        Integer32 (1..2147483647)
        MAX-ACCESS    not-accessible
        STATUS        current
        DESCRIPTION
            "An index into the set of parameters associated with the
             given tag and direction."
        ::= { pnniMetricsEntry 3 }


pnniMetricsClasses OBJECT-TYPE
        SYNTAX        INTEGER(0..31)
        MAX-ACCESS    read-create
        STATUS        current
        DESCRIPTION
            "The service categories to which this set of parameters
             applies.  This is an integer used as a bit mask with each
             bit that is set representing a single service category for
             which the resources indicated are available.  Bit 5
             represents CBR, bit 4 represents real-time VBR, bit 3
             represents non-real-time VBR, bit 2 represents ABR, and
             bit 1 (LSB) represents UBR."
        REFERENCE
            "ATM Forum Traffic Management 4.0 Section 2,
             ATM Forum PNNI 1.0 Section 5.8.1.1.3.1"
        ::= { pnniMetricsEntry 4 }

pnniMetricsGcacClp OBJECT-TYPE
        SYNTAX        ClpType
        MAX-ACCESS    read-create
        STATUS        current
        DESCRIPTION
            "Indicates whether the advertised GCAC parameters apply for
             CLP=0 traffic or for CLP=0+1 traffic."
        REFERENCE
            "ATM Forum PNNI 1.0 Sections 5.8.1.1.3.1, 5.13.4.1"
        ::= { pnniMetricsEntry 5 }


pnniMetricsAdminWeight OBJECT-TYPE
        SYNTAX        Unsigned32   (1..16777215)
        MAX-ACCESS    read-create
        STATUS        current
        DESCRIPTION
            "The administrative weight from the advertising node to the
             remote end of the PNNI entity or to the reachable address
             or transit network, for the specified service categories."
        REFERENCE
            "ATM Forum PNNI 1.0 Section 5.8.1.1.3.4"
        DEFVAL     { 5040 }
        ::= { pnniMetricsEntry 6 }


pnniMetrics1 OBJECT-TYPE
        SYNTAX        Unsigned32
        MAX-ACCESS    read-create
        STATUS        current
        DESCRIPTION
            "An alternate routing parameter from the advertising node to
             the remote end of the PNNI entity or to the reachable
             address or transit network, for the specified service
             categories.

             For information learned from PNNI nodes, this is the
             maximum cell rate in cells per second for the specified
             service categories.

             If this parameter is not used, its value should be set to
             0xFFFFFFFF."
        REFERENCE
            "ATM Forum PNNI 1.0 Section 5.8.1.1.3.7"
        DEFVAL { 'FFFFFFFF'h }
        ::= { pnniMetricsEntry 7 }


pnniMetrics2 OBJECT-TYPE
        SYNTAX        Unsigned32
        MAX-ACCESS    read-create
        STATUS        current
        DESCRIPTION
            "An alternate routing parameter from the advertising node to
             the remote end of the PNNI entity or to the reachable
             address or transit network, for the specified service
             categories.

             For information learned from PNNI nodes, this is the
             available cell rate in cells per second for the specified
             service categories.

             If this parameter is not used, its value should be set to
             0xFFFFFFFF."
        REFERENCE
            "ATM Forum PNNI 1.0 Section 5.8.1.1.3.8"
        DEFVAL { 'FFFFFFFF'h }
        ::= { pnniMetricsEntry 8 }


pnniMetrics3 OBJECT-TYPE
        SYNTAX        Unsigned32
        MAX-ACCESS    read-create
        STATUS        current
        DESCRIPTION
            "An alternate routing parameter from the advertising node to
             the remote end of the PNNI entity or to the reachable
             address or transit network, for the specified service
             categories.

             For information learned from PNNI nodes, this is the
             maximum cell transfer delay in microseconds for the
             specified service categories.

             If this parameter is not used, its value should be set to
             0xFFFFFFFF."
        REFERENCE
            "ATM Forum PNNI 1.0 Section 5.8.1.1.3.3"
        DEFVAL { 'FFFFFFFF'h }
        ::= { pnniMetricsEntry 9 }


pnniMetrics4 OBJECT-TYPE
        SYNTAX        Unsigned32
        MAX-ACCESS    read-create
        STATUS        current
        DESCRIPTION
            "An alternate routing parameter from the advertising node to
             the remote end of the PNNI entity or to the reachable
             address or transit network, for the specified service
             categories.

             For information learned from PNNI nodes, this is the cell
             delay variation in microseconds for the specified service
             categories.

             If this parameter is not used, its value should be set to
             0xFFFFFFFF."
        REFERENCE
            "ATM Forum PNNI 1.0 Section 5.8.1.1.3.2"
        DEFVAL { 'FFFFFFFF'h }
        ::= { pnniMetricsEntry 10 }


pnniMetrics5 OBJECT-TYPE
        SYNTAX        Unsigned32
        MAX-ACCESS    read-create
        STATUS        current
        DESCRIPTION
            "An alternate routing parameter from the advertising node to
             the remote end of the PNNI entity or to the reachable
             address or transit network, for the specified service
             categories.

             For PNNI, this is the cell loss ratio for CLP=0 traffic for
             the specified service categories.  The cell loss ratio
             value is computed as 10**(-n) where 'n' is the value
             returned in this variable.

             If this parameter is not used, its value should be set to
             0xFFFFFFFF."
        REFERENCE
            "ATM Forum PNNI 1.0 Section 5.8.1.1.3.5"
        DEFVAL { 'FFFFFFFF'h }
        ::= { pnniMetricsEntry 11 }

pnniMetrics6 OBJECT-TYPE
        SYNTAX        Unsigned32
        MAX-ACCESS    read-create
        STATUS        current
        DESCRIPTION
            "An alternate routing parameter from the advertising node to
             the remote end of the PNNI entity or to the reachable
             address or transit network, for the specified service
             categories.

             For PNNI, this is the cell loss ratio for CLP=0+1 traffic
             for the specified service categories.  The cell loss ratio
             value is computed as 10**(-n) where 'n' is the value
             returned in this variable.

             If this parameter is not used, its value should be set to
             0xFFFFFFFF."
        REFERENCE
            "ATM Forum PNNI 1.0 Section 5.8.1.1.3.6"
        DEFVAL { 'FFFFFFFF'h }
        ::= { pnniMetricsEntry 12 }


pnniMetrics7 OBJECT-TYPE
        SYNTAX        Unsigned32
        MAX-ACCESS    read-create
        STATUS        current
        DESCRIPTION
            "An alternate routing parameter from the advertising node to
             the remote end of the PNNI entity or to the reachable
             address or transit network, for the specified service
             categories.

             For information learned from PNNI nodes, this is the cell
             rate margin in cells per second for the specified service
             categories.

             If this parameter is not used, its value should be set to
             0xFFFFFFFF."
        REFERENCE
            "ATM Forum PNNI 1.0 Section 5.8.1.1.3.9"
        DEFVAL { 'FFFFFFFF'h }
        ::= { pnniMetricsEntry 13 }


pnniMetrics8 OBJECT-TYPE
        SYNTAX        Unsigned32
        MAX-ACCESS    read-create
        STATUS        current
        DESCRIPTION
            "An alternate routing parameter from the advertising node to
             the remote end of the PNNI entity or to the reachable
             address or transit network, for the specified service
             categories.

             For information learned from PNNI nodes, this is the
             variance factor in units of 2**(-8) for the specified
             service categories.

             If this parameter is not used, its value should be set to
             0xFFFFFFFF."
        REFERENCE
            "ATM Forum PNNI 1.0 Section 5.8.1.1.3.10"
        DEFVAL { 'FFFFFFFF'h }
        ::= { pnniMetricsEntry 14 }


pnniMetricsRowStatus OBJECT-TYPE
        SYNTAX        RowStatus
        MAX-ACCESS    read-create
        STATUS        current
        DESCRIPTION
            "To create, delete, activate and de-activate a set of
             metrics."
        ::= { pnniMetricsEntry 15 }


--
--  PNNI Routing Tables
--

pnniRoutingGroup OBJECT IDENTIFIER ::= { pnniMIBObjects 19 }
pnniRouteBaseGroup OBJECT IDENTIFIER ::= { pnniRoutingGroup 1 }

pnniRouteNodeNumber OBJECT-TYPE
        SYNTAX        Gauge32
        MAX-ACCESS    read-only
        STATUS        current
        DESCRIPTION
            "The number of current precalculated PNNI routes to PNNI
             nodes that are not invalid."
        ::= { pnniRouteBaseGroup 1 }


pnniRouteAddrNumber OBJECT-TYPE
        SYNTAX        Gauge32
        MAX-ACCESS    read-only
        STATUS        current
        DESCRIPTION
            "The number of current PNNI routes from nodes in the PNNI
             routing domain to addresses and transit networks that are
             not invalid."
        ::= { pnniRouteBaseGroup 2 }


-- Table of routes to other nodes

pnniRouteNodeTable OBJECT-TYPE
        SYNTAX        SEQUENCE OF PnniRouteNodeEntry
        MAX-ACCESS    not-accessible
        STATUS        current
        DESCRIPTION
            "This entity's PNNI Routing table (of routes to other
             nodes)."
        ::= { pnniRoutingGroup 2 }

pnniRouteNodeEntry OBJECT-TYPE
        SYNTAX        PnniRouteNodeEntry
        MAX-ACCESS    not-accessible
        STATUS        current
        DESCRIPTION
            "A particular route to a particular destination node, under
             a particular policy."
        INDEX         { pnniNodeIndex,
                        pnniRouteNodeClass,
                        pnniRouteNodeDestNodeId,
                        pnniRouteNodeDTL }
        ::= { pnniRouteNodeTable 1 }

PnniRouteNodeEntry ::=
        SEQUENCE {
                pnniRouteNodeClass         ServiceCategory,
                pnniRouteNodeDestNodeId    PnniNodeId,
                pnniRouteNodeDTL           Integer32,
                pnniRouteNodeDestPortId    PnniPortId,
                pnniRouteNodeProto         INTEGER,
                pnniRouteNodeTimeStamp     TimeStamp,
                pnniRouteNodeInfo          OBJECT IDENTIFIER,
                pnniRouteNodeGcacClp       ClpType,
                pnniRouteNodeFwdMetricAW   Unsigned32,
                pnniRouteNodeFwdMetric1    Unsigned32,
                pnniRouteNodeFwdMetric2    Unsigned32,
                pnniRouteNodeFwdMetric3    Unsigned32,
                pnniRouteNodeFwdMetric4    Unsigned32,
                pnniRouteNodeFwdMetric5    Unsigned32,
                pnniRouteNodeFwdMetric6    Unsigned32,
                pnniRouteNodeFwdMetric7    Unsigned32,
                pnniRouteNodeFwdMetric8    Unsigned32,
                pnniRouteNodeBwdMetricAW   Unsigned32,
                pnniRouteNodeBwdMetric1    Unsigned32,
                pnniRouteNodeBwdMetric2    Unsigned32,
                pnniRouteNodeBwdMetric3    Unsigned32,
                pnniRouteNodeBwdMetric4    Unsigned32,
                pnniRouteNodeBwdMetric5    Unsigned32,
                pnniRouteNodeBwdMetric6    Unsigned32,
                pnniRouteNodeBwdMetric7    Unsigned32,
                pnniRouteNodeBwdMetric8    Unsigned32,
                pnniRouteNodeVPCapability  TruthValue,
                pnniRouteNodeStatus        RowStatus
                }

pnniRouteNodeClass OBJECT-TYPE
        SYNTAX        ServiceCategory
        MAX-ACCESS    not-accessible
        STATUS        current
        DESCRIPTION
            "Indicates the service category with which this forwarding
             table entry is associated."
        ::= { pnniRouteNodeEntry 1 }

pnniRouteNodeDestNodeId OBJECT-TYPE
        SYNTAX        PnniNodeId
        MAX-ACCESS    not-accessible
        STATUS        current
        DESCRIPTION
            "The node ID of the destination node to which this route
             proceeds, and at which the DTL stack for this route
             terminates."
        ::= { pnniRouteNodeEntry 2 }

pnniRouteNodeDTL OBJECT-TYPE
        SYNTAX        Integer32 (1..2147483647)
        MAX-ACCESS    not-accessible
        STATUS        current
        DESCRIPTION
            "The index into the owning PNNI node's DTL table of the DTL
             stack that goes with this route."
        ::= { pnniRouteNodeEntry 3 }

pnniRouteNodeDestPortId OBJECT-TYPE
        SYNTAX        PnniPortId
        MAX-ACCESS    read-create
        STATUS        current
        DESCRIPTION
            "The port ID of the destination node at which the route
             terminates.  A port ID of zero indicates the node nucleus.
             When the destination node is represented by the simple node
             representation, this value should be set to zero."
        DEFVAL { 0 }
        ::= { pnniRouteNodeEntry 4 }


pnniRouteNodeProto OBJECT-TYPE
        SYNTAX        INTEGER {
                                other(1), -- not specified
                                local(2), -- e.g. ilmi
                                mgmt(3), -- configured by management,
                                       -- for example by SNMP or console
                                        -- the following are all dynamic
                                        -- routing protocols
                                pnni(4) -- ATM Forum PNNI
                                }
        MAX-ACCESS    read-only
        STATUS        current
        DESCRIPTION
            "The routing mechanism via which this route was learned."
        ::= { pnniRouteNodeEntry 5 }

pnniRouteNodeTimeStamp OBJECT-TYPE
        SYNTAX        TimeStamp 
        MAX-ACCESS    read-only
        STATUS        current
        DESCRIPTION
            "The time at which this  route  was last  updated  or
             otherwise  determined  to be correct.  Note that no
             semantics of  `too  old' can  be implied except through
             knowledge of the routing  protocol  by  which  the route
             was learned."
        ::= { pnniRouteNodeEntry 6 }

pnniRouteNodeInfo OBJECT-TYPE
        SYNTAX        OBJECT IDENTIFIER
        MAX-ACCESS    read-create
        STATUS        current
        DESCRIPTION
            "A reference to MIB definitions specific to the particular
             routing protocol which is responsible for this route, as
             determined by the value specified in the route's
             pnniRouteNodeProto value.  If this information is not
             present, its value should be set to the OBJECT IDENTIFIER
             zeroDotZero."
        DEFVAL { zeroDotZero }
        ::= { pnniRouteNodeEntry 7 }

pnniRouteNodeGcacClp OBJECT-TYPE
        SYNTAX        ClpType
        MAX-ACCESS    read-create
        STATUS        current
        DESCRIPTION
            "For PNNI, indicates whether any advertised GCAC parameters
             apply for CLP=0 traffic or for CLP=0+1 traffic."
        ::= { pnniRouteNodeEntry 8 }

pnniRouteNodeFwdMetricAW OBJECT-TYPE
        SYNTAX        Unsigned32
        MAX-ACCESS    read-create
        STATUS        current
        DESCRIPTION
            "The cumulative administrative weight calculated for the
             forward direction of this route.  If this metric is not
             used, its value should be set to 0xFFFFFFFF."
        REFERENCE
            "ATM Forum PNNI 1.0 Section 5.8.1.1.3.4"
        DEFVAL { 'FFFFFFFF'h }
        ::= { pnniRouteNodeEntry 9 }

pnniRouteNodeFwdMetric1 OBJECT-TYPE
        SYNTAX        Unsigned32
        MAX-ACCESS    read-create
        STATUS        current
        DESCRIPTION
            "An alternate routing parameter for the forward direction of
             this route.

             For information learned from PNNI nodes, this is the
             maximum possible cell rate (in cells per second) for the
             forward direction of the route.

             If this parameter is not used, its value should be set to
             0xFFFFFFFF."
        REFERENCE
            "ATM Forum PNNI 1.0 Section 5.8.1.1.3.7"
        DEFVAL { 'FFFFFFFF'h }
        ::= { pnniRouteNodeEntry 10 }

pnniRouteNodeFwdMetric2 OBJECT-TYPE
        SYNTAX        Unsigned32
        MAX-ACCESS    read-create
        STATUS        current
        DESCRIPTION
            "An alternate routing parameter for the forward direction of
             this route.

             For information learned from PNNI nodes, this is the
             Available cell rate (in cells per second) for the forward
             direction of the route.  Further information on available
             bandwidth may be obtainable by reference to the nodal
             advertisements of the nodes in the path.

             If this parameter is not used, its value should be set to
             0xFFFFFFFF."
        REFERENCE
            "ATM Forum PNNI 1.0 Section 5.8.1.1.3.8"
        DEFVAL { 'FFFFFFFF'h }
        ::= { pnniRouteNodeEntry 11 }

pnniRouteNodeFwdMetric3 OBJECT-TYPE
        SYNTAX        Unsigned32
        MAX-ACCESS    read-create
        STATUS        current
        DESCRIPTION
            "An alternate routing parameter for the forward direction of
             this route.

             For information learned from PNNI nodes, this is the
             cumulative Maximum Cell Transfer Delay (in microseconds)
             for the forward direction of the route.

             If this parameter is not used, its value should be set to
             0xFFFFFFFF."
        REFERENCE
            "ATM Forum PNNI 1.0 Section 5.8.1.1.3.3"
        DEFVAL { 'FFFFFFFF'h }
        ::= { pnniRouteNodeEntry 12 }

pnniRouteNodeFwdMetric4 OBJECT-TYPE
        SYNTAX        Unsigned32
        MAX-ACCESS    read-create
        STATUS        current
        DESCRIPTION
            "An alternate routing parameter for the forward direction of
             this route.

             For information learned from PNNI nodes, this is the
             cumulative Cell Delay Variation (in microseconds) for the
             forward direction of the route.

             If this parameter is not used, its value should be set to
             0xFFFFFFFF."
        REFERENCE
            "ATM Forum PNNI 1.0 Section 5.8.1.1.3.2"
        DEFVAL { 'FFFFFFFF'h }
        ::= { pnniRouteNodeEntry 13 }

pnniRouteNodeFwdMetric5 OBJECT-TYPE
        SYNTAX        Unsigned32
        MAX-ACCESS    read-create
        STATUS        current
        DESCRIPTION
            "An alternate routing parameter for the forward direction of
             this route.

             For information learned from PNNI nodes, this is the
             cumulative Cell Loss Ratio for CLP=0 traffic for the
             forward direction of the route. The cell loss ratio value
             is computed as 10**(-n) where 'n' is the value returned in
             this variable.

             If this parameter is not used, its value should be set to
             0xFFFFFFFF."
        REFERENCE
            "ATM Forum PNNI 1.0 Section 5.8.1.1.3.5"
        DEFVAL { 'FFFFFFFF'h }
        ::= { pnniRouteNodeEntry 14 }

pnniRouteNodeFwdMetric6 OBJECT-TYPE
        SYNTAX        Unsigned32
        MAX-ACCESS    read-create
        STATUS        current
        DESCRIPTION
            "An alternate routing parameter for the forward direction of
             this route.

             For information learned from PNNI nodes, this is the
             cumulative Cell Loss Ratio for CLP=0+1 traffic for the
             forward direction of the route. The cell loss ratio value
             is computed as 10**(-n) where 'n' is the value returned in
             this variable.

             If this parameter is not used, its value should be set to
             0xFFFFFFFF."
        REFERENCE
            "ATM Forum PNNI 1.0 Section 5.8.1.1.3.6"
        DEFVAL { 'FFFFFFFF'h }
        ::= { pnniRouteNodeEntry 15 }


pnniRouteNodeFwdMetric7 OBJECT-TYPE
        SYNTAX        Unsigned32
        MAX-ACCESS    read-create
        STATUS        current
        DESCRIPTION
            "An alternate routing parameter for the forward direction of
             this route.

             For information learned from PNNI nodes, this is the Cell
             Rate Margin (in cells per second) for the forward direction
             of the route.

             If this parameter is not used, its value should be set to
             0xFFFFFFFF."
        REFERENCE
            "ATM Forum PNNI 1.0 Section 5.8.1.1.3.9"
        DEFVAL { 'FFFFFFFF'h }
        ::= { pnniRouteNodeEntry 16 }

pnniRouteNodeFwdMetric8 OBJECT-TYPE
        SYNTAX        Unsigned32
        MAX-ACCESS    read-create
        STATUS        current
        DESCRIPTION
            "An alternate routing parameter for the forward direction of
             this route.

             For information learned from PNNI nodes, this is the
             Variance Factor (in units of 2**(-8)) for the forward
             direction of the route.

             If this parameter is not used, its value should be set to
             0xFFFFFFFF."
        REFERENCE
            "ATM Forum PNNI 1.0 Section 5.8.1.1.3.10"
        DEFVAL { 'FFFFFFFF'h }
        ::= { pnniRouteNodeEntry 17 }

pnniRouteNodeBwdMetricAW OBJECT-TYPE
        SYNTAX        Unsigned32
        MAX-ACCESS    read-create
        STATUS        current
        DESCRIPTION
            "The administrative weight calculated for the backward
             direction of this route.  If this metric is not used, its
             value should be set to 0xFFFFFFFF."
        REFERENCE
            "ATM Forum PNNI 1.0 Section 5.8.1.1.3.4"
        DEFVAL { 'FFFFFFFF'h }
        ::= { pnniRouteNodeEntry 18 }

pnniRouteNodeBwdMetric1 OBJECT-TYPE
        SYNTAX        Unsigned32
        MAX-ACCESS    read-create
        STATUS        current
        DESCRIPTION
            "An alternate routing parameter for the backward direction
             of this route.

             For information learned from PNNI nodes, this is the
             maximum possible cell rate (in cells per second) for the
             backward direction of the route.

             If this parameter is not used, its value should be set to
             0xFFFFFFFF."
        REFERENCE
            "ATM Forum PNNI 1.0 Section 5.8.1.1.3.7"
        DEFVAL { 'FFFFFFFF'h }
        ::= { pnniRouteNodeEntry 19 }

pnniRouteNodeBwdMetric2 OBJECT-TYPE
        SYNTAX        Unsigned32
        MAX-ACCESS    read-create
        STATUS        current
        DESCRIPTION
            "An alternate routing parameter for the backward direction
             of this route.

             For information learned from PNNI nodes, this is the
             Available cell rate (in cells per second) for the backward
             direction of the route.  Further information on available
             bandwidth may be obtainable by reference to the nodal
             advertisements of the nodes in the path.

             If this parameter is not used, its value should be set to
             0xFFFFFFFF."
        REFERENCE
            "ATM Forum PNNI 1.0 Section 5.8.1.1.3.8"
        DEFVAL { 'FFFFFFFF'h }
        ::= { pnniRouteNodeEntry 20 }

pnniRouteNodeBwdMetric3 OBJECT-TYPE
        SYNTAX        Unsigned32
        MAX-ACCESS    read-create
        STATUS        current
        DESCRIPTION
            "An alternate routing parameter for the backward direction
             of this route.

             For information learned from PNNI nodes, this is the
             cumulative Maximum Cell Transfer Delay (in microseconds)
             for the backward direction of the route.

             If this parameter is not used, its value should be set to
             0xFFFFFFFF."
        REFERENCE
            "ATM Forum PNNI 1.0 Section 5.8.1.1.3.3"
        DEFVAL { 'FFFFFFFF'h }
        ::= { pnniRouteNodeEntry 21 }

pnniRouteNodeBwdMetric4 OBJECT-TYPE
        SYNTAX        Unsigned32
        MAX-ACCESS    read-create
        STATUS        current
        DESCRIPTION
            "An alternate routing parameter for the backward direction
             of this route.

             For information learned from PNNI nodes, this is the
             cumulative Cell Delay Variation (in microseconds) for the
             backward direction of the route.

             If this parameter is not used, its value should be set to
             0xFFFFFFFF."
        REFERENCE
            "ATM Forum PNNI 1.0 Section 5.8.1.1.3.2"
        DEFVAL { 'FFFFFFFF'h }
        ::= { pnniRouteNodeEntry 22 }

pnniRouteNodeBwdMetric5 OBJECT-TYPE
        SYNTAX        Unsigned32
        MAX-ACCESS    read-create
        STATUS        current
        DESCRIPTION
            "An alternate routing parameter for the backward direction
             of this route.

             For information learned from PNNI nodes, this is the
             cumulative Cell Loss Ratio for CLP=0 traffic for the
             backward direction of the route. The cell loss ratio value
             is computed as 10**(-n) where 'n' is the value returned in
             this variable.

             If  this parameter is not used, its value should be set to
             0xFFFFFFFF."
        REFERENCE
            "ATM Forum PNNI 1.0 Section 5.8.1.1.3.5"
        DEFVAL { 'FFFFFFFF'h }
        ::= { pnniRouteNodeEntry 23 }

pnniRouteNodeBwdMetric6 OBJECT-TYPE
        SYNTAX        Unsigned32
        MAX-ACCESS    read-create
        STATUS        current
        DESCRIPTION
            "An alternate routing parameter for the backward direction
             of this route.

             For information learned from PNNI nodes, this is the
             cumulative Cell Loss Ratio for CLP=0+1 traffic for the
             backward direction of the route. The cell loss ratio value
             is computed as 10**(-n) where 'n' is the value returned in
             this variable.

             If  this parameter is not used, its value should be set to
             0xFFFFFFFF."
        REFERENCE
            "ATM Forum PNNI 1.0 Section 5.8.1.1.3.6"
        DEFVAL { 'FFFFFFFF'h }
        ::= { pnniRouteNodeEntry 24 }


pnniRouteNodeBwdMetric7 OBJECT-TYPE
        SYNTAX        Unsigned32
        MAX-ACCESS    read-create
        STATUS        current
        DESCRIPTION
            "An alternate routing parameter for the backward direction
             of this route.

             For information learned from PNNI nodes, this is the Cell
             Rate Margin (in cells per second) for the backward
             direction of the route.

             If this parameter is not used, its value should be set to
             0xFFFFFFFF."
        REFERENCE
            "ATM Forum PNNI 1.0 Section 5.8.1.1.3.9"
        DEFVAL { 'FFFFFFFF'h }
        ::= { pnniRouteNodeEntry 25 }

pnniRouteNodeBwdMetric8 OBJECT-TYPE
        SYNTAX        Unsigned32
        MAX-ACCESS    read-create
        STATUS        current
        DESCRIPTION
            "An alternate routing parameter for the backward direction
             of this route.

             For information learned from PNNI nodes, this is the
             Variance Factor (in units of 2**(-8)) for the backward
             direction of the route.

             If this parameter is not used, its value should be set to
             0xFFFFFFFF."
        REFERENCE
            "ATM Forum PNNI 1.0 Section 5.8.1.1.3.10"
        DEFVAL { 'FFFFFFFF'h }
        ::= { pnniRouteNodeEntry 26 }

pnniRouteNodeVPCapability OBJECT-TYPE
        SYNTAX        TruthValue
        MAX-ACCESS    read-create
        STATUS        current
        DESCRIPTION
            "This attribute indicates whether a VPC setup on this route
             is possible."
        ::= { pnniRouteNodeEntry 27 }

pnniRouteNodeStatus OBJECT-TYPE
        SYNTAX        RowStatus
        MAX-ACCESS    read-create
        STATUS        current
        DESCRIPTION
            "The row status variable, used according to row installation
             and removal conventions."
        ::= { pnniRouteNodeEntry 28 }


-- Table of DTL stacks for routes to other nodes

pnniDTLTable OBJECT-TYPE
        SYNTAX        SEQUENCE OF PnniDTLEntry
        MAX-ACCESS    not-accessible
        STATUS        current
        DESCRIPTION
            "The set of all DTL stacks used for the pre-computed routes
             maintained by this managed entity."
        ::= { pnniRoutingGroup 3 }

pnniDTLEntry OBJECT-TYPE
        SYNTAX        PnniDTLEntry
        MAX-ACCESS    not-accessible
        STATUS        current
        DESCRIPTION
            "A segment of a DTL stack.  The complete DTL stack is formed
             by traversing the rows of the table for which the
             pnniDTLIndex is the same.  Level transitions are indicated
             using the pnniDLTLinkType column."
        INDEX {
                pnniNodeIndex,
                pnniDTLIndex,
                pnniDTLEntryIndex
                }
        ::= { pnniDTLTable 1 }

PnniDTLEntry ::=
        SEQUENCE {
                pnniDTLIndex      Integer32,
                pnniDTLEntryIndex Integer32,
                pnniDTLNodeId     PnniNodeId,
                pnniDTLPortId     PnniPortId,
                pnniDTLLinkType   INTEGER,
                pnniDTLStatus     RowStatus
                }

pnniDTLIndex OBJECT-TYPE
        SYNTAX        Integer32 (1..2147483647)
        MAX-ACCESS    not-accessible
        STATUS        current
        DESCRIPTION
            "The index in the node's DTL table of this DTL stack."
        ::= { pnniDTLEntry 1 }

pnniDTLEntryIndex OBJECT-TYPE
        SYNTAX        Integer32 (1..200)
        MAX-ACCESS    not-accessible
        STATUS        current
        DESCRIPTION
            "The index in the current DTL stack of this entry."
        ::= { pnniDTLEntry 2 }

pnniDTLNodeId OBJECT-TYPE
        SYNTAX        PnniNodeId
        MAX-ACCESS    read-create
        STATUS        current
        DESCRIPTION
            "The node which is this hop in the DTL stack."
        ::= { pnniDTLEntry 3 }

pnniDTLPortId OBJECT-TYPE
        SYNTAX        PnniPortId
        MAX-ACCESS    read-create
        STATUS        current
        DESCRIPTION
            "The port from the pnniDTLNodeId to use as the exit.  If the
             DTL stack does not care, this is coded as zero."
        ::= { pnniDTLEntry 4 }

pnniDTLLinkType OBJECT-TYPE
        SYNTAX        INTEGER {
                                invalid    (1), -- An invalid link
                                horizontal (2), -- A normal link within
                                            -- the containing peer group
                                uplink     (3), -- A link going up a
                                                -- level
                                last       (4) -- The last entry in the
                                               -- DTL stack
                                }
        MAX-ACCESS    read-create
        STATUS        current
        DESCRIPTION
            "The type of link out from this node (pnniDTLNodeId).  This
             is well defined even if the specific port is not
             specified."
        ::= { pnniDTLEntry 5 }

pnniDTLStatus OBJECT-TYPE
        SYNTAX        RowStatus
        MAX-ACCESS    read-create
        STATUS        current
        DESCRIPTION
            "The row status variable, used according to row installation
             and removal conventions."
        ::= { pnniDTLEntry 6 }


-- Table of routes from nodes to reachable addresses

pnniRouteAddrTable OBJECT-TYPE
        SYNTAX        SEQUENCE OF PnniRouteAddrEntry
        MAX-ACCESS    not-accessible
        STATUS        current
        DESCRIPTION
            "A table containing all the attributes necessary to
             determine what the PNNI entity believes is reachable in
             terms of ATM End System Addresses and to determine which
             nodes are advertising this reachability.  This table is
             also used to configure static routes to reachable address
             prefixes.  The local node index that received the
             reachability information, reachable address, address prefix
             length, and an index that distinguishes between multiple
             listings of connectivity to a given address prefix from a
             given local node are combined to form an instance ID for
             this object."
        REFERENCE
            "ATM Forum PNNI 1.0 Section 5.8.1.3"
        ::= { pnniRoutingGroup 4 }

pnniRouteAddrEntry OBJECT-TYPE
        SYNTAX        PnniRouteAddrEntry
        MAX-ACCESS    not-accessible
        STATUS        current
        DESCRIPTION
            "An entry in the table, containing information about a
             reachable address prefix."
        REFERENCE
            "ATM Forum PNNI 1.0 Section 5.8.1.3"
        INDEX         { pnniNodeIndex,
                        pnniRouteAddrAddress,
                        pnniRouteAddrPrefixLength,
                        pnniRouteAddrIndex }
        ::= { pnniRouteAddrTable 1 }
PnniRouteAddrEntry ::=
        SEQUENCE {
                pnniRouteAddrAddress            AtmAddrPrefix,
                pnniRouteAddrPrefixLength       PnniPrefixLength,
                pnniRouteAddrIndex              Integer32,
                pnniRouteAddrIfIndex            InterfaceIndex,
                pnniRouteAddrAdvertisingNodeId  PnniNodeId,
                pnniRouteAddrAdvertisedPortId   PnniPortId,
                pnniRouteAddrType               INTEGER,
                pnniRouteAddrProto              INTEGER,
                pnniRouteAddrPnniScope          PnniLevel,
                pnniRouteAddrVPCapability       TruthValue,
                pnniRouteAddrMetricsTag         PnniMetricsTag,
                pnniRouteAddrPtseId             Unsigned32,
                pnniRouteAddrOriginateAdvertisement     TruthValue,
                pnniRouteAddrInfo               OBJECT IDENTIFIER,
                pnniRouteAddrOperStatus         INTEGER,
                pnniRouteAddrTimeStamp          TimeStamp,
                pnniRouteAddrRowStatus          RowStatus
                }
pnniRouteAddrAddress OBJECT-TYPE
        SYNTAX        AtmAddrPrefix
        MAX-ACCESS    not-accessible
        STATUS        current
        DESCRIPTION
            "The value of the ATM End System Address prefix."
        ::= { pnniRouteAddrEntry 1 }

pnniRouteAddrPrefixLength OBJECT-TYPE
        SYNTAX        PnniPrefixLength
        MAX-ACCESS    not-accessible
        STATUS        current
        DESCRIPTION
            "The prefix length to be applied to the ATM End System
             Address prefix."
        ::= { pnniRouteAddrEntry 2 }

pnniRouteAddrIndex OBJECT-TYPE
        SYNTAX        Integer32 (1..65535)
        MAX-ACCESS    not-accessible
        STATUS        current
        DESCRIPTION
            "An index into the set of listings of connectivity to a
             given address prefix from a given local node."
        ::= { pnniRouteAddrEntry 3 }

pnniRouteAddrIfIndex OBJECT-TYPE
        SYNTAX        InterfaceIndex
        MAX-ACCESS    read-create
        STATUS        current
        DESCRIPTION
            "The local interface over which the reachable address can be
             reached.  The value zero indicates an unknown interface or
             reachability through a remote node.

             This object may only have a non-zero value if the value of
             the corresponding instance of pnniRouteAddrProto is other
             than 'pnni', pnniRouteAddrType is other than 'reject', and
             the node identified by pnniRouteAddrAdvertisingNodeId is
             instantiated within this switching system."
        ::= { pnniRouteAddrEntry 4 }

pnniRouteAddrAdvertisingNodeId OBJECT-TYPE
        SYNTAX        PnniNodeId
        MAX-ACCESS    read-create
        STATUS        current
        DESCRIPTION
            "The node ID of a node advertising reachability to the
             address prefix.  If the local node index is zero, then the
             advertising node ID must be set to all zeros."
        ::= { pnniRouteAddrEntry 5 }
pnniRouteAddrAdvertisedPortId OBJECT-TYPE
        SYNTAX        PnniPortId
        MAX-ACCESS    read-create
        STATUS        current
        DESCRIPTION
            "The port identifier used from the advertising node to reach
             the given address prefix."
        DEFVAL { 0 }
        ::= { pnniRouteAddrEntry 6 }

pnniRouteAddrType OBJECT-TYPE
        SYNTAX        INTEGER {
                                other(1), -- not specified by this MIB
                                reject(2), -- route which discards
                                           -- traffic
                                internal(3),
                                exterior(4)
                                }
        MAX-ACCESS    read-create
        STATUS        current
        DESCRIPTION
            "The type (e.g. internal or exterior) of reachability from
             the advertising node to the address prefix.

             Reject(2) refers to an address prefix which, if matched,
             indicates that the message should be discarded as
             unreachable. This is used in some protocols as a means of
             correctly aggregating routes."
        REFERENCE
            "ATM Forum PNNI 1.0 Section 5.8.1.3"
        DEFVAL { exterior }
        ::= { pnniRouteAddrEntry 7 }

pnniRouteAddrProto OBJECT-TYPE
        SYNTAX        INTEGER {
                                other(1), -- not specified
                                local(2), -- e.g. ilmi
                                mgmt(3), -- configured by management,
                                       -- for example by SNMP or console
                                        -- the following are all dynamic
                                        -- routing protocols
                                pnni(4) -- ATM Forum PNNI
                                }
        MAX-ACCESS    read-only
        STATUS        current
        DESCRIPTION
            "The routing mechanism via which the connectivity from the
             advertising node to the reachable address prefix was
             learned."
        ::= { pnniRouteAddrEntry 8 }


pnniRouteAddrPnniScope OBJECT-TYPE
        SYNTAX        PnniLevel
        MAX-ACCESS    read-create
        STATUS        current
        DESCRIPTION
            "The PNNI scope of advertisement (i.e. level of PNNI
             hierarchy) of the reachability from the advertising node to
             the address prefix."
        REFERENCE
            "ATM Forum PNNI 1.0 Sections 5.3.6, 5.9.1"
        ::= { pnniRouteAddrEntry 9 }

pnniRouteAddrVPCapability OBJECT-TYPE
        SYNTAX        TruthValue
        MAX-ACCESS    read-create
        STATUS        current
        DESCRIPTION
            "Indicates whether VPCs can be established from the
             advertising node to the reachable address prefix."
        REFERENCE
            "ATM Forum PNNI 1.0 Section 5.14.9.1 Table 5-34"
        ::= { pnniRouteAddrEntry 10 }

pnniRouteAddrMetricsTag OBJECT-TYPE
        SYNTAX        PnniMetricsTag
        MAX-ACCESS    read-create
        STATUS        current
        DESCRIPTION
            "The index into the pnniMetricsTable for the traffic
             parameter values that apply for the connectivity from the
             advertising node to the reachable address prefix.  There
             will be one or more entries in the pnniMetricsTable whose
             first instance identifier matches the value of this
             variable.

             If there are no parameters associated with this reachable
             address prefix then the distinguished value zero is used."
        DEFVAL { 0 }
        ::= { pnniRouteAddrEntry 11 }

pnniRouteAddrPtseId OBJECT-TYPE
        SYNTAX        Unsigned32
        MAX-ACCESS    read-only
        STATUS        current
        DESCRIPTION
            "For reachable addresses learned via PNNI, this attribute
             contains the value of the PTSE Identifier for the PTSE
             being originated by the originating node which contains the
             information group(s) describing the reachable address.  For
             reachable addresses learned by means other than PNNI, this
             attribute is set to zero."
        REFERENCE
            "ATM Forum PNNI 1.0 Section 5.8.2"
        ::= { pnniRouteAddrEntry 12 }

pnniRouteAddrOriginateAdvertisement OBJECT-TYPE
        SYNTAX        TruthValue
        MAX-ACCESS    read-create
        STATUS        current
        DESCRIPTION
            "Whether or not the reachable address specified by this
             entry is to be advertised by the local node into its PNNI
             routing domain.

             This object may only take on the value 'true' when the
             value of the corresponding instance of pnniRouteAddrProto
             is other than 'pnni'."
        DEFVAL { true }
        ::= { pnniRouteAddrEntry 13 }

pnniRouteAddrInfo OBJECT-TYPE
        SYNTAX        OBJECT IDENTIFIER
        MAX-ACCESS    read-create
        STATUS        current
        DESCRIPTION
            "A reference to MIB definitions specific to the particular
             routing protocol which is responsible for this reachable
             address prefix, as determined by the value specified in the
             route's pnniRouteAddrProto value.  If this information is
             not present, its value should be set to the OBJECT
             IDENTIFIER zeroDotZero."
        DEFVAL { zeroDotZero }
        ::= { pnniRouteAddrEntry 14 }

pnniRouteAddrOperStatus OBJECT-TYPE
        SYNTAX        INTEGER {
                                inactive(1),
                                active(2), -- i.e. reachability to this
                                           -- prefix exists and is not
                                           -- being advertised in PNNI
                                advertised(3)
                                }
        MAX-ACCESS    read-only
        STATUS        current
        DESCRIPTION
            "Indicates whether the reachable address prefix is
             operationally valid and whether it is being advertised by
             this node."
        ::= { pnniRouteAddrEntry 15 }

pnniRouteAddrTimeStamp OBJECT-TYPE
        SYNTAX        TimeStamp
        MAX-ACCESS    read-only
        STATUS        current
        DESCRIPTION
            "Indicates when the connectivity from the advertising node
             to the reachable address prefix became known to the local
             node."
        ::= { pnniRouteAddrEntry 16 }

pnniRouteAddrRowStatus OBJECT-TYPE
        SYNTAX        RowStatus
        MAX-ACCESS    read-create
        STATUS        current
        DESCRIPTION
            "To create, delete, activate and de-activate a reachable
             address prefix."
        ::= { pnniRouteAddrEntry 17 }


-- Table of routes from nodes to reachable transit networks

pnniRouteTnsTable OBJECT-TYPE
        SYNTAX        SEQUENCE OF PnniRouteTnsEntry
        MAX-ACCESS    not-accessible
        STATUS        current
        DESCRIPTION
            "A table containing all the attributes necessary to
             determine what transit networks the PNNI entity believes
             are reachable and to determine which nodes are advertising
             this reachability.  This table is also used to add static
             routes to reachable transit networks.  The local node index
             which received the reachability information, type of
             network identification, network identification plan,
             transit network identifier, and an index that distinguishes
             between multiple listings of connectivity to a given
             transit network from a given local node are combined to
             form an instance ID for this object."
        REFERENCE
            "ATM Forum PNNI 1.0 Section 5.8.1.3.2"
        ::= { pnniRoutingGroup 5 }

pnniRouteTnsEntry OBJECT-TYPE
        SYNTAX        PnniRouteTnsEntry
        MAX-ACCESS    not-accessible
        STATUS        current
        DESCRIPTION
            "An entry in the table, containing information about a
             reachable transit network."
        REFERENCE
            "ATM Forum PNNI 1.0 Section 5.8.1.3.2"
        INDEX         { pnniNodeIndex,
                        pnniRouteTnsType,
                        pnniRouteTnsPlan,
                        pnniRouteTnsId,
                        pnniRouteTnsIndex }
        ::= { pnniRouteTnsTable 1 }

PnniRouteTnsEntry ::=
        SEQUENCE {
                pnniRouteTnsType                TnsType,
                pnniRouteTnsPlan                TnsPlan,
                pnniRouteTnsId                  DisplayString,
                pnniRouteTnsIndex               Integer32,
                pnniRouteTnsIfIndex             InterfaceIndex,
                pnniRouteTnsAdvertisingNodeId   PnniNodeId,
                pnniRouteTnsAdvertisedPortId    PnniPortId,
                pnniRouteTnsRouteType           INTEGER,
                pnniRouteTnsProto               INTEGER,
                pnniRouteTnsPnniScope           PnniLevel,
                pnniRouteTnsVPCapability        TruthValue,
                pnniRouteTnsMetricsTag          PnniMetricsTag,
                pnniRouteTnsPtseId              Unsigned32,
                pnniRouteTnsOriginateAdvertisement      TruthValue,
                pnniRouteTnsInfo                OBJECT IDENTIFIER,
                pnniRouteTnsOperStatus          INTEGER,
                pnniRouteTnsTimeStamp           TimeStamp,
                pnniRouteTnsRowStatus           RowStatus
                }

pnniRouteTnsType OBJECT-TYPE
        SYNTAX        TnsType
        MAX-ACCESS    not-accessible
        STATUS        current
        DESCRIPTION
            "The type of network identification used for this transit
             network."
        ::= { pnniRouteTnsEntry 1 }

pnniRouteTnsPlan OBJECT-TYPE
        SYNTAX        TnsPlan
        MAX-ACCESS    not-accessible
        STATUS        current
        DESCRIPTION
            "The network identification plan according to which network
             identification has been assigned."
        ::= { pnniRouteTnsEntry 2 }

pnniRouteTnsId OBJECT-TYPE
        SYNTAX        DisplayString
        MAX-ACCESS    not-accessible
        STATUS        current
        DESCRIPTION
            "The value of the transit network identifier."
        ::= { pnniRouteTnsEntry 3 }

pnniRouteTnsIndex OBJECT-TYPE
        SYNTAX        Integer32 (1..65535)
        MAX-ACCESS    not-accessible
        STATUS        current
        DESCRIPTION
            "An index into the set of listings of connectivity to a
             given transit network from a given local node."
        ::= { pnniRouteTnsEntry 4 }

pnniRouteTnsIfIndex OBJECT-TYPE
        SYNTAX        InterfaceIndex
        MAX-ACCESS    read-create
        STATUS        current
        DESCRIPTION
            "The local interface over which the transit network can be
             reached.  The value zero indicates an unknown interface or
             reachability through a remote node.

             This object may only have a non-zero value if the value of
             the corresponding instance of pnniRouteTnsProto is other
             than 'pnni' and the node identified by
             pnniRouteTnsAdvertisingNodeId is instantiated within this
             switching system."
        ::= { pnniRouteTnsEntry 5 }

pnniRouteTnsAdvertisingNodeId OBJECT-TYPE
        SYNTAX        PnniNodeId
        MAX-ACCESS    read-create
        STATUS        current
        DESCRIPTION
            "The node ID of a node advertising reachability to the
             transit network.  If the local node index is zero, then the
             advertising node ID must also be set to zero."
        ::= { pnniRouteTnsEntry 6 }
pnniRouteTnsAdvertisedPortId OBJECT-TYPE
        SYNTAX        PnniPortId
        MAX-ACCESS    read-create
        STATUS        current
        DESCRIPTION
            "The port identifier used from the advertising node to
             reach the given transit network."
        DEFVAL { 0 }
        ::= { pnniRouteTnsEntry 7 }

pnniRouteTnsRouteType OBJECT-TYPE
        SYNTAX        INTEGER {
                                other(1), -- not specified by this MIB
                                exterior(4)
                                }
        MAX-ACCESS    read-create
        STATUS        current
        DESCRIPTION
            "The type (e.g. exterior or other) of reachability from the
             advertising node to the transit network."
        REFERENCE
            "ATM Forum PNNI 1.0 Section 5.8.1.3"
        DEFVAL { exterior }
        ::= { pnniRouteTnsEntry 8 }

pnniRouteTnsProto OBJECT-TYPE
        SYNTAX        INTEGER {
                                other(1), -- not specified
                                local(2), -- e.g. ilmi
                                mgmt(3), -- configured by management,
                                       -- for example by SNMP or console
                                        -- the following are all dynamic
                                        -- routing protocols
                                pnni(4) -- ATM Forum PNNI
                                }
        MAX-ACCESS    read-only
        STATUS        current
        DESCRIPTION
            "The routing mechanism via which the connectivity from the
             advertising node to the transit network was learned."
        ::= { pnniRouteTnsEntry 9 }


pnniRouteTnsPnniScope OBJECT-TYPE
        SYNTAX        PnniLevel
        MAX-ACCESS    read-create
        STATUS        current
        DESCRIPTION
            "The PNNI scope of advertisement (i.e. level of PNNI
             hierarchy) of the reachability from the advertising node to
             the transit network."
        REFERENCE
            "ATM Forum PNNI 1.0 Section 5.3.6"
        ::= { pnniRouteTnsEntry 10 }

pnniRouteTnsVPCapability OBJECT-TYPE
        SYNTAX        TruthValue
        MAX-ACCESS    read-create
        STATUS        current
        DESCRIPTION
            "Indicates whether VPCs can be established from the
             advertising node to the reachable transit network."
        REFERENCE
            "ATM Forum PNNI 1.0 Section 5.14.9.1 Table 5-34"
        ::= { pnniRouteTnsEntry 11 }

pnniRouteTnsMetricsTag OBJECT-TYPE
        SYNTAX        PnniMetricsTag
        MAX-ACCESS    read-create
        STATUS        current
        DESCRIPTION
            "The index into the pnniMetricsTable for the traffic
             parameter values that apply for the connectivity from the
             advertising node to the transit network.  There will be one
             or more entries in the pnniMetricsTable whose first
             instance identifier matches the value of this variable.

             If there are no parameters associated with this transit
             network then the distinguished value zero is used."
        DEFVAL { 0 }
        ::= { pnniRouteTnsEntry 12 }

pnniRouteTnsPtseId OBJECT-TYPE
        SYNTAX        Unsigned32
        MAX-ACCESS    read-only
        STATUS        current
        DESCRIPTION
            "For reachable transit networks learned via PNNI, this
             attribute contains the value of the PTSE Identifier for the
             PTSE being originated by the originating node which
             contains the information group(s) describing the transit
             network.  For reachable transit networks learned by means
             other than PNNI, this attribute is set to zero."
        REFERENCE
            "ATM Forum PNNI 1.0 Section 5.8.2"
        ::= { pnniRouteTnsEntry 13 }

pnniRouteTnsOriginateAdvertisement OBJECT-TYPE
        SYNTAX        TruthValue
        MAX-ACCESS    read-create
        STATUS        current
        DESCRIPTION
            "Whether or not the transit network specified by this entry
             is to be advertised by the local node into its PNNI routing
             domain.

             This object may only take on the value 'true' when the
             value of the corresponding instance of pnniRouteNodeProto
             is other than 'pnni'."
        DEFVAL { true }
        ::= { pnniRouteTnsEntry 14 }

pnniRouteTnsInfo OBJECT-TYPE
        SYNTAX        OBJECT IDENTIFIER
        MAX-ACCESS    read-create
        STATUS        current
        DESCRIPTION
            "A reference to MIB definitions specific to the particular
             routing protocol which is responsible for this transit
             network, as determined by the value specified in the
             route's pnniRouteTnsProto value.  If this information is
             not present, its value should be set to the OBJECT
             IDENTIFIER zeroDotZero."
        DEFVAL { zeroDotZero }
        ::= { pnniRouteTnsEntry 15 }

pnniRouteTnsOperStatus OBJECT-TYPE
        SYNTAX        INTEGER {
                                inactive(1),
                                active(2), -- i.e. reachability to this
                                        -- transit network exists and is
                                        -- not being advertised in PNNI
                                advertised(3)
                                }
        MAX-ACCESS    read-only
        STATUS        current
        DESCRIPTION
            "Indicates whether the reachable transit network is
             operationally valid and whether it is being advertised by
             this node."
        ::= { pnniRouteTnsEntry 16 }

pnniRouteTnsTimeStamp OBJECT-TYPE
        SYNTAX        TimeStamp
        MAX-ACCESS    read-only
        STATUS        current
        DESCRIPTION
            "Indicates how long the connectivity from the advertising
             node to the reachable transit network has been known to the
             local node."
        ::= { pnniRouteTnsEntry 17 }

pnniRouteTnsRowStatus OBJECT-TYPE
        SYNTAX        RowStatus
        MAX-ACCESS    read-create
        STATUS        current
        DESCRIPTION
            "To create, delete, activate and de-activate a reachable
             transit network."
        ::= { pnniRouteTnsEntry 18 }


-- conformance information

pnniMIBConformance
                   OBJECT IDENTIFIER ::= { pnniMIB 2 }
pnniMIBCompliances
                   OBJECT IDENTIFIER ::= { pnniMIBConformance 1 }
pnniMIBGroups
                   OBJECT IDENTIFIER ::= { pnniMIBConformance 2 }


-- compliance statements

pnniMIBCompliance MODULE-COMPLIANCE
        STATUS        current
        DESCRIPTION
            "The compliance statement for entities which implement
             the PNNI MIB.

             Groups of PNNI objects required for management of a minimum
             function node are identified by the suffix MinGroup.

             Groups of PNNI objects required for management of a border
             node are identified by the suffix BorderGroup.

             Groups of PNNI objects required for management of a PGL/LGN
             capable node are identified by the suffix LgnGroup.

             Groups of optional PNNI objects are identified by the
             suffix OptionalGroup."
        MODULE  -- this module
            MANDATORY-GROUPS { pnniGeneralMinGroup,
                               pnniNodeMinGroup,
                               pnniNodePglMinGroup,
                               pnniNodeTimerMinGroup,
                               pnniScopeMinGroup,
                               pnniIfMinGroup,
                               pnniLinkMinGroup,
                               pnniNbrPeerMinGroup,
                               pnniNbrPeerPortMinGroup }
        OBJECT pnniNodeId
        MIN-ACCESS read-only
        DESCRIPTION
            "Support for manual configuration of node IDs is optional."

        OBJECT pnniNodeLowest
        MIN-ACCESS read-only
        DESCRIPTION
            "Only switching systems that are PGL/LGN capable are allowed
             to provide write/create access to the pnniNodeLowest
             object."

        OBJECT pnniNodeRestrictedTransit
        MIN-ACCESS read-only
        DESCRIPTION
            "Support for the restricted transit capability is optional."

        OBJECT pnniNodeComplexRep
        MIN-ACCESS read-only
        DESCRIPTION
            "The ability to generate the complex node representation is
             only required for PGL/LGN capable switching systems, and is
             otherwise optional."

        OBJECT pnniNodeRowStatus
        SYNTAX INTEGER { active(1) }
        MIN-ACCESS read-only
        DESCRIPTION
            "The ability to create more than one node in a switching
             system is optional."

        OBJECT pnniNodePglLeadershipPriority
        MIN-ACCESS read-only
        DESCRIPTION
            "Only switching systems that are PGL/LGN capable are allowed
             to provide write/create access to the
             pnniNodePglLeadershipPriority object."

        OBJECT pnniIfNodeIndex
        MIN-ACCESS read-only
        DESCRIPTION
            "Write access to the pnniIfNodeIndex object is optional.  It
             only applies when there can be multiple lowest-level nodes
             in the switching system."

        OBJECT pnniIfVPCapability
        MIN-ACCESS read-only
        DESCRIPTION
            "The ability to support switched virtual paths is optional."

        ::= { pnniMIBCompliances 1 }

-- units of conformance

pnniGeneralMinGroup OBJECT-GROUP
        OBJECTS {
                  pnniHighestVersion,
                  pnniLowestVersion,
                  pnniDtlCountOriginator,
                  pnniCrankbackCountOriginator,
                  pnniAltRouteCountOriginator,
                  pnniRouteFailCountOriginator,
                  pnniRouteFailUnreachableOriginator
                  }
        STATUS current
        DESCRIPTION
            "A collection of general PNNI objects required for
             management of a minimum function switching system."
        ::= { pnniMIBGroups 1 }

pnniGeneralBorderGroup OBJECT-GROUP
        OBJECTS {
                  pnniDtlCountBorder,
                  pnniCrankbackCountBorder,
                  pnniAltRouteCountBorder,
                  pnniRouteFailCountBorder,
                  pnniRouteFailUnreachableBorder
                  }
        STATUS current
        DESCRIPTION
            "A collection of general PNNI objects required for
             management of a border node."
        ::= { pnniMIBGroups 2 }

pnniNodeMinGroup OBJECT-GROUP
        OBJECTS {
                  pnniNodeLevel,
                  pnniNodeId,
                  pnniNodeLowest,
                  pnniNodeAdminStatus,
                  pnniNodeOperStatus,
                  pnniNodeDomainName,
                  pnniNodeAtmAddress,
                  pnniNodePeerGroupId,
                  pnniNodeRestrictedTransit,
                  pnniNodeComplexRep,
                  pnniNodeRestrictedBranching,
                  pnniNodeDatabaseOverload,
                  pnniNodePtses,
                  pnniNodeRowStatus
                  }
        STATUS current
        DESCRIPTION
            "A collection of per node PNNI objects required for
             management of a minimum function switching system."
        ::= { pnniMIBGroups 3 }

pnniNodePglMinGroup OBJECT-GROUP
        OBJECTS {
                  pnniNodePglLeadershipPriority,
                  pnniNodePglInitTime,
                  pnniNodePglReelectTime ,
                  pnniNodePglState,
                  pnniNodePreferredPgl,
                  pnniNodePeerGroupLeader,
                  pnniNodePglTimeStamp,
                  pnniNodeActiveParentNodeId
                  }
        STATUS current
        DESCRIPTION
            "A collection of per node PGL election related PNNI objects
             required for management of a minimum function switching
             system."
        ::= { pnniMIBGroups 4 }

pnniNodePglLgnGroup OBJECT-GROUP
        OBJECTS {
                  pnniNodeCfgParentNodeIndex,
                  pnniNodePglOverrideDelay
                  }
        STATUS current
        DESCRIPTION
            "A collection of per node PGL election related PNNI objects
             required for management of a PGL/LGN capable switching
             system."
        ::= { pnniMIBGroups 5 }

pnniNodeTimerMinGroup OBJECT-GROUP
        OBJECTS {
                  pnniNodePtseHolddown,
                  pnniNodeHelloHolddown,
                  pnniNodeHelloInterval,
                  pnniNodeHelloInactivityFactor,
                  pnniNodePtseRefreshInterval,
                  pnniNodePtseLifetimeFactor,
                  pnniNodeRxmtInterval,
                  pnniNodePeerDelayedAckInterval,
                  pnniNodeAvcrPm,
                  pnniNodeAvcrMt,
                  pnniNodeCdvPm,
                  pnniNodeCtdPm
                  }
        STATUS current
        DESCRIPTION
            "A collection of per node PNNI objects required for
             management of timers and significant change thresholds in a
             minimum function switching system."
        ::= { pnniMIBGroups 6 }

pnniNodeTimerLgnGroup OBJECT-GROUP
        OBJECTS {
                  pnniNodeHlinkInact
                  }
        STATUS current
        DESCRIPTION
            "A collection of per node PNNI objects required for
             management of timers in a PGL/LGN capable switching
             system."
        ::= { pnniMIBGroups 7 }


pnniNodeSvccLgnGroup OBJECT-GROUP
        OBJECTS {
                  pnniNodeSvccInitTime,
                  pnniNodeSvccRetryTime,
                  pnniNodeSvccCallingIntegrityTime,
                  pnniNodeSvccCalledIntegrityTime,
                  pnniNodeSvccTrafficDescriptorIndex
                  }
        STATUS current
        DESCRIPTION
            "A collection of per node SVCC-based RCC related PNNI
             objects required for management of a PGL/LGN capable
             switching system."
        ::= { pnniMIBGroups 8 }

pnniScopeMinGroup OBJECT-GROUP
        OBJECTS {
                  pnniScopeLocalNetwork,
                  pnniScopeLocalNetworkPlusOne,
                  pnniScopeLocalNetworkPlusTwo,
                  pnniScopeSiteMinusOne,
                  pnniScopeIntraSite,
                  pnniScopeSitePlusOne,
                  pnniScopeOrganizationMinusOne,
                  pnniScopeIntraOrganization,
                  pnniScopeOrganizationPlusOne,
                  pnniScopeCommunityMinusOne,
                  pnniScopeIntraCommunity,
                  pnniScopeCommunityPlusOne,
                  pnniScopeRegional,
                  pnniScopeInterRegional,
                  pnniScopeGlobal
                  }
        STATUS current
        DESCRIPTION
            "A collection of per node scope mapping related PNNI objects
             required for management of a minimum function switching
             system."
        ::= { pnniMIBGroups 9 }

pnniSummaryLgnGroup OBJECT-GROUP
        OBJECTS {
                  pnniSummaryType,
                  pnniSummarySuppress,
                  pnniSummaryState,
                  pnniSummaryRowStatus
                  }
        STATUS deprecated
        DESCRIPTION
            "A collection of PNNI objects required for controlling
             address summarization."
        ::= { pnniMIBGroups 10 }

pnniSummaryAddressLgnGroup OBJECT-GROUP
       OBJECTS {
	pnniSummaryAddressSuppress,
	pnniSummaryAddressState,
	pnniSummaryAddressRowStatus
	}
        STATUS current
        DESCRIPTION
	    "A collection of PNNI objects required for controlling address 
            summarization."
        ::= { pnniMIBGroups 31 }

pnniIfMinGroup OBJECT-GROUP
        OBJECTS {
                  pnniIfNodeIndex,
                  pnniIfPortId,
                  pnniIfVPCapability,
                  pnniIfAdmWeightCbr,
                  pnniIfAdmWeightRtVbr,
                  pnniIfAdmWeightNrtVbr,
                  pnniIfAdmWeightAbr,
                  pnniIfAdmWeightUbr,
                  pnniIfRccServiceCategory,
                  pnniIfRccTrafficDescrIndex
                  }
        STATUS current
        DESCRIPTION
            "A collection of per interface PNNI objects required for
             management of a minimum function switching system."
        ::= { pnniMIBGroups 11 }

pnniIfBorderGroup OBJECT-GROUP
        OBJECTS {
                  pnniIfAggrToken
                  }
        STATUS current
        DESCRIPTION
            "A collection of per interface PNNI objects required for
             management of a border node."
        ::= { pnniMIBGroups 12 }

pnniLinkMinGroup OBJECT-GROUP
        OBJECTS {
                  pnniLinkType,
                  pnniLinkVersion,
                  pnniLinkHelloState,
                  pnniLinkRemoteNodeId,
                  pnniLinkRemotePortId,
                  pnniLinkIfIndex,
                  pnniLinkRcvHellos,
                  pnniLinkXmtHellos
                  }
        STATUS current
        DESCRIPTION
            "A collection of per link PNNI objects required for
             management of a minimum function switching system."
        ::= { pnniMIBGroups 13 }

pnniLinkBorderOrLgnGroup OBJECT-GROUP
        OBJECTS {
                  pnniLinkDerivedAggrToken,
                  pnniLinkUpnodeId,
                  pnniLinkUpnodeAtmAddress,
                  pnniLinkCommonPeerGroupId
                  }
        STATUS current
        DESCRIPTION
            "A collection of per link PNNI objects required for
             management of a border node or a PGL/LGN capable switching
             system."
        ::= { pnniMIBGroups 14 }

pnniLinkLgnGroup OBJECT-GROUP
        OBJECTS {
                  pnniLinkSvccRccIndex
                  }
        STATUS current
        DESCRIPTION
            "A collection of per link PNNI objects required for
             management of a PGL/LGN capable switching system."
        ::= { pnniMIBGroups 15 }

pnniNbrPeerMinGroup OBJECT-GROUP
        OBJECTS {
                  pnniNbrPeerState,
                  pnniNbrPeerPortCount,
                  pnniNbrPeerRcvDbSums,
                  pnniNbrPeerXmtDbSums,
                  pnniNbrPeerRcvPtsps,
                  pnniNbrPeerXmtPtsps,
                  pnniNbrPeerRcvPtseReqs,
                  pnniNbrPeerXmtPtseReqs,
                  pnniNbrPeerRcvPtseAcks,
                  pnniNbrPeerXmtPtseAcks
                  }
        STATUS current
        DESCRIPTION
            "A collection of per neighboring peer PNNI objects required
             for management of a minimum function switching system."
        ::= { pnniMIBGroups 16 }

pnniNbrPeerLgnGroup OBJECT-GROUP
        OBJECTS {
                  pnniNbrPeerSvccRccIndex
                  }
        STATUS current
        DESCRIPTION
            "A collection of per neighboring peer PNNI objects required
             for management of a PGL/LGN capable switching system."
        ::= { pnniMIBGroups 17 }

pnniNbrPeerPortMinGroup OBJECT-GROUP
        OBJECTS {
                  pnniNbrPeerPortFloodStatus
                   }
        STATUS current
        DESCRIPTION
            "A collection of per port to neighboring peer PNNI objects
             required for management of a minimum function switching
             system."
        ::= { pnniMIBGroups 18 }

pnniSvccRccLgnGroup OBJECT-GROUP
        OBJECTS {
                  pnniSvccRccVersion,
                  pnniSvccRccHelloState,
                  pnniSvccRccRemoteNodeId ,
                  pnniSvccRccRemoteAtmAddress,
                  pnniSvccRccRcvHellos,
                  pnniSvccRccXmtHellos,
                  pnniSvccRccIfIndex,
                  pnniSvccRccVpi,
                  pnniSvccRccVci
                  }
        STATUS current
        DESCRIPTION
            "A collection of per SVCC-based RCC PNNI objects required
             for management of a PGL/LGN capable switching system."
        ::= { pnniMIBGroups 19 }

pnniPtseOptionalGroup OBJECT-GROUP
        OBJECTS {
                  pnniPtseType,
                  pnniPtseSequenceNum,
                  pnniPtseChecksum,
                  pnniPtseLifeTime,
                  pnniPtseInfo
                  }
        STATUS current
        DESCRIPTION
            "A collection of optional per PTSE PNNI objects."
        ::= { pnniMIBGroups 20 }


pnniMapOptionalGroup OBJECT-GROUP
        OBJECTS {
                  pnniMapType,
                  pnniMapPeerGroupId,
                  pnniMapAggrToken,
                  pnniMapRemoteNodeId,
                  pnniMapRemotePortId,
                  pnniMapVPCapability,
                  pnniMapPtseId,
                  pnniMapMetricsTag
                  }
        STATUS current
        DESCRIPTION
            "A collection of optional PNNI objects used to create a map
             of nodes and links in the PNNI routing domain."
        ::= { pnniMIBGroups 21 }

pnniMapNodeOptionalGroup OBJECT-GROUP
        OBJECTS {
                  pnniMapNodePeerGroupId,
                  pnniMapNodeAtmAddress,
                  pnniMapNodeRestrictedTransit,
                  pnniMapNodeComplexRep,
                  pnniMapNodeRestrictedBranching,
                  pnniMapNodeDatabaseOverload,
                  pnniMapNodeIAmLeader,
                  pnniMapNodeLeadershipPriority,
                  pnniMapNodePreferredPgl,
                  pnniMapNodeParentNodeId,
                  pnniMapNodeParentAtmAddress,
                  pnniMapNodeParentPeerGroupId,
                  pnniMapNodeParentPglNodeId
                 }
        STATUS current
        DESCRIPTION
            "A collection of optional PNNI objects used to create a map
             of nodes in the PNNI routing domain."
        ::= { pnniMIBGroups 22 }

pnniMapAddrOptionalGroup OBJECT-GROUP
        OBJECTS {
                  pnniMapAddrAddress,
                  pnniMapAddrPrefixLength
                  }
        STATUS current
        DESCRIPTION
            "A collection of optional PNNI objects used to create a map
             of reachable addresses in the PNNI routing domain."
        ::= { pnniMIBGroups 23 }

pnniMapTnsOptionalGroup OBJECT-GROUP
        OBJECTS {
                  pnniMapTnsId
                  }
        STATUS current
        DESCRIPTION
            "A collection of optional PNNI objects used to create a map
             of reachable transit networks in the PNNI routing domain."
        ::= { pnniMIBGroups 24 }

pnniMetricsOptionalGroup OBJECT-GROUP
        OBJECTS {
                  pnniMetricsClasses,
                  pnniMetricsGcacClp,
                  pnniMetricsAdminWeight,
                  pnniMetrics1,
                  pnniMetrics2,
                  pnniMetrics3,
                  pnniMetrics4,
                  pnniMetrics5,
                  pnniMetrics6,
                  pnniMetrics7,
                  pnniMetrics8,
                  pnniMetricsRowStatus
                  }
        STATUS current
        DESCRIPTION
            "A collection of optional PNNI objects used to manage
             metrics and attributes associated with PNNI entities."
        ::= { pnniMIBGroups 25 }

pnniRouteGeneralOptionalGroup OBJECT-GROUP
        OBJECTS {
                  pnniRouteNodeNumber,
                  pnniRouteAddrNumber
                  }
        STATUS current
        DESCRIPTION
            "A collection of optional PNNI objects."
        ::= { pnniMIBGroups 26 }

pnniRouteNodeOptionalGroup OBJECT-GROUP
        OBJECTS {
                  pnniRouteNodeDestPortId,
                  pnniRouteNodeProto,
                  pnniRouteNodeTimeStamp,
                  pnniRouteNodeInfo,
                  pnniRouteNodeGcacClp,
                  pnniRouteNodeFwdMetricAW,
                  pnniRouteNodeFwdMetric1,
                  pnniRouteNodeFwdMetric2,
                  pnniRouteNodeFwdMetric3,
                  pnniRouteNodeFwdMetric4,
                  pnniRouteNodeFwdMetric5,
                  pnniRouteNodeFwdMetric6,
                  pnniRouteNodeFwdMetric7,
                  pnniRouteNodeFwdMetric8,
                  pnniRouteNodeBwdMetricAW,
                  pnniRouteNodeBwdMetric1,
                  pnniRouteNodeBwdMetric2,
                  pnniRouteNodeBwdMetric3,
                  pnniRouteNodeBwdMetric4,
                  pnniRouteNodeBwdMetric5,
                  pnniRouteNodeBwdMetric6,
                  pnniRouteNodeBwdMetric7,
                  pnniRouteNodeBwdMetric8,
                  pnniRouteNodeVPCapability,
                  pnniRouteNodeStatus
                  }
        STATUS current
        DESCRIPTION
            "A collection of optional PNNI objects used to manage
             precalculated routes to nodes in the PNNI routing domain."
        ::= { pnniMIBGroups 27 }

pnniDTLOptionalGroup OBJECT-GROUP
        OBJECTS {
                  pnniDTLNodeId,
                  pnniDTLPortId,
                  pnniDTLLinkType,
                  pnniDTLStatus
                  }
        STATUS current
        DESCRIPTION
            "A collection of optional PNNI objects used to manage
             precalculated routes to nodes in the PNNI routing domain."
        ::= { pnniMIBGroups 28 }

pnniRouteAddrOptionalGroup OBJECT-GROUP
        OBJECTS {
                  pnniRouteAddrIfIndex,
                  pnniRouteAddrAdvertisingNodeId,
                  pnniRouteAddrAdvertisedPortId,
                  pnniRouteAddrType,
                  pnniRouteAddrProto,
                  pnniRouteAddrPnniScope,
                  pnniRouteAddrVPCapability,
                  pnniRouteAddrMetricsTag,
                  pnniRouteAddrPtseId,
                  pnniRouteAddrOriginateAdvertisement,
                  pnniRouteAddrInfo,
                  pnniRouteAddrOperStatus,
                  pnniRouteAddrTimeStamp,
                  pnniRouteAddrRowStatus
                  }
        STATUS current
        DESCRIPTION
            "A collection of optional PNNI objects used to manage routes
             to reachable addresses in the PNNI routing domain."
        ::= { pnniMIBGroups 29 }

pnniRouteTnsOptionalGroup OBJECT-GROUP
        OBJECTS {
                  pnniRouteTnsIfIndex,
                  pnniRouteTnsAdvertisingNodeId,
                  pnniRouteTnsAdvertisedPortId,
                  pnniRouteTnsRouteType,
                  pnniRouteTnsProto,
                  pnniRouteTnsPnniScope,
                  pnniRouteTnsVPCapability,
                  pnniRouteTnsMetricsTag,
                  pnniRouteTnsPtseId,
                  pnniRouteTnsOriginateAdvertisement,
                  pnniRouteTnsInfo,
                  pnniRouteTnsOperStatus,
                  pnniRouteTnsTimeStamp,
                  pnniRouteTnsRowStatus
                  }
        STATUS current
        DESCRIPTION
            "A collection of optional PNNI objects used to manage routes
             to reachable transit networks in the PNNI routing domain."
        ::= { pnniMIBGroups 30 }


END
