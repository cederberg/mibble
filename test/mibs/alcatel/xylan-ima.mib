XYLAN-IMA-MIB DEFINITIONS ::= BEGIN

     --  RCSID information

     --  $RCSfile: xylan-ima.mib,v $
     --  $Revision: 1.2 $		$State: Exp $
     --  $Date: 1998/11/24 05:59:41 $
     --  $Author: ktran $

     --  xylan-ima.mib
     --  Revision: 1.00
     --  Date: September 30, 1998

     --  Alcatel Internetworking, Inc.
     --  26801 W. Agoura Road
     --  Calabasas, CA 91301
     --  (818) 880-3500
     --  support@ind.alcatel.com

     --  This module provides authoritative definitions for Alcatel Internetworking, Inc.
     --  enterprise-specific physical port parameters MIB.

     --  This module will be extended, as needed.


     --  Alcatel Internetworking, Inc. reserves the right to make changes in 
     --  specification and other information contained in this document 
     --  without prior notice.  The reader should consult Alcatel Internetworking,
     --  Inc. to determine whether any such changes have been made.

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1998, Alcatel Internetworking, Inc. All Rights Reserved.
     
     	IMPORTS
		Counter, TimeTicks
	         	FROM RFC1155-SMI
		OBJECT-TYPE
			FROM RFC-1212
		DisplayString 
			FROM RFC1213-MIB
	        xylanPportArch
			FROM XYLAN-BASE-MIB 
			;
	
        xylanImaMib   OBJECT IDENTIFIER ::= { xylanPportArch 3 }

    --  IMA Link Table

	 xylanImaLinkTable  OBJECT-TYPE
	    SYNTAX   SEQUENCE OF XylanImaLinkEntry
            ACCESS   not-accessible
            STATUS   mandatory
            DESCRIPTION
            	   "A table of IMA link status and configuration information."
            ::= { xylanImaMib 1 }

         xylanImaLinkEntry  OBJECT-TYPE
	    SYNTAX   XylanImaLinkEntry
            ACCESS   not-accessible
            STATUS   mandatory
            DESCRIPTION
                   "An entry in the table containing information about 
                    the IMA Link."
            INDEX   { xylanImaLinkSlotIndex, xylanImaLinkPortIndex }
            ::= { xylanImaLinkTable 1 }

	 XylanImaLinkEntry ::=
             SEQUENCE {
	         xylanImaLinkSlotIndex
                     INTEGER,
		 xylanImaLinkPortIndex
                     INTEGER,
		 xylanImaLinkDescription
		     DisplayString,
	         xylanImaLinkAdminStatus
	             INTEGER,
	         xylanImaLinkIfIndex
		     INTEGER,
	         xylanImaLinkRxIcpCells
	             INTEGER,
	         xylanImaLinkTxIcpCells
	             INTEGER,
	         xylanImaLinkRxFillerCells
	             INTEGER,
		 xylanImaLinkTxFillerCells
	             INTEGER,
	         xylanImaLinkRxAtmLayerCells
	             INTEGER,
	         xylanImaLinkTxAtmLayerCells
	             INTEGER,
	         xylanImaLinkRxBadIcpCells
		     INTEGER,
                 xylanImaLinkRxBadCrcIcpCells
	             INTEGER,
	         xylanImaLinkCellsInRxBuffer
		     INTEGER,
	         xylanImaLinkRxBufferFlush
	             INTEGER,
	         xylanImaLinkRxBufferOverflow
		     INTEGER,
		 xylanImaLinkRxCellDiscarded
		     INTEGER,
		 xylanImaLinkRxStuffEvents
		     INTEGER,
		 xylanImaLinkTxStuffEvents
		     INTEGER,
                 xylanImaLinkClearStatistics 
                     INTEGER
             }

         xylanImaLinkSlotIndex  OBJECT-TYPE
             SYNTAX   INTEGER (1..9)
             ACCESS   read-only
             STATUS   mandatory
             DESCRIPTION
                    "A unique value which identifies this slot."
             ::= { xylanImaLinkEntry 1 }

         xylanImaLinkPortIndex   OBJECT-TYPE
             SYNTAX   INTEGER (1..32)
             ACCESS   read-only
             STATUS   mandatory
             DESCRIPTION
                    "A unique value which identifies this port."
             ::= { xylanImaLinkEntry 2 }

         xylanImaLinkDescription   OBJECT-TYPE
             SYNTAX   DisplayString (SIZE (0..31))
             ACCESS   read-write
             STATUS   mandatory
             DESCRIPTION
                "A description for this link."
             ::= { xylanImaLinkEntry 3 }
             
          xylanImaLinkAdminStatus OBJECT-TYPE
               SYNTAX   INTEGER  {
		     up(1),
                     down(2)
	        }
               ACCESS  read-write
               STATUS  mandatory
               DESCRIPTION
                "The desired state of this link."
               ::= { xylanImaLinkEntry 4 }

          xylanImaLinkIfIndex OBJECT-TYPE
               SYNTAX   INTEGER
               ACCESS  read-only
               STATUS  mandatory
               DESCRIPTION
                  "This indicates the ifIndex of this link."
               ::= { xylanImaLinkEntry 5 }

          xylanImaLinkRxIcpCells OBJECT-TYPE
               SYNTAX   INTEGER
               ACCESS  read-only
               STATUS  mandatory
               DESCRIPTION
                  "This object indicates number of good ICP cells have 
	           been received on this link."
               ::= { xylanImaLinkEntry 6 }

          xylanImaLinkTxIcpCells OBJECT-TYPE
               SYNTAX  INTEGER
               ACCESS  read-only
               STATUS  mandatory
               DESCRIPTION
                  "This object indicates number of good ICP cells have 
	           been transmitted on this link."
               ::= { xylanImaLinkEntry 7 }

          xylanImaLinkRxFillerCells OBJECT-TYPE
               SYNTAX  INTEGER
               ACCESS  read-only
               STATUS  mandatory
               DESCRIPTION
                  "This object indicates number of good filler cells have 
	           been received on this link."
               ::= { xylanImaLinkEntry 8 }

          xylanImaLinkTxFillerCells OBJECT-TYPE
               SYNTAX  INTEGER
               ACCESS  read-only
               STATUS  mandatory
               DESCRIPTION
                  "This object indicates number of good filler cells have 
	           been transmitted on this link."
               ::= { xylanImaLinkEntry 9 }

          xylanImaLinkRxAtmLayerCells OBJECT-TYPE
               SYNTAX  INTEGER
               ACCESS  read-only
               STATUS  mandatory
               DESCRIPTION
                  "This object indicates number of ATM layer cells have 
	           been received on this link."
               ::= { xylanImaLinkEntry 10 }

          xylanImaLinkTxAtmLayerCells OBJECT-TYPE
               SYNTAX  INTEGER
               ACCESS  read-only
               STATUS  mandatory
               DESCRIPTION
                  "This object indicates number of ATM layer cells have 
	           been transmitted on this link."
               ::= { xylanImaLinkEntry 11 }

          xylanImaLinkRxBadIcpCells OBJECT-TYPE
               SYNTAX  INTEGER
               ACCESS  read-only
               STATUS  mandatory
               DESCRIPTION
                  "This object indicates number of invalid ICP cells 
	           have been received on this link."
               ::= { xylanImaLinkEntry 12 }

          xylanImaLinkRxBadCrcIcpCells OBJECT-TYPE
               SYNTAX  INTEGER
               ACCESS  read-only
               STATUS  mandatory
               DESCRIPTION
                  "This object indicates number of ICP cells with bad CRC-10
	           have been received on this link."
               ::= { xylanImaLinkEntry 13 }

          xylanImaLinkCellsInRxBuffer OBJECT-TYPE
               SYNTAX  INTEGER
               ACCESS  read-only
               STATUS  mandatory
               DESCRIPTION
                  "This object indicates number of cells that are currently
	           in receive buffer on this link."
               ::= { xylanImaLinkEntry 14 }

          xylanImaLinkRxBufferFlush OBJECT-TYPE
               SYNTAX  INTEGER
               ACCESS  read-only
               STATUS  mandatory
               DESCRIPTION
                  "This object indicates number of times that receive buffer
	           is flushed on this link."
               ::= { xylanImaLinkEntry 15 }

          xylanImaLinkRxBufferOverflow OBJECT-TYPE
               SYNTAX  INTEGER
               ACCESS  read-only
               STATUS  mandatory
               DESCRIPTION
                  "This object indicates number of times that receive buffer
	           is overflowed on this link."
               ::= { xylanImaLinkEntry 16 }

          xylanImaLinkRxCellDiscarded OBJECT-TYPE
               SYNTAX  INTEGER
               ACCESS  read-only
               STATUS  mandatory
               DESCRIPTION
                  "This object indicates number of receive cells that have
		   been discarded on this link."
               ::= { xylanImaLinkEntry 17 }

          xylanImaLinkRxStuffEvents OBJECT-TYPE
               SYNTAX  INTEGER
               ACCESS  read-only
               STATUS  mandatory
               DESCRIPTION
                  "This object indicates number of stuff events that have
		   been received on this link."
               ::= { xylanImaLinkEntry 18 }

          xylanImaLinkTxStuffEvents OBJECT-TYPE
               SYNTAX  INTEGER
               ACCESS  read-only
               STATUS  mandatory
               DESCRIPTION
                  "This object indicates number of stuff events that have
		   been transmitted on this link."
               ::= { xylanImaLinkEntry 19 }

          xylanImaLinkClearStatistics OBJECT-TYPE
               SYNTAX  INTEGER {
	                noAction(1),
	                clear(2)
                     }
               ACCESS  read-write
               STATUS  mandatory
               DESCRIPTION
                  "Setting this object to clear(2) will clear all statistics of
	           this link to zero's."
               ::= { xylanImaLinkEntry 20 }

    --  IMA Group Table

	 xylanImaGroupTable  OBJECT-TYPE
	    SYNTAX   SEQUENCE OF XylanImaGroupEntry
            ACCESS   not-accessible
            STATUS   mandatory
            DESCRIPTION
            	   "A table of IMA Group status and configuration information."
            ::= { xylanImaMib 2 }

         xylanImaGroupEntry  OBJECT-TYPE
	    SYNTAX   XylanImaGroupEntry
            ACCESS   not-accessible
            STATUS   mandatory
            DESCRIPTION
                   "An entry in the table containing information about 
                    the IMA Group."
            INDEX   { xylanImaGroupIndex }
            ::= { xylanImaGroupTable 1 }

	 XylanImaGroupEntry ::=
             SEQUENCE {
	         xylanImaGroupIndex
                     INTEGER,
		 xylanImaGroupDescription
		     DisplayString,
	         xylanImaGroupAdminStatus
	             INTEGER,
		 xylanImaGroupMaxDelaySlot
		     INTEGER,
		 xylanImaGroupMaxDelayPort
		     INTEGER,
		 xylanImaGroupAtmLayerSlot
		     INTEGER,
		 xylanImaGroupAtmLayerPort
		     INTEGER,
		 xylanImaGroupRxAtmLayerCells
		     INTEGER,
		 xylanImaGroupTxAtmLayerCells
		     INTEGER,
                 xylanImaGroupPhyFrameFormat
                     INTEGER,
                 xylanImaGroupPhyLoopbackMode
                     INTEGER,
                 xylanImaGroupPhyLineLength
                     INTEGER,
                 xylanImaGroupPhyTxClkSource
                     INTEGER,
		 xylanImaGroupClearStatistics
		     INTEGER,
		 xylanImaGroupPhyUniqueParameter
		     INTEGER
	   }

	xylanImaGroupIndex OBJECT-TYPE
	     SYNTAX   INTEGER 
             ACCESS   read-only
             STATUS   mandatory
             DESCRIPTION
                    "A unique value which identifies this group."
             ::= { xylanImaGroupEntry 1 }

	xylanImaGroupDescription OBJECT-TYPE
	     SYNTAX   DisplayString(SIZE (0..31))
             ACCESS   read-write
             STATUS   mandatory
             DESCRIPTION
                    "A string description of this IMA group."
             ::= { xylanImaGroupEntry 2 }

        xylanImaGroupAdminStatus OBJECT-TYPE
               SYNTAX  INTEGER  {
		     up(1),
                     down(2)
	        }
               ACCESS  read-write
               STATUS  mandatory
               DESCRIPTION
                "The desired state of this group."
               ::= { xylanImaGroupEntry 3 }

	xylanImaGroupMaxDelaySlot OBJECT-TYPE
	     SYNTAX   INTEGER (1..9)
             ACCESS   read-only
             STATUS   mandatory
             DESCRIPTION
                    "A unique value which identifies slot where the link
		     experiences with maximum differential delay within
	             this IMA group."
             ::= { xylanImaGroupEntry 4 }

	xylanImaGroupMaxDelayPort OBJECT-TYPE
	     SYNTAX   INTEGER (1..32)
             ACCESS   read-only
             STATUS   mandatory
             DESCRIPTION
                    "A unique value which identifies port where the link
		     experiences with maximum differential delay within
	             this IMA group."
             ::= { xylanImaGroupEntry 5 }

	xylanImaGroupAtmLayerSlot OBJECT-TYPE
	     SYNTAX   INTEGER (1..9)
             ACCESS   read-write
             STATUS   mandatory
             DESCRIPTION
                    "A unique value which identifies slot of an ATM layer port
	             where this IMA group is mapped to."
             ::= { xylanImaGroupEntry 6 }

	xylanImaGroupAtmLayerPort OBJECT-TYPE
	     SYNTAX   INTEGER (1..32)
             ACCESS   read-write
             STATUS   mandatory
             DESCRIPTION
                    "A unique value which identifies port of an ATM layer port
	             where this IMA group is mapped to."
             ::= { xylanImaGroupEntry 7 }

          xylanImaGroupRxAtmLayerCells OBJECT-TYPE
               SYNTAX  INTEGER
               ACCESS  read-only
               STATUS  mandatory
               DESCRIPTION
                  "This object indicates number of ATM layer cells have 
	           been received on this group."
               ::= { xylanImaGroupEntry 8 }

          xylanImaGroupTxAtmLayerCells OBJECT-TYPE
               SYNTAX  INTEGER
               ACCESS  read-only
               STATUS  mandatory
               DESCRIPTION
                  "This object indicates number of ATM layer cells have 
	           been transmitted on this group."
               ::= { xylanImaGroupEntry 9 }

          xylanImaGroupPhyFrameFormat OBJECT-TYPE
               SYNTAX  INTEGER {
                         other(1),
                         esf(2),
                         sf(3),
                         e1(4),
                         e1-crc(5)
                       }
               ACCESS  read-write
               STATUS  mandatory
               DESCRIPTION
                  "This object indicates frame format of all physical
                   links assigned to this group."
               ::= { xylanImaGroupEntry 10 }

          xylanImaGroupPhyLoopbackMode OBJECT-TYPE
               SYNTAX  INTEGER {
                         none(1),
                         payloop(2),
                         line(3),
                         other(4),
                         inward(5)
                      }
               ACCESS  read-write
               STATUS  mandatory
               DESCRIPTION
                  "This object indicates loopback configuration of all physical
                   links assigned to this group."
               ::= { xylanImaGroupEntry 11 }

          xylanImaGroupPhyLineLength OBJECT-TYPE
               SYNTAX  INTEGER (0..64000)
               ACCESS  read-write
               STATUS  mandatory
               DESCRIPTION
                  "This object indicates line length of all physical
                   links assigned to this group."
               ::= { xylanImaGroupEntry 12 }

          xylanImaGroupPhyTxClkSource OBJECT-TYPE
               SYNTAX  INTEGER {
                        loopTiming(1),
                        localTiming(2)
                      }
               ACCESS  read-write
               STATUS  mandatory
               DESCRIPTION
                  "This object indicates transmit clock source of all physical
                   links assigned to this group."
               ::= { xylanImaGroupEntry 13 }

          xylanImaGroupClearStatistics OBJECT-TYPE
               SYNTAX  INTEGER {
	                noAction(1),
	                clear(2)
                     }
               ACCESS  read-write
               STATUS  mandatory
               DESCRIPTION
                  "Setting this object to clear(2) will clear all statistics of
	           this group to zero's."
               ::= { xylanImaGroupEntry 14 }

          xylanImaGroupPhyUniqueParameter OBJECT-TYPE
               SYNTAX  INTEGER {
	                yes(1),
	                no(2)
                     }
               ACCESS  read-write
               STATUS  mandatory
               DESCRIPTION
                  "Whenever a PHY configuration (xylanImaGroupPhyTxClkSource,
                   xylanImaGroupPhyLineLength, xylanImaGroupPhyLoopbackMode,
                   xylanImaGroupPhyFrameFormat) is changed, and this
                   this object is set to yes(1), the new PHY configuration
                   will be applied to all physical ports (T1/E1) in the group."
               ::= { xylanImaGroupEntry 15 }
   END
