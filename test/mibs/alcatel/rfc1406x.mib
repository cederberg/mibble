RFC1406-MIB DEFINITIONS ::= BEGIN
     IMPORTS
             Gauge, TimeTicks
                     FROM RFC1155-SMI
             transmission, DisplayString
                     FROM RFC1213-MIB
             TRAP-TYPE
                     FROM RFC-1215
             OBJECT-TYPE
                     FROM RFC-1212;

     --  This MIB module uses the extended OBJECT-TYPE macro as
     --  defined in RFC 1212.

     --  this is the MIB module for the DS1 objects

     ds1 OBJECT IDENTIFIER ::= { transmission 18 }

     -- note that this subsumes cept (19); there is no separate CEPT MIB


     -- The DS1 Near End Group

     -- Implementation of this group is mandatory for all systems
     -- that attach to a DS1 Interface.

     -- The DS1 Near End Group consists of four tables:
     --    DS1 Configuration
     --    DS1 Current
     --    DS1 Interval
     --    DS1 Total

     -- the DS1 Configuration Table

         dsx1ConfigTable OBJECT-TYPE
             SYNTAX  SEQUENCE OF Dsx1ConfigEntry
             ACCESS  not-accessible
             STATUS  mandatory
             DESCRIPTION
                "The DS1 Configuration table."
            ::= { ds1 6 }


         dsx1ConfigEntry OBJECT-TYPE
             SYNTAX  Dsx1ConfigEntry
             ACCESS  not-accessible
             STATUS  mandatory
             DESCRIPTION
                "An entry in the DS1 Configuration table."
            INDEX   { dsx1LineIndex }
            ::= { dsx1ConfigTable 1 }

     Dsx1ConfigEntry ::=
         SEQUENCE {
             dsx1LineIndex
                 INTEGER,
             dsx1IfIndex
                 INTEGER,
             dsx1TimeElapsed
                 INTEGER,
             dsx1ValidIntervals
                 INTEGER,
             dsx1LineType
                 INTEGER,
             dsx1LineCoding
                 INTEGER,
             dsx1SendCode
                 INTEGER,
             dsx1CircuitIdentifier
                 DisplayString,
             dsx1LoopbackConfig
                 INTEGER,
             dsx1LineStatus
                 INTEGER,
             dsx1SignalMode
                 INTEGER,
             dsx1TransmitClockSource
                 INTEGER,
             dsx1Fdl
                 INTEGER,
             dsx1InvalidIntervals            
	         INTEGER,
             dsx1LineLength
	         INTEGER,
             dsx1LineStatusLastChange
                 TimeTicks,
             dsx1LineStatusChangeTrapEnable
	         INTEGER,
             dsx1LoopbackStatus
	         INTEGER
         }

         dsx1LineIndex OBJECT-TYPE
             SYNTAX  INTEGER (1..'7fffffff'h)
             ACCESS  read-only
             STATUS  mandatory
             DESCRIPTION
                "This object is the identifier of a DS1  Inter-
                face on a managed device.  If there is an ifEn-
                try that is directly associated with  this  and
                only  this  DS1  interface,  it should have the
                same value as ifIndex.   Otherwise,  the  value
                exceeds  ifNumber,  and  is a unique identifier
                following this rule: inside  interfaces  (e.g.,
                equipment  side)  with even numbers and outside
                interfaces  (e.g.,  network   side)   with   odd
                numbers."
            ::= { dsx1ConfigEntry 1 }


         dsx1IfIndex OBJECT-TYPE
             SYNTAX  INTEGER (1..'7fffffff'h)
             ACCESS  read-only
             STATUS  mandatory
             DESCRIPTION
                "This value for this object  is  equal  to  the
                value  of  ifIndex from the Interfaces table of
                MIB II (RFC 1213)."
            ::= { dsx1ConfigEntry 2 }


         dsx1TimeElapsed OBJECT-TYPE
             SYNTAX  INTEGER (0..899)
             ACCESS  read-only
             STATUS  mandatory
             DESCRIPTION
                "The number of seconds that have elapsed  since
                the  beginning of the current error-measurement
                period."
            ::= { dsx1ConfigEntry 3 }


         dsx1ValidIntervals OBJECT-TYPE
             SYNTAX  INTEGER (0..96)
             ACCESS  read-only
             STATUS  mandatory
             DESCRIPTION
                "The number of  previous  intervals  for  which
                valid data was collected.  The value will be 96
                unless the interface was brought on-line within
                the last 24 hours, in which case the value will
                be the number of complete 15  minute  intervals
                the since interface has been online."
            ::= { dsx1ConfigEntry 4 }


         dsx1LineType OBJECT-TYPE
             SYNTAX  INTEGER {
                         other(1),
                         dsx1ESF(2),
                         dsx1D4(3),
                         dsx1E1(4),
                         dsx1E1-CRC(5),
                         dsx1E1-MF(6),
                         dsx1E1-CRC-MF(7),
                         dsx1Unframed(8),
                         dsx1E1Unframed(9)
                     }
	       ACCESS  read-write
               STATUS  mandatory
               DESCRIPTION
                      "This variable indicates  the  variety  of  DS1
                      Line  implementing  this  circuit.  The type of
                      circuit affects the number of bits  per  second
                      that  the circuit can reasonably carry, as well
                      as the interpretation of the  usage  and  error
                      statistics.  The values, in sequence, describe:

                      TITLE:         SPECIFICATION:
                      dsx1ESF         Extended SuperFrame DS1
                      dsx1D4          AT&T D4 format DS1
                      dsx1E1          CCITT Recommendation G.704
                                       (Table 4a)
                      dsx1E1-CRC      CCITT Recommendation G.704
                                       (Table 4b)
                      dsxE1-MF        G.704 (Table 4a) with TS16
                                       multiframing enabled
                      dsx1E1-CRC-MF   G.704 (Table 4b) with TS16
                                       multiframing enabled
                      dsx1Unframed    No Framing performed
                      dsx1E1Unframed  E1 with No Framing
                      For clarification, the capacity for each E1 type
                      is as listed below:
                      dsx1E1Unframed - E1, no framing = 32 x 64k = 2048k
                      dsx1E1 or dsx1E1CRC - E1, with framing,
                         no signalling = 31 x 64k = 1984k
                      dsx1E1MF or dsx1E1CRCMF - E1, with framing,
                         signalling = 30 x 64k = 1920k

                      For further information See CCITT Recomm G.704"
                    ::= { dsx1ConfigEntry 5 }


         dsx1LineCoding OBJECT-TYPE
             SYNTAX  INTEGER {
                         dsx1JBZS (1),
                         dsx1B8ZS (2),
                         dsx1HDB3 (3),
                         dsx1ZBTSI (4),
                         dsx1AMI (5),
                         other(6)
                     }
             ACCESS  read-write
             STATUS  mandatory
             DESCRIPTION
                "This variable describes the  variety  of  Zero
                Code  Suppression  used  on  the link, which in
                turn affects a number of its characteristics.

                dsx1JBZS refers the Jammed  Bit  Zero  Suppres-
                sion,  in  which  the  AT&T specification of at
                least one pulse every 8 bit periods is literal-
                ly  implemented  by forcing a pulse in bit 8 of
                each channel.  Thus, only seven bits per  chan-
                nel, or 1.344 Mbps, is available for data.

                dsx1B8ZS refers to the use of a specified  pat-
                tern  of  normal  bits  and  bipolar violations
                which are used to replace a sequence  of  eight
                zero bits.

                ANSI Clear Channels may use dsx1ZBTSI, or  Zero
                Byte Time Slot Interchange.

                E1 links, with or without CRC, use dsx1HDB3  or
                dsx1AMI.

                dsx1AMI refers to a mode wherein no  zero  code
                suppression  is  present  and the line encoding
                does not solve the problem directly.   In  this
                application, the higher layer must provide data
                which meets or exceeds the  pulse  density  re-
                quirements, such as inverting HDLC data."
            ::= { dsx1ConfigEntry 6 }


         dsx1SendCode OBJECT-TYPE
             SYNTAX  INTEGER {
                         dsx1SendNoCode(1),
                         dsx1SendLineCode(2),
                         dsx1SendPayloadCode(3),
                         dsx1SendResetCode(4),
                         dsx1SendQRS(5),
                         dsx1Send511Pattern(6),
                         dsx1Send3in24Pattern(7),
                         dsx1SendOtherTestPattern(8)
                     }
             ACCESS  read-write
             STATUS  mandatory
             DESCRIPTION
                "This variable indicates what type of  code  is
                being sent across the DS1 interface by the dev-
                ice.  The values mean:

                dsx1SendNoCode
                     sending looped or normal data

                dsx1SendLineCode
                     sending a request for a line loopback

                dsx1SendPayloadCode
                     sending a request for a payload loopback

                dsx1SendResetCode
                     sending a loopback termination request

                dsx1SendQRS
                     sending a Quasi-Random Signal  (QRS)  test
                     pattern

                dsx1Send511Pattern
                     sending a 511 bit fixed test pattern

                dsx1Send3in24Pattern
                     sending a fixed test pattern of 3 bits set
                     in 24

                dsx1SendOtherTestPattern
                     sending a test pattern  other  than  those
                     described by this object"
            ::= { dsx1ConfigEntry 7 }


         dsx1CircuitIdentifier OBJECT-TYPE
             SYNTAX  DisplayString (SIZE (0..255))
             ACCESS  read-write
             STATUS  mandatory
             DESCRIPTION
                "This  variable   contains   the   transmission
                vendor's circuit identifier, for the purpose of
                facilitating troubleshooting."
            ::= { dsx1ConfigEntry 8 }


         dsx1LoopbackConfig OBJECT-TYPE
             SYNTAX  INTEGER {
                         dsx1NoLoop(1),
                         dsx1PayloadLoop(2),
                         dsx1LineLoop(3),
                         dsx1OtherLoop(4)
                     }
             ACCESS  read-write
             STATUS  mandatory
             DESCRIPTION
                "This variable represents the  loopback  confi-
                guration of the DS1 interface.  Agents support-
                ing read/write access should return badValue in
                response to a requested loopback state that the
                interface does not support.  The values mean:

                dsx1NoLoop
                     Not in the loopback state.  A device  that
                     is not capable of performing a loopback on
                     the interface shall always return this  as
                     it's value.

                dsx1PayloadLoop
                     The received signal at this  interface  is
                     looped  through  the device. Typically the
                     received signal is  looped  back  for  re-
                     transmission  after  it has passed through
                     the device's framing function.

                dsx1LineLoop
                     The received signal at this interface does
                     not  go  through the device (minimum pene-
                     tration) but is looped back out.

                dsx1OtherLoop
                     Loopbacks that are not defined here."
            ::= { dsx1ConfigEntry 9 }


         dsx1LineStatus OBJECT-TYPE
             SYNTAX  INTEGER (1..8191)
             ACCESS  read-only
             STATUS  mandatory
             DESCRIPTION
                "This variable indicates the Line Status of the
                interface.   It contains loopback, failure, re-
                ceived 'alarm'  and transmitted 'alarm'  infor-
                mation.

     The dsx1LineStatus is a bit  map  represented  as  a  sum,
     therefore, it can represent multiple failures (alarms) and
     a LoopbackState simultaneously.

     dsx1NoAlarm should be set if and only if no other flag  is
     set.

     If the dsx1LoopbackState bit is set, the loopback  in  ef-
     fect can be determined from the dsx1LoopbackConfig object.

     The various bit positions are:
          1     dsx1NoAlarm           No Alarm Present
          2     dsx1RcvFarEndLOF      Far end LOF (a.k.a., Yellow Alarm)
          4     dsx1XmtFarEndLOF      Near end sending LOF Indication
          8     dsx1RcvAIS            Far end sending AIS
         16     dsx1XmtAIS            Near end sending AIS
         32     dsx1LossOfFrame       Near end LOF (a.k.a., Red Alarm)
         64     dsx1LossOfSignal      Near end Loss Of Signal
        128     dsx1LoopbackState     Near end is looped
        256     dsx1T16AIS            E1 TS16 AIS
        512     dsx1RcvFarEndLOMF     Far End Sending TS16 LOMF
       1024     dsx1XmtFarEndLOMF     Near End Sending TS16 LOMF
       2048     dsx1RcvTestCode       Near End detects a test code
       4096     dsx1OtherFailure      any line status not defined here"
         ::= { dsx1ConfigEntry 10 }


         dsx1SignalMode OBJECT-TYPE
             SYNTAX  INTEGER {
                         none (1),
                         robbedBit (2),
                         bitOriented (3),
                         messageOriented (4)
                     }
             ACCESS  read-write
             STATUS  mandatory
             DESCRIPTION
                "'none' indicates that no bits are reserved for
                signaling on this channel.

                 'robbedBit' indicates that T1 Robbed Bit  Sig-
                naling is in use.

                 'bitOriented' indicates that E1 Channel  Asso-
                ciated Signaling is in use.

                 'messageOriented' indicates that Common  Chan-
                nel Signaling is in use either on channel 16 of
                an E1 link or channel 24 of a T1."
            ::= { dsx1ConfigEntry 11 }


         dsx1TransmitClockSource OBJECT-TYPE
             SYNTAX  INTEGER {
                         loopTiming (1),
                         localTiming (2),
                         throughTiming (3)
                     }
             ACCESS  read-write
             STATUS  mandatory
             DESCRIPTION
                "The source of Tranmit Clock.
                 'loopTiming' indicates that the recovered  re-
                ceive clock is used as the transmit clock.

                 'localTiming' indicates  that  a  local  clock
                source is used.

                 'throughTiming' indicates that  recovered  re-
                ceive  clock  from another interface is used as
                the transmit clock."
            ::= { dsx1ConfigEntry 12 }


         dsx1Fdl OBJECT-TYPE
             SYNTAX  INTEGER {
                           other(1),
                           dsx1Ansi-T1-403(2),
                           dsx1Att-54016(4),
                           dsx1Fdl-none(8)
                     }
             ACCESS  read-write
             STATUS  mandatory
             DESCRIPTION
                "This bitmap describes the use of  the  facili-
                ties data link, and is the sum of the capabili-
                ties:

                 'other' indicates that a protocol  other  than
                one following is used.

                 'dsx1Ansi-T1-403' refers to the  FDL  exchange
                recommended by ANSI.

                 'dsx1Att-54016' refers to ESF FDL exchanges.

                 'dsx1Fdl-none' indicates that the device  does
                not use the FDL."
            ::= { dsx1ConfigEntry 13 }

          dsx1InvalidIntervals OBJECT-TYPE
               SYNTAX  INTEGER (0..96)
               ACCESS  read-only
               STATUS  mandatory
               DESCRIPTION
                      "The number of intervals for which no valid data
                      is available."
               ::= { dsx1ConfigEntry 14 }

          dsx1LineLength OBJECT-TYPE
               SYNTAX  INTEGER (0..64000)
	       ACCESS  read-write
               STATUS  mandatory
               DESCRIPTION
                      "The length of the ds1 line in meters. This
                      objects provides information for line build out
                      circuitry if it exists and can use this object to
                      adjust the line build out."
               ::= { dsx1ConfigEntry 15 }

          dsx1LineStatusLastChange OBJECT-TYPE
               SYNTAX  TimeTicks
               ACCESS  read-only
               STATUS  mandatory
               DESCRIPTION
                      "The value of MIB II's sysUpTime object at the
                      time this DS1 entered its current line status
                      state.  If the current state was entered prior to
                      the last re-initialization of the proxy-agent,
                      then this object contains a zero value."
               ::= { dsx1ConfigEntry 16 }

          dsx1LineStatusChangeTrapEnable  OBJECT-TYPE
               SYNTAX   INTEGER {
                           enabled(1),
                           disabled(2)
                        }
               ACCESS  read-write
               STATUS  mandatory
               DESCRIPTION
                      "Indicates whether dsx1LineStatusChange traps
                      should be generated for this interface."
               DEFVAL { disabled }
               ::= { dsx1ConfigEntry 17 }

          dsx1LoopbackStatus  OBJECT-TYPE
               SYNTAX      INTEGER (1..127)
               ACCESS      read-only
               STATUS      mandatory
               DESCRIPTION
                      "This variable represents the current state of the
                      loopback on the DS1 interface.  It contains
                      information about loopbacks established by a
                      manager and remotely from the far end.

                      The dsx1LoopbackStatus is a bit map represented as
                      a sum, therefore is can represent multiple
                      loopbacks simultaneously.

                      The various bit positions are:
                       1  dsx1NoLoopback
                       2  dsx1NearEndPayloadLoopback
                       4  dsx1NearEndLineLoopback
                       8  dsx1NearEndOtherLoopback
                      16  dsx1NearEndInwardLoopback
                      32  dsx1FarEndPayloadLoopback
                      64  dsx1FarEndLineLoopback"
          ::= { dsx1ConfigEntry 18 }

     -- the DS1 Current Table

     -- The DS1 current table contains various statistics being
     -- collected for the current 15 minute interval.

         dsx1CurrentTable OBJECT-TYPE
             SYNTAX  SEQUENCE OF Dsx1CurrentEntry
             ACCESS  not-accessible
             STATUS  mandatory
             DESCRIPTION
                "The DS1 Current table."
            ::= { ds1 7 }


         dsx1CurrentEntry OBJECT-TYPE
             SYNTAX  Dsx1CurrentEntry
             ACCESS  not-accessible
             STATUS  mandatory
             DESCRIPTION
                "An entry in the DS1 Current table."
            INDEX   { dsx1CurrentIndex }
            ::= { dsx1CurrentTable 1 }

     Dsx1CurrentEntry ::=
         SEQUENCE {
             dsx1CurrentIndex
                 INTEGER,
             dsx1CurrentESs
                 Gauge,
             dsx1CurrentSESs
                 Gauge,
             dsx1CurrentSEFSs
                 Gauge,
             dsx1CurrentUASs
                 Gauge,
             dsx1CurrentCSSs
                 Gauge,
             dsx1CurrentPCVs
                 Gauge,
             dsx1CurrentLESs
                 Gauge,
             dsx1CurrentBESs
                 Gauge,
             dsx1CurrentDMs
                 Gauge,
             dsx1CurrentLCVs
                 Gauge
         }

         dsx1CurrentIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1CurrentEntry 1 }


         dsx1CurrentESs OBJECT-TYPE
             SYNTAX  Gauge
             ACCESS  read-only
             STATUS  mandatory
             DESCRIPTION
                "The number of Errored Seconds, encountered  by
                a DS1 interface in the current 15 minute inter-
                val."
            ::= { dsx1CurrentEntry 2 }


         dsx1CurrentSESs OBJECT-TYPE
             SYNTAX  Gauge
             ACCESS  read-only
             STATUS  mandatory
             DESCRIPTION
                "The number of Severely Errored Seconds encoun-
                tered  by  a  DS1  interface  in the current 15
                minute interval."
            ::= { dsx1CurrentEntry 3 }


         dsx1CurrentSEFSs OBJECT-TYPE
             SYNTAX  Gauge
             ACCESS  read-only
             STATUS  mandatory
             DESCRIPTION
                "The number of Severely Errored Framing Seconds
                encountered  by  a DS1 interface in the current
                15 minute interval."
            ::= { dsx1CurrentEntry 4 }


         dsx1CurrentUASs OBJECT-TYPE
             SYNTAX  Gauge
             ACCESS  read-only
             STATUS  mandatory
             DESCRIPTION
                "The number of Unavailable Seconds  encountered
                by a DS1 interface in the current 15 minute in-
                terval."
            ::= { dsx1CurrentEntry 5 }

         dsx1CurrentCSSs OBJECT-TYPE
             SYNTAX  Gauge
             ACCESS  read-only
             STATUS  mandatory
             DESCRIPTION
                "The number of Controlled Slip Seconds  encoun-
                tered  by  a  DS1  interface  in the current 15
                minute interval."
            ::= { dsx1CurrentEntry 6 }


         dsx1CurrentPCVs OBJECT-TYPE
             SYNTAX  Gauge
             ACCESS  read-only
             STATUS  mandatory
             DESCRIPTION
                "The number of Path Coding  Violations  encoun-
                tered  by  a  DS1  interface  in the current 15
                minute interval."
            ::= { dsx1CurrentEntry 7 }


         dsx1CurrentLESs OBJECT-TYPE
             SYNTAX  Gauge
             ACCESS  read-only
             STATUS  mandatory
             DESCRIPTION
                "The number of Line Errored Seconds encountered
                by a DS1 interface in the current 15 minute in-
                terval."
            ::= { dsx1CurrentEntry 8 }


         dsx1CurrentBESs OBJECT-TYPE
             SYNTAX Gauge
             ACCESS read-only
             STATUS mandatory
             DESCRIPTION
                "The number of Bursty  Errored  Seconds  (BESs)
                encountered  by  a DS1 interface in the current
                15 minute interval."
            ::= {dsx1CurrentEntry 9 }


         dsx1CurrentDMs OBJECT-TYPE
             SYNTAX Gauge
             ACCESS read-only
             STATUS mandatory
             DESCRIPTION
                "The number of Degraded Minutes  (DMs)  encoun-
                tered  by  a  DS1  interface  in the current 15
                minute interval."
            ::= { dsx1CurrentEntry 10 }


         dsx1CurrentLCVs OBJECT-TYPE
             SYNTAX Gauge
             ACCESS read-only
             STATUS mandatory
             DESCRIPTION
                "The number of Line Code Violations (LCVs)  en-
                countered  by a DS1 interface in the current 15
                minute interval."
         ::= {dsx1CurrentEntry 11 }


     -- the DS1 Interval

     -- The DS1 Interval Table contains various statistics
     -- collected by each DS1 Interface over the previous 24 hours of
     -- operation.  The past 24 hours are broken into 96 completed
     -- 15 minute intervals.

         dsx1IntervalTable OBJECT-TYPE
             SYNTAX  SEQUENCE OF Dsx1IntervalEntry
             ACCESS  not-accessible
             STATUS  mandatory
             DESCRIPTION
                "The DS1 Interval table."
            ::= { ds1 8 }


         dsx1IntervalEntry OBJECT-TYPE
             SYNTAX  Dsx1IntervalEntry
             ACCESS  not-accessible
             STATUS  mandatory
             DESCRIPTION
                "An entry in the DS1 Interval table."
            INDEX   { dsx1IntervalIndex, dsx1IntervalNumber }
            ::= { dsx1IntervalTable 1 }

     Dsx1IntervalEntry ::=
         SEQUENCE {
             dsx1IntervalIndex
                 INTEGER,
             dsx1IntervalNumber
                 INTEGER,
             dsx1IntervalESs
                 Gauge,
             dsx1IntervalSESs
                 Gauge,
             dsx1IntervalSEFSs
                 Gauge,
             dsx1IntervalUASs
                 Gauge,
             dsx1IntervalCSSs
                 Gauge,
             dsx1IntervalPCVs
                 Gauge,
             dsx1IntervalLESs
                 Gauge,
             dsx1IntervalBESs
                 Gauge,
             dsx1IntervalDMs
                 Gauge,
             dsx1IntervalLCVs
                 Gauge,
	     dsx1IntervalValidData 
                 INTEGER
         }

         dsx1IntervalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1IntervalEntry 1 }


         dsx1IntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { dsx1IntervalEntry 2 }

         dsx1IntervalESs OBJECT-TYPE
             SYNTAX  Gauge
             ACCESS  read-only
             STATUS  mandatory
             DESCRIPTION
                "The number of Errored Seconds encountered by a
                DS1  interface in one of the previous 96, indi-
                vidual 15 minute, intervals."
            ::= { dsx1IntervalEntry 3 }


         dsx1IntervalSESs OBJECT-TYPE
             SYNTAX  Gauge
             ACCESS  read-only
             STATUS  mandatory
             DESCRIPTION
                "The number of Severely Errored Seconds encoun-
                tered by a DS1 interface in one of the previous
                96, individual 15 minute, intervals."
            ::= { dsx1IntervalEntry 4 }


         dsx1IntervalSEFSs OBJECT-TYPE
             SYNTAX  Gauge
             ACCESS  read-only
             STATUS  mandatory
             DESCRIPTION
                "The number of Severely Errored Framing Seconds
                encountered  by  a  DS1 interface in one of the
                previous 96, individual 15 minute, intervals."
            ::= { dsx1IntervalEntry 5 }


         dsx1IntervalUASs OBJECT-TYPE
             SYNTAX  Gauge
             ACCESS  read-only
             STATUS  mandatory
             DESCRIPTION
                "The number of Unavailable Seconds  encountered
                by  a  DS1 interface in one of the previous 96,
                individual 15 minute, intervals."
            ::= { dsx1IntervalEntry 6 }


         dsx1IntervalCSSs OBJECT-TYPE
             SYNTAX  Gauge
             ACCESS  read-only
             STATUS  mandatory
             DESCRIPTION
                "The number of Controlled Slip Seconds  encoun-
                tered by a DS1 interface in one of the previous
                96, individual 15 minute, intervals."
            ::= { dsx1IntervalEntry 7 }


         dsx1IntervalPCVs OBJECT-TYPE
             SYNTAX  Gauge
             ACCESS  read-only
             STATUS  mandatory
             DESCRIPTION
                "The number of Path Coding  Violations  encoun-
                tered by a DS1 interface in one of the previous
                96, individual 15 minute, intervals."
            ::= { dsx1IntervalEntry 8 }


         dsx1IntervalLESs OBJECT-TYPE
             SYNTAX  Gauge
             ACCESS  read-only
             STATUS  mandatory
             DESCRIPTION
                "The number of Line Errored Seconds encountered
                by  a  DS1 interface in one of the previous 96,
                individual 15 minute, intervals."
            ::= { dsx1IntervalEntry 9 }


         dsx1IntervalBESs OBJECT-TYPE
             SYNTAX Gauge
             ACCESS read-only
             STATUS mandatory
             DESCRIPTION
                "The number of Bursty  Errored  Seconds  (BESs)
                encountered  by  a  DS1 interface in one of the
                previous 96, individual 15 minute, intervals."
            ::= {dsx1IntervalEntry 10 }


         dsx1IntervalDMs OBJECT-TYPE
             SYNTAX Gauge
             ACCESS read-only
             STATUS mandatory
             DESCRIPTION
                "The number of Degraded Minutes  (DMs)  encoun-
                tered by a DS1 interface in one of the previous
                96, individual 15 minute, intervals."
            ::= { dsx1IntervalEntry 11 }


         dsx1IntervalLCVs OBJECT-TYPE
             SYNTAX Gauge
             ACCESS read-only
             STATUS mandatory
             DESCRIPTION
                "The number of Line Code Violations (LCVs)  en-
                countered  by a DS1 interface in the current 15
                minute interval."
         ::= {dsx1IntervalEntry 12 }

         dsx1IntervalValidData OBJECT-TYPE
               SYNTAX INTEGER {
	                true(1),
	                false(2)
	              }
               ACCESS read-only
               STATUS mandatory
               DESCRIPTION
                      "This variable indicates if there is valid data
                      for this interval."
               ::= { dsx1IntervalEntry 13 }

     -- the DS1 Total

     -- The DS1 Total Table contains the cumulative sum of the
     -- various statistics for the 24 hour period preceding the
     -- current interval.

         dsx1TotalTable OBJECT-TYPE
             SYNTAX  SEQUENCE OF Dsx1TotalEntry
             ACCESS  not-accessible
             STATUS  mandatory
             DESCRIPTION
                "The DS1 Total table.  24 hour interval."
            ::= { ds1 9 }


         dsx1TotalEntry OBJECT-TYPE
             SYNTAX  Dsx1TotalEntry
             ACCESS  not-accessible
             STATUS  mandatory
             DESCRIPTION
                "An entry in the DS1 Total table."
            INDEX   { dsx1TotalIndex }
            ::= { dsx1TotalTable 1 }

     Dsx1TotalEntry ::=
         SEQUENCE {
             dsx1TotalIndex
                 INTEGER,
             dsx1TotalESs
                 Gauge,
             dsx1TotalSESs
                 Gauge,
             dsx1TotalSEFSs
                 Gauge,
             dsx1TotalUASs
                 Gauge,
             dsx1TotalCSSs
                 Gauge,
             dsx1TotalPCVs
                 Gauge,
             dsx1TotalLESs
                 Gauge,
             dsx1TotalBESs
                 Gauge,
             dsx1TotalDMs
                 Gauge,
             dsx1TotalLCVs
                 Gauge
         }

         dsx1TotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1TotalEntry 1 }


         dsx1TotalESs OBJECT-TYPE
             SYNTAX  Gauge
             ACCESS  read-only
             STATUS  mandatory
             DESCRIPTION
                "The number of Errored Seconds encountered by a
                DS1 interface in the previous 24 hour interval"
            ::= { dsx1TotalEntry 2 }


         dsx1TotalSESs OBJECT-TYPE
             SYNTAX  Gauge
             ACCESS  read-only
             STATUS  mandatory
             DESCRIPTION
                "The number of Severely Errored Seconds encoun-
                tered  by  a  DS1  interface in the previous 24
                hour interval."
            ::= { dsx1TotalEntry 3 }


         dsx1TotalSEFSs OBJECT-TYPE
             SYNTAX  Gauge
             ACCESS  read-only
             STATUS  mandatory
             DESCRIPTION
                "The number of Severely Errored Framing Seconds
                encountered  by a DS1 interface in the previous
                24 hour interval."
            ::= { dsx1TotalEntry 4 }


         dsx1TotalUASs OBJECT-TYPE
             SYNTAX  Gauge
             ACCESS  read-only
             STATUS  mandatory
             DESCRIPTION
                "The number of Unavailable Seconds  encountered
                by  a DS1 interface in the previous 24 hour in-
                terval."
            ::= { dsx1TotalEntry 5 }


         dsx1TotalCSSs OBJECT-TYPE
             SYNTAX  Gauge
             ACCESS  read-only
             STATUS  mandatory
             DESCRIPTION
                "The number of Controlled Slip Seconds  encoun-
                tered  by  a  DS1  interface in the previous 24
                hour interval."
            ::= { dsx1TotalEntry 6 }


         dsx1TotalPCVs OBJECT-TYPE
             SYNTAX  Gauge
             ACCESS  read-only
             STATUS  mandatory
             DESCRIPTION
                "The number of Path Coding  Violations  encoun-
                tered  by  a  DS1  interface in the previous 24
                hour interval."
            ::= { dsx1TotalEntry 7 }

         dsx1TotalLESs OBJECT-TYPE
             SYNTAX  Gauge
             ACCESS  read-only
             STATUS  mandatory
             DESCRIPTION
                "The number of Line Errored Seconds encountered
                by  a DS1 interface in the previous 24 hour in-
                terval."
            ::= { dsx1TotalEntry 8 }


         dsx1TotalBESs OBJECT-TYPE
             SYNTAX Gauge
             ACCESS read-only
             STATUS mandatory
             DESCRIPTION
                "The number of Bursty  Errored  Seconds  (BESs)
                encountered  by a DS1 interface in the previous
                24 hour interval."
            ::= { dsx1TotalEntry 9 }


         dsx1TotalDMs OBJECT-TYPE
             SYNTAX Gauge
             ACCESS read-only
             STATUS mandatory
             DESCRIPTION
                "The number of Degraded Minutes  (DMs)  encoun-
                tered  by  a  DS1  interface in the previous 24
                hour interval."
            ::= { dsx1TotalEntry 10 }


         dsx1TotalLCVs OBJECT-TYPE
             SYNTAX Gauge
             ACCESS read-only
             STATUS mandatory
             DESCRIPTION
                "The number of Line Code Violations (LCVs)  en-
                countered  by a DS1 interface in the current 15
                minute interval."
         ::= {dsx1TotalEntry 11 }


     -- The DS1 Far End Group

     -- Implementation of this group is optional for all systems
     -- that attach to a DS1 Interface.
     -- The DS1 Far End Group consists of three tables:
     --   DS1 Far End Current
     --   DS1 Far End Interval
     --   DS1 Far End Total

     -- The DS1 Far End Current Table

     -- The DS1 Far End Current table contains various statistics
     -- being collected for the current 15 minute interval.
     -- The statistics are collected from the far end messages on the
     -- Facilities Data Link.  The definitions are the same as
     -- described for the near-end information.

         dsx1FarEndCurrentTable OBJECT-TYPE
             SYNTAX  SEQUENCE OF Dsx1FarEndCurrentEntry
             ACCESS  not-accessible
             STATUS  mandatory
             DESCRIPTION
                "The DS1 Far End Current table."
            ::= { ds1 10 }


         dsx1FarEndCurrentEntry OBJECT-TYPE
             SYNTAX  Dsx1FarEndCurrentEntry
             ACCESS  not-accessible
             STATUS  mandatory
             DESCRIPTION
                "An entry in the DS1 Far End Current table."
            INDEX   { dsx1FarEndCurrentIndex }
            ::= { dsx1FarEndCurrentTable 1 }

      Dsx1FarEndCurrentEntry ::=
         SEQUENCE {
             dsx1FarEndCurrentIndex
                 INTEGER,
             dsx1FarEndTimeElapsed
                 INTEGER,
             dsx1FarEndValidIntervals
                 INTEGER,
             dsx1FarEndCurrentESs
                 Gauge,
             dsx1FarEndCurrentSESs
                 Gauge,
             dsx1FarEndCurrentSEFSs
                 Gauge,
             dsx1FarEndCurrentUASs
                 Gauge,
             dsx1FarEndCurrentCSSs
                 Gauge,
             dsx1FarEndCurrentLESs
                 Gauge,
             dsx1FarEndCurrentPCVs
                 Gauge,
             dsx1FarEndCurrentBESs
                 Gauge,
             dsx1FarEndCurrentDMs
                 Gauge
         }

         dsx1FarEndCurrentIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value  an  dsx1LineIndex
                object instance."
            ::= { dsx1FarEndCurrentEntry 1 }


         dsx1FarEndTimeElapsed OBJECT-TYPE
             SYNTAX  INTEGER (0..899)
             ACCESS  read-only
             STATUS  mandatory
             DESCRIPTION
                     "The number of seconds that  have  elapsed
                     since the beginning of the far end current
                     error-measurement period."
            ::= { dsx1FarEndCurrentEntry 2 }


         dsx1FarEndValidIntervals OBJECT-TYPE
             SYNTAX  INTEGER (0..96)
             ACCESS  read-only
             STATUS  mandatory
             DESCRIPTION
                     "The number of previous far end  intervals
                     for  which  valid data was collected.  The
                     value will be 96 unless the interface  was
                     brought  online  within the last 24 hours,
                     in which case the value will be the number
                     of  complete  15  minute far end intervals
                     since the interface has been online."
            ::= { dsx1FarEndCurrentEntry 3 }


         dsx1FarEndCurrentESs OBJECT-TYPE
             SYNTAX  Gauge
             ACCESS  read-only
             STATUS  mandatory
             DESCRIPTION
                "The number of Far Far End Errored Seconds  en-
                countered  by a DS1 interface in the current 15
                minute interval."
            ::= { dsx1FarEndCurrentEntry 4 }


         dsx1FarEndCurrentSESs OBJECT-TYPE
             SYNTAX  Gauge
             ACCESS  read-only
             STATUS  mandatory
             DESCRIPTION
                "The number of Far End Severely Errored Seconds
                encountered  by  a DS1 interface in the current
                15 minute interval."
            ::= { dsx1FarEndCurrentEntry 5 }


         dsx1FarEndCurrentSEFSs OBJECT-TYPE
             SYNTAX  Gauge
             ACCESS  read-only
             STATUS  mandatory
             DESCRIPTION
                "The number of Far End Severely Errored Framing
                Seconds  encountered  by a DS1 interface in the
                current 15 minute interval."
            ::= { dsx1FarEndCurrentEntry 6 }


         dsx1FarEndCurrentUASs OBJECT-TYPE
             SYNTAX  Gauge
             ACCESS  read-only
             STATUS  mandatory
             DESCRIPTION
                "The number of Unavailable Seconds  encountered
                by a DS1 interface in the current 15 minute in-
                terval."
            ::= { dsx1FarEndCurrentEntry 7 }

         dsx1FarEndCurrentCSSs OBJECT-TYPE
             SYNTAX  Gauge
             ACCESS  read-only
             STATUS  mandatory
             DESCRIPTION
                "The number of Far End Controlled Slip  Seconds
                encountered  by  a DS1 interface in the current
                15 minute interval."
            ::= { dsx1FarEndCurrentEntry 8 }


         dsx1FarEndCurrentLESs OBJECT-TYPE
             SYNTAX  Gauge
             ACCESS  read-only
             STATUS  mandatory
             DESCRIPTION
                "The number of Far End Line Errored Seconds en-
                countered  by a DS1 interface in the current 15
                minute interval."
            ::= { dsx1FarEndCurrentEntry 9 }


         dsx1FarEndCurrentPCVs OBJECT-TYPE
             SYNTAX  Gauge
             ACCESS  read-only
             STATUS  mandatory
             DESCRIPTION
                "The number of Far End Path  Coding  Violations
                reported  via the far end block error count en-
                countered by a DS1 interface in the current  15
                minute interval."
            ::= { dsx1FarEndCurrentEntry 10 }


         dsx1FarEndCurrentBESs OBJECT-TYPE
             SYNTAX Gauge
             ACCESS read-only
             STATUS mandatory
             DESCRIPTION
                "The number of Bursty  Errored  Seconds  (BESs)
                encountered  by  a DS1 interface in the current
                15 minute interval."
            ::= {dsx1FarEndCurrentEntry 11 }


         dsx1FarEndCurrentDMs OBJECT-TYPE
             SYNTAX Gauge
             ACCESS read-only
             STATUS mandatory
             DESCRIPTION
                "The number of Degraded Minutes  (DMs)  encoun-
                tered  by  a  DS1  interface  in the current 15
                minute interval."
            ::= { dsx1FarEndCurrentEntry 12 }


     -- The DS1 Far End Interval Table

     -- The DS1 Far End Interval Table contains various statistics
     -- collected by each DS1 interface over the previous 24 hours of
     -- operation.  The past 24 hours are broken into 96
     -- completed 15 minute intervals.

         dsx1FarEndIntervalTable OBJECT-TYPE
             SYNTAX  SEQUENCE OF Dsx1FarEndIntervalEntry
             ACCESS  not-accessible
             STATUS  mandatory
             DESCRIPTION
                "The DS1 Far End Interval table."
            ::= { ds1 11 }


         dsx1FarEndIntervalEntry OBJECT-TYPE
             SYNTAX  Dsx1FarEndIntervalEntry
             ACCESS  not-accessible
             STATUS  mandatory
             DESCRIPTION
                "An entry in the DS1 Far End Interval table."
            INDEX   { dsx1FarEndIntervalIndex,
                      dsx1FarEndIntervalNumber }
            ::= { dsx1FarEndIntervalTable 1 }

     Dsx1FarEndIntervalEntry ::=
         SEQUENCE {
             dsx1FarEndIntervalIndex
                 INTEGER,
             dsx1FarEndIntervalNumber
                 INTEGER,
             dsx1FarEndIntervalESs
                 Gauge,
             dsx1FarEndIntervalSESs
                 Gauge,
             dsx1FarEndIntervalSEFSs
                 Gauge,
             dsx1FarEndIntervalUASs
                 Gauge,
             dsx1FarEndIntervalCSSs
                 Gauge,
             dsx1FarEndIntervalLESs
                 Gauge,
             dsx1FarEndIntervalPCVs
                 Gauge,
             dsx1FarEndIntervalBESs
                 Gauge,
             dsx1FarEndIntervalDMs
                 Gauge,
             dsx1FarEndIntervalValidData
	         INTEGER
         }

         dsx1FarEndIntervalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value as a dsx1LineIndex
                object instance."
            ::= { dsx1FarEndIntervalEntry 1 }


         dsx1FarEndIntervalNumber OBJECT-TYPE
             SYNTAX  INTEGER (1..96)
             ACCESS  read-only
             STATUS  mandatory
             DESCRIPTION
                "A number between 1 and 96, where 1 is the most
                recently completed 15 minute interval and 96 is
                the least recently completed 15 minutes  inter-
                val   (assuming   that  all  96  intervals  are
                valid)."
            ::= { dsx1FarEndIntervalEntry 2 }


         dsx1FarEndIntervalESs OBJECT-TYPE
             SYNTAX  Gauge
             ACCESS  read-only
             STATUS  mandatory
             DESCRIPTION
                "The number of Far End Errored Seconds  encoun-
                tered by a DS1 interface in one of the previous
                96, individual 15 minute, intervals."
            ::= { dsx1FarEndIntervalEntry 3 }

         dsx1FarEndIntervalSESs OBJECT-TYPE
             SYNTAX  Gauge
             ACCESS  read-only
             STATUS  mandatory
             DESCRIPTION
                "The number of Far End Severely Errored Seconds
                encountered  by  a  DS1 interface in one of the
                previous 96, individual 15 minute, intervals."
            ::= { dsx1FarEndIntervalEntry 4 }


         dsx1FarEndIntervalSEFSs OBJECT-TYPE
             SYNTAX  Gauge
             ACCESS  read-only
             STATUS  mandatory
             DESCRIPTION
                "The number of Far End Severely Errored Framing
                Seconds  encountered  by a DS1 interface in one
                of the previous 96, individual 15  minute,  in-
                tervals."
            ::= { dsx1FarEndIntervalEntry 5 }


         dsx1FarEndIntervalUASs OBJECT-TYPE
             SYNTAX  Gauge
             ACCESS  read-only
             STATUS  mandatory
             DESCRIPTION
                "The number of Unavailable Seconds  encountered
                by  a  DS1 interface in one of the previous 96,
                individual 15 minute, intervals."
            ::= { dsx1FarEndIntervalEntry 6 }


         dsx1FarEndIntervalCSSs OBJECT-TYPE
             SYNTAX  Gauge
             ACCESS  read-only
             STATUS  mandatory
             DESCRIPTION
                "The number of Far End Controlled Slip  Seconds
                encountered  by  a  DS1 interface in one of the
                previous 96, individual 15 minute, intervals."
            ::= { dsx1FarEndIntervalEntry 7 }


         dsx1FarEndIntervalLESs OBJECT-TYPE
             SYNTAX  Gauge
             ACCESS  read-only
             STATUS  mandatory
             DESCRIPTION
                "The number of Far End Line Errored Seconds en-
                countered by a DS1 interface in one of the pre-
                vious 96, individual 15 minute, intervals."
            ::= { dsx1FarEndIntervalEntry 8 }


         dsx1FarEndIntervalPCVs OBJECT-TYPE
             SYNTAX  Gauge
             ACCESS  read-only
             STATUS  mandatory
             DESCRIPTION
                "The number of Far End Path  Coding  Violations
                reported  via the far end block error count en-
                countered by a DS1 interface in one of the pre-
                vious 96, individual 15 minute, intervals."
            ::= { dsx1FarEndIntervalEntry 9 }


         dsx1FarEndIntervalBESs OBJECT-TYPE
             SYNTAX Gauge
             ACCESS read-only
             STATUS mandatory
             DESCRIPTION
                "The number of Bursty  Errored  Seconds  (BESs)
                encountered  by  a  DS1 interface in one of the
                previous 96, individual 15 minute, intervals."
            ::= {dsx1FarEndIntervalEntry 10 }


         dsx1FarEndIntervalDMs OBJECT-TYPE
             SYNTAX Gauge
             ACCESS read-only
             STATUS mandatory
             DESCRIPTION
                "The number of Degraded Minutes  (DMs)  encoun-
                tered by a DS1 interface in one of the previous
                96, individual 15 minute, intervals."
            ::= { dsx1FarEndIntervalEntry 11 }

          dsx1FarEndIntervalValidData OBJECT-TYPE
               SYNTAX INTEGER {
                         true(1),
	                 false(2)
	             }
               ACCESS read-only
               STATUS mandatory
               DESCRIPTION
                      "This variable indicates if there is valid data
                      for this interval."
               ::= { dsx1FarEndIntervalEntry 12 }

     -- The DS1 Far End Total Table

     -- The DS1 Far End Total Table contains the cumulative sum of the
     -- various statistics for the 24 hour period preceding the
     -- current interval.

         dsx1FarEndTotalTable OBJECT-TYPE
             SYNTAX  SEQUENCE OF Dsx1FarEndTotalEntry
             ACCESS  not-accessible
             STATUS  mandatory
             DESCRIPTION
                "The DS1 Far End Total table."
            ::= { ds1 12 }

         dsx1FarEndTotalEntry OBJECT-TYPE
             SYNTAX  Dsx1FarEndTotalEntry
             ACCESS  not-accessible
             STATUS  mandatory
             DESCRIPTION
                "An entry in the DS1 Far End Total table."
            INDEX   { dsx1FarEndTotalIndex }
            ::= { dsx1FarEndTotalTable 1 }

     Dsx1FarEndTotalEntry ::=
         SEQUENCE {
             dsx1FarEndTotalIndex
                 INTEGER,
             dsx1FarEndTotalESs
                 Gauge,
             dsx1FarEndTotalSESs
                 Gauge,
             dsx1FarEndTotalSEFSs
                 Gauge,
             dsx1FarEndTotalUASs
                 Gauge,
             dsx1FarEndTotalCSSs
                 Gauge,
             dsx1FarEndTotalLESs
                 Gauge,
             dsx1FarEndTotalPCVs
                 Gauge,
             dsx1FarEndTotalBESs
                 Gauge,
             dsx1FarEndTotalDMs
                 Gauge
         }

         dsx1FarEndTotalIndex OBJECT-TYPE
             SYNTAX  INTEGER (1..'7fffffff'h)
             ACCESS  read-only
             STATUS  mandatory
             DESCRIPTION
                "The index value which uniquely identifies  the
                DS1  interface  to which this entry is applica-
                ble.  The interface identified by a  particular
                value  of  this  index is the same interface as
                identified by the same value  an  dsx1LineIndex
                object instance."
            ::= { dsx1FarEndTotalEntry 1 }


         dsx1FarEndTotalESs OBJECT-TYPE
             SYNTAX  Gauge
             ACCESS  read-only
             STATUS  mandatory
             DESCRIPTION
                "The number of Far End Errored Seconds  encoun-
                tered  by  a  DS1  interface in the previous 24
                hour interval."
            ::= { dsx1FarEndTotalEntry 2 }


         dsx1FarEndTotalSESs OBJECT-TYPE
             SYNTAX  Gauge
             ACCESS  read-only
             STATUS  mandatory
             DESCRIPTION
                "The number of Far End Severely Errored Seconds
                encountered  by a DS1 interface in the previous
                24 hour interval."
            ::= { dsx1FarEndTotalEntry 3 }


         dsx1FarEndTotalSEFSs OBJECT-TYPE
             SYNTAX  Gauge
             ACCESS  read-only
             STATUS  mandatory
             DESCRIPTION
                "The number of Far End Severely Errored Framing
                Seconds  encountered  by a DS1 interface in the
                previous 24 hour interval."
            ::= { dsx1FarEndTotalEntry 4 }


         dsx1FarEndTotalUASs OBJECT-TYPE
             SYNTAX  Gauge
             ACCESS  read-only
             STATUS  mandatory
             DESCRIPTION
                "The number of Unavailable Seconds  encountered
                by  a DS1 interface in the previous 24 hour in-
                terval."
            ::= { dsx1FarEndTotalEntry 5 }


         dsx1FarEndTotalCSSs OBJECT-TYPE
             SYNTAX  Gauge
             ACCESS  read-only
             STATUS  mandatory
             DESCRIPTION
                "The number of Far End Controlled Slip  Seconds
                encountered  by a DS1 interface in the previous
                24 hour interval."
            ::= { dsx1FarEndTotalEntry 6 }


         dsx1FarEndTotalLESs OBJECT-TYPE
             SYNTAX  Gauge
             ACCESS  read-only
             STATUS  mandatory
             DESCRIPTION
                "The number of Far End Line Errored Seconds en-
                countered by a DS1 interface in the previous 24
                hour interval."
            ::= { dsx1FarEndTotalEntry 7 }


         dsx1FarEndTotalPCVs OBJECT-TYPE
             SYNTAX  Gauge
             ACCESS  read-only
             STATUS  mandatory
             DESCRIPTION
                "The number of Far End Path  Coding  Violations
                reported  via the far end block error count en-
                countered by a DS1 interface in the previous 24
                hour interval."
            ::= { dsx1FarEndTotalEntry 8 }


         dsx1FarEndTotalBESs OBJECT-TYPE
             SYNTAX Gauge
             ACCESS read-only
             STATUS mandatory
             DESCRIPTION
                "The number of Bursty  Errored  Seconds  (BESs)
                encountered  by a DS1 interface in the previous
                24 hour interval."
            ::= { dsx1FarEndTotalEntry 9 }

         dsx1FarEndTotalDMs OBJECT-TYPE
             SYNTAX Gauge
             ACCESS read-only
             STATUS mandatory
             DESCRIPTION
                "The number of Degraded Minutes  (DMs)  encoun-
                tered  by  a  DS1  interface in the previous 24
                hour interval."
            ::= { dsx1FarEndTotalEntry 10 }

           -- Ds1 TRAPS

          ds1Traps OBJECT IDENTIFIER ::= { ds1 15 }

          dsx1LineStatusChange TRAP-TYPE
              ENTERPRISE ds1Traps
	      VARIABLES  { dsx1LineStatus, dsx1LineStatusLastChange }
              DESCRIPTION
                      "A dsx1LineStatusChange trap is sent when the
                      value of an instance dsx1LineStatus changes. It
                      can be utilized by an NMS to trigger polls.  When
                      the line status change results from a higher level
                      line status change (i.e. ds3), then no traps for
                      the ds1 are sent."
               ::= 1

     END
