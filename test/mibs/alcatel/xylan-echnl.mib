ECHANNEL DEFINITIONS ::= BEGIN

	--  RCSID information

	--  $RCSfile: xylan-echnl.mib,v $
	--  $Revision: 1.2 $
	--  $Date: 1997/10/09 03:01:50 $
	--  $Author: mangesh $


	--  xylan-port.mib
	--  Revision: 1.00
	--  Date: October 13, 1994

	--  Alcatel Internetworking, Inc.
	--  26801 W. Agoura Road
	--  Calabasas, CA 91301
	--  (818) 880-3500
	--  support@ind.alcatel.com

	--  This module provides authoritative definitions for Alcatel Internetworking, Inc.
	--  enterprise-specific virtual PORT MIB.

	--  This module will be extended, as needed.


	--  Alcatel Internetworking, Inc. reserves the right to make changes in 
	--  specification and other information contained in this document 
	--  without prior notice.  The reader should consult Alcatel Internetworking,
	--  Inc. to determine whether any such changes have been made.
	--  Current MIBs are availible from the following URLs:
	--		ftp://ftp.ind.alcatel.com/pub/products/mibs
	--		http://www.ind.alcatel.com
	--
	--  In no event shall Alcatel Internetworking, Inc. be liable for any incidental, 
	--  indirect, special, or consequential damages whatsoever (including 
	--  but not limited to lost profits) arising out of or related to this
	--  document or the information contained in it, even if Alcatel Internetworking,
	--  Inc. has been advised of, known, or should have known, the 
	--  possibility of such damages.

	--  Alcatel Internetworking, Inc. grants vendors, end-users, and other interested
	--  parties a non-exclusive license to use this Specification in connection
	--  with the management of Alcatel Internetworking, Inc. products.

	--  Copyright (C) 1994, Alcatel Internetworking, Inc. All Rights Reserved

	IMPORTS
		OBJECT-TYPE
			FROM RFC-1212
		xylanVportArch
			FROM XYLAN-BASE-MIB 
			;

	--  This MIB module uses the extended OBJECT-TYPE macro as defined in
	--  RFC 1212



	--  groups within the xylanVportArch mib

	virtualPort            OBJECT IDENTIFIER ::= { xylanVportArch 1 }
	logicalPort            OBJECT IDENTIFIER ::= { xylanVportArch 2 }
	physicalPort           OBJECT IDENTIFIER ::= { xylanVportArch 3 }
	mirrorPort             OBJECT IDENTIFIER ::= { xylanVportArch 4 }
	echannelPort	       OBJECT IDENTIFIER ::= { xylanVportArch 5 }

	-- ethChnlPriPortTable OBJECT IDENTIFIER ::= { echannelPort 1 }
	-- ethChnlSecPortTable OBJECT IDENTIFIER ::= { echannelPort 2 }

	-- The EtherChannel Table
 
        ethChnlPriPortTable  OBJECT-TYPE
            SYNTAX  SEQUENCE OF EthChnlPriPortEntry
            ACCESS  not-accessible
            STATUS  mandatory
            DESCRIPTION
                "A list of Ether Channel Primary Port Table instances in this
                 physical OmniSwitch."
            ::= { echannelPort 1 }
 
        ethChnlPriPortEntry  OBJECT-TYPE
            SYNTAX  EthChnlPriPortEntry
            ACCESS  not-accessible
            STATUS  mandatory
            DESCRIPTION
                "An Ether Channel  Primary Port entry."
            INDEX { ethChannelId }
            ::= { ethChnlPriPortTable 1 }
 
        EthChnlPriPortEntry ::= SEQUENCE {
            ethChannelId
                INTEGER,
            priPortSlot
                INTEGER,
            priPortPhysIntf
                INTEGER,
	    ethChannelType
		INTEGER,
	    adminStatus
		INTEGER
            }

	ethChannelId	OBJECT-TYPE
	    SYNTAX  INTEGER(1..254)
	    ACCESS  read-write
	    STATUS  mandatory
	    DESCRIPTION
		"A unique number that identifies this Ether Channel within
		 the physical OmniSwitch."
	    ::= { ethChnlPriPortEntry 1 }

	priPortSlot	OBJECT-TYPE
	    SYNTAX  INTEGER(1..9)
	    ACCESS  read-write
	    STATUS  mandatory
	    DESCRIPTION
		"The physical slot on which the Primary Port (first_port)
		  is configured."
	    ::= { ethChnlPriPortEntry 2 }

	priPortPhysIntf	OBJECT-TYPE
	    SYNTAX  INTEGER(1..12)
	    ACCESS  read-write
	    STATUS  mandatory
	    DESCRIPTION
		"The physical port number that is associated with the Primary
		 Port (first_port)."
		::= { ethChnlPriPortEntry 3 }

	ethChannelType	OBJECT-TYPE
	    SYNTAX  INTEGER {
			etherChnl(1),
			serverChnl(2)
			}
	    ACCESS  read-write
	    STATUS  mandatory
	    DESCRIPTION
		"A unique number that identifies this Ether Channel within
		 the physical OmniSwitch."
	    ::= { ethChnlPriPortEntry 4 }	

	adminStatus	 OBJECT-TYPE
		SYNTAX	INTEGER {
				enable(1),
				disable(2)
				}
	    ACCESS  read-write
	    STATUS  mandatory
	    DESCRIPTION
		"This object indicates whether to add(1) or delete(2) the Ether Channel 
		 Primary Port Entry."		
		::= { ethChnlPriPortEntry 5 }
	    

	ethChnlSecPortTable	OBJECT-TYPE
	    SYNTAX  SEQUENCE OF EthChnlSecPortEntry
            ACCESS  not-accessible
            STATUS  mandatory
            DESCRIPTION
                "A list of Ether Channel Secondary Port Table instances in this
                 physical OmniSwitch."
            ::= { echannelPort 2 }

	ethChnlSecPortEntry  OBJECT-TYPE
            SYNTAX  EthChnlSecPortEntry
            ACCESS  not-accessible
            STATUS  mandatory
            DESCRIPTION
                "An Ether Channel  Secondary Port entry."
            INDEX { secethChannelId, secPortSlot, secPortPhysIntf }
            ::= { ethChnlSecPortTable 1 }
 
        EthChnlSecPortEntry ::= SEQUENCE {
            secethChannelId
                INTEGER,
            secPortSlot
                INTEGER,
            secPortPhysIntf
                INTEGER,
            secAdminStatus
                INTEGER 
            }

    secethChannelId    OBJECT-TYPE
        SYNTAX  INTEGER(1..254)
        ACCESS  read-write
        STATUS  mandatory
        DESCRIPTION
        "A unique number that identifies this Ether Channel within
         the physical OmniSwitch."
        ::= { ethChnlSecPortEntry 1 }
 
    secPortSlot OBJECT-TYPE
        SYNTAX  INTEGER(1..9)
        ACCESS  read-write
        STATUS  mandatory
        DESCRIPTION
        "The physical slot on which the Secondary Port is configured."
        ::= { ethChnlSecPortEntry 2 }
 
    secPortPhysIntf OBJECT-TYPE
        SYNTAX  INTEGER(1..32)
        ACCESS  read-write
        STATUS  mandatory
        DESCRIPTION
        "The physical port number that is associated with the Secondary
         Port."
		::= { ethChnlSecPortEntry 3 }
 
    secAdminStatus  OBJECT-TYPE
        SYNTAX  INTEGER {
                          enable(1),
                          disable(2)
                         }
        ACCESS  read-write
        STATUS  mandatory
        DESCRIPTION
        "This object indicates whether to add(1) or delete(2) the Ether Channel
         Secondary Port Entry."
		::= { ethChnlSecPortEntry 4 }
 
	END
