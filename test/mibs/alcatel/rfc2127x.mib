ISDN-MIB DEFINITIONS ::= BEGIN

IMPORTS
--  plim: commented out because we can use the rfc1253.  declare locally
--    TruthValue
--        FROM RFC1253-MIB
    TRAP-TYPE
        FROM RFC-1215
    DisplayString
        FROM RFC1213-MIB
    OBJECT-TYPE
        FROM RFC-1212
    Counter
        FROM RFC1155-SMI
    transmission
        FROM RFC1213-MIB
    ifIndex
        FROM RFC1213-MIB
    TimeTicks
        FROM RFC1155-SMI;
-- plim commented out because of snmpV2.  declare locally
--    IANAifType
--        FROM IANAifType-MIB
--    InterfaceIndex, ifIndex
--        FROM IF-MIB
-- plim: commented out because of snmpV2.  declare locally
--    TestAndIncr, RowStatus, TimeStamp
--        FROM SNMPv2-TC
--    Gauge32
--        FROM SNMPv2-SMI;

-- created from isdnMib (9609231642Z)

-- plim start the local definition so any SNMPV2 specific is declared locally
-- Gauge32              ::= INTEGER (0..2147483647) 
InterfaceIndex       ::= INTEGER         
TimeStamp            ::= TimeTicks
TruthValue           ::= INTEGER {true(1), false(2)}
-- Get rfc1573a.mib, IANAifType defined as follow
--                   other(1),          
--                   regular1822(2),
--                   hdh1822(3),
--                   ddnX25(4),
--                   rfc877x25(5),
--                   ethernetCsmacd(6),
--                   iso88023Csmacd(7),
--                   iso88024TokenBus(8),
--                   iso88025TokenRing(9),
--                   iso88026Man(10),
--                   starLan(11),
--                   proteon10Mbit(12),
--                   proteon80Mbit(13),
--                   hyperchannel(14),
--                   fddi(15),
--                   lapb(16),
--                   sdlc(17),
--                   ds1(18),           
--                   e1(19),            
--                   basicISDN(20),
--                   primaryISDN(21),
--                   propPointToPointSerial(22), 
--                   ppp(23),
--                   softwareLoopback(24),
--                   eon(25),            
--                   ethernet3Mbit(26),
--                   nsip(27),           
--                   slip(28),            generic SLIP
--                   ultra(29),           ULTRA technologies
--                   ds3(30),             T-3
--                   sip(31),             SMDS
--                   frameRelay(32),     DTE only
--                   rs232(33),
--                   para(34),            parallel-port
--                   arcnet(35),          arcnet
--                   arcnetPlus(36),      arcnet plus
--                   atm(37),             ATM cells
--                   miox25(38),
--                   sonet(39),           SONET or SDH
--                   x25ple(40),
--                   iso88022llc(41),
--                   localTalk(42),
--                   smdsDxi(43),
--                   frameRelayService(44),  Frame relay DCE
--                   v35(45),
--                   hssi(46),
--                   hippi(47),
--                   modem(48),           Generic modem
--                   aal5(49),            AAL5 over ATM
--                   sonetPath(50),
--                   sonetVT(51),
--                   smdsIcip(52),        SMDS InterCarrier Interface
--                   propVirtual(53),     proprietary virtual/internal
--                   propMultiplexor(54)  proprietary multiplexing
-- IANAifType           ::= INTEGER (1..54)
TestAndIncr          ::= INTEGER (0..2147483647)

isdnMib OBJECT IDENTIFIER ::= { transmission  20 }

IsdnSignalingProtocol ::=
    INTEGER {
 other(1),
 dss1(2),
 etsi(3),
 dass2(4),
 ess4(5),
 ess5(6),
 dms100(7),
 dms250(8),
 ni1(9),
 ni2(10),
 ni3(11),
 vn2(12),
 vn3(13),
 vn4(14),
 vn6(15),
 kdd(16),
 ins64(17),
 ins1500(18),
 itr6(19),
 cornet(20),
 ts013(21),
 ts014(22),
 qsig(23),
 swissnet2(24),
 swissnet3(25)
 }

isdnMibObjects OBJECT IDENTIFIER ::= { isdnMib  1 }

isdnBasicRateGroup OBJECT IDENTIFIER ::= { isdnMibObjects  1 }

isdnBasicRateTable OBJECT-TYPE
    SYNTAX  SEQUENCE OF IsdnBasicRateEntry
    ACCESS  not-accessible
    STATUS  mandatory
    DESCRIPTION
           "Table containing configuration and operational
             parameters for all physical Basic Rate
             interfaces on this managed device."
    ::= { isdnBasicRateGroup  1 }

isdnBasicRateEntry OBJECT-TYPE
    SYNTAX  IsdnBasicRateEntry
    ACCESS  not-accessible
    STATUS  mandatory
    DESCRIPTION
           "An entry in the ISDN Basic Rate Table."
    INDEX   { ifIndex }
    ::= { isdnBasicRateTable  1 }

IsdnBasicRateEntry ::=
    SEQUENCE {
        isdnBasicRateIfType
            INTEGER,

        isdnBasicRateLineTopology
            INTEGER,

        isdnBasicRateIfMode
            INTEGER,

        isdnBasicRateSignalMode
            INTEGER
    }

isdnBasicRateIfType OBJECT-TYPE
    SYNTAX  INTEGER {
                 isdns(75),
                 isdnu(76)
               }
    ACCESS  read-write
    STATUS  mandatory
    DESCRIPTION
           "The physical interface type. For 'S/T' interfaces,
             also called 'Four-wire Basic Access Interface',
             the value of this object is isdns(75).
             For 'U' interfaces, also called 'Two-wire Basic
             Access Interface', the value of this object is
             isdnu(76)."
    ::= { isdnBasicRateEntry  1 }

isdnBasicRateLineTopology OBJECT-TYPE
    SYNTAX  INTEGER {
                 pointToPoint(1),
                 pointToMultipoint(2)
               }
    ACCESS  read-write
    STATUS  mandatory
    DESCRIPTION
           "The line topology to be used for this interface.
             Note that setting isdnBasicRateIfType to isdns(75)
             does not necessarily mean a line topology of
             point-to-multipoint."
    ::= { isdnBasicRateEntry  2 }

isdnBasicRateIfMode OBJECT-TYPE
    SYNTAX  INTEGER {
                 te(1),
                 nt(2)
               }
    ACCESS  read-write
    STATUS  mandatory
    DESCRIPTION
           "The physical interface mode. For TE mode, the value
             of this object is te(1). For NT mode, the value
             of this object is nt(2)."
    ::= { isdnBasicRateEntry  3 }

isdnBasicRateSignalMode OBJECT-TYPE
    SYNTAX  INTEGER {
                 active(1),
                 inactive(2)
               }
    ACCESS  read-write
    STATUS  mandatory
    DESCRIPTION
           "The signaling channel operational mode for this interface.
             If active(1) there is a signaling channel on this
             interface. If inactive(2) a signaling channel is
             not available."
    ::= { isdnBasicRateEntry  4 }

isdnBearerGroup OBJECT IDENTIFIER ::= { isdnMibObjects  2 }

isdnBearerTable OBJECT-TYPE
    SYNTAX  SEQUENCE OF IsdnBearerEntry
    ACCESS  not-accessible
    STATUS  mandatory
    DESCRIPTION
           "This table defines port specific operational, statistics
             and active call data for ISDN B channels. Each entry
             in this table describes one B (bearer) channel."
    ::= { isdnBearerGroup  1 }

isdnBearerEntry OBJECT-TYPE
    SYNTAX  IsdnBearerEntry
    ACCESS  not-accessible
    STATUS  mandatory
    DESCRIPTION
           "Operational and statistics information relating to
             one port. A port is a single B channel."
    INDEX   { ifIndex }
    ::= { isdnBearerTable  1 }

IsdnBearerEntry ::=
    SEQUENCE {
        isdnBearerChannelType
            INTEGER,

        isdnBearerOperStatus
            INTEGER,

        isdnBearerChannelNumber
            INTEGER,

        isdnBearerPeerAddress
            DisplayString,

        isdnBearerPeerSubAddress
            DisplayString,

        isdnBearerCallOrigin
            INTEGER,

        isdnBearerInfoType
            INTEGER,

        isdnBearerMultirate
            TruthValue,

        isdnBearerCallSetupTime
            TimeStamp,

        isdnBearerCallConnectTime
            TimeStamp,

        isdnBearerChargedUnits
            INTEGER
    }

isdnBearerChannelType OBJECT-TYPE
    SYNTAX  INTEGER {
                 dialup(1),
                 leased(2)
               }
    ACCESS  read-write
    STATUS  mandatory
    DESCRIPTION
           "The B channel type. If the B channel is connected
             to a dialup line, this object has a value of
             dialup(1). In this case, it is controlled by
             an associated signaling channel. If the B channel
             is connected to a leased line, this object has
             a value of leased(2). For leased line B channels, there
             is no signaling channel control available."
    ::= { isdnBearerEntry  1 }

isdnBearerOperStatus OBJECT-TYPE
    SYNTAX  INTEGER {
                 idle(1),
                 connecting(2),
                 connected(3),
                 active(4)
               }
    ACCESS  read-only
    STATUS  mandatory
    DESCRIPTION
           "The current call control state for this port.
             idle(1):       The B channel is idle.
                            No call or call attempt is going on.
             connecting(2): A connection attempt (outgoing call)
                            is being made on this interface.
             connected(3):  An incoming call is in the process
                            of validation.
             active(4):     A call is active on this interface."
    ::= { isdnBearerEntry  2 }

isdnBearerChannelNumber OBJECT-TYPE
    SYNTAX  INTEGER
    ACCESS  read-only
    STATUS  mandatory
    DESCRIPTION
           "The identifier being used by a signaling protocol
             to identify this B channel, also referred to as
             B channel number. If the Agent also supports the DS0 MIB,
             the values of isdnBearerChannelNumber and dsx0Ds0Number
             must be identical for a given B channel."
    ::= { isdnBearerEntry  3 }

isdnBearerPeerAddress OBJECT-TYPE
    SYNTAX  DisplayString
    ACCESS  read-only
    STATUS  mandatory
    DESCRIPTION
           "The ISDN address the current or last call is or was
             connected to.


             In some cases, the format of this information can not
             be predicted, since it largely depends on the type
             of switch or PBX the device is connected to. Therefore,
             the detailed format of this information is not
             specified and is implementation dependent.


             If possible, the agent should supply this information
             using the E.164 format. In this case, the number must
             start with '+'. Otherwise, IA5 number digits must be used.


             If the peer ISDN address is not available,
             this object has a length of zero."
    REFERENCE
           "ITU-T E.164, Q.931 chapter 4.5.10"
    ::= { isdnBearerEntry  4 }

isdnBearerPeerSubAddress OBJECT-TYPE
    SYNTAX  DisplayString
    ACCESS  read-only
    STATUS  mandatory
    DESCRIPTION
           "The ISDN subaddress the current or last call is or was
             connected to.


             The subaddress is an user supplied string of up to 20
             IA5 characters and is transmitted transparently through
             the network.


             If the peer subaddress is not available, this object
             has a length of zero."
    REFERENCE
           "ITU-T I.330, Q.931 chapter 4.5.11"
    ::= { isdnBearerEntry  5 }

isdnBearerCallOrigin OBJECT-TYPE
    SYNTAX  INTEGER {
                 unknown(1),
                 originate(2),
                 answer(3),
                 callback(4)
               }
    ACCESS  read-only
    STATUS  mandatory
    DESCRIPTION
           "The call origin for the current or last call. If since
             system startup there was no call on this interface,
             this object has a value of unknown(1)."
    ::= { isdnBearerEntry  6 }

isdnBearerInfoType OBJECT-TYPE
    SYNTAX  INTEGER {
                 unknown(1),
                 speech(2),
                 unrestrictedDigital(3),
                 unrestrictedDigital56(4),
                 restrictedDigital(5),
                 audio31(6),
                 audio7(7),
                 video(8),
                 packetSwitched(9)
               }
    ACCESS  read-only
    STATUS  mandatory
    DESCRIPTION
           "The Information Transfer Capability for the current
             or last call.


             speech(2) refers to a non-data connection, whereas
             audio31(6) and audio7(7) refer to data mode connections.


             Note that Q.931, chapter 4.5.5, originally defined
             audio7(7) as '7 kHz audio' and now defines it as
             'Unrestricted digital information with tones/
             announcements'.


             If since system startup there has been no call on this
             interface, this object has a value of unknown(1)."
    REFERENCE
           "Q.931 [8], chapter 4.5.5, octet 3 of bearer capability
             information element, combined with the User Rate
             (as defined in octets 5 and 5a to 5d), if rate adaption
             is being used."
    ::= { isdnBearerEntry  7 }

isdnBearerMultirate OBJECT-TYPE
    SYNTAX  TruthValue
    ACCESS  read-only
    STATUS  mandatory
    DESCRIPTION
           "This flag indicates if the current or last call used
             multirate. The actual information transfer rate,
             in detail specified in octet 4.1 (rate multiplier),
             is the sum of all B channel ifSpeed values for
             the hyperchannel.


             If since system startup there was no call on this
             interface, this object has a value of false(2)."
    REFERENCE
           "Q.931 [8], chapter 4.5.5."
    ::= { isdnBearerEntry  8 }

isdnBearerCallSetupTime OBJECT-TYPE
    SYNTAX  TimeStamp
    ACCESS  read-only
    STATUS  mandatory
    DESCRIPTION
           "The value of sysUpTime when the ISDN setup message for
             the current or last call was sent or received. If since
             system startup there has been no call on this interface,
             this object has a value of zero."
    ::= { isdnBearerEntry  9 }

isdnBearerCallConnectTime OBJECT-TYPE
    SYNTAX  TimeStamp
    ACCESS  read-only
    STATUS  mandatory
    DESCRIPTION
           "The value of sysUpTime when the ISDN connect message for
             the current or last call was sent or received. If since
             system startup there has been no call on this interface,
             this object has a value of zero."
    ::= { isdnBearerEntry  10 }

isdnBearerChargedUnits OBJECT-TYPE
    SYNTAX  INTEGER(0..2147483647)
    ACCESS  read-only
    STATUS  mandatory
    DESCRIPTION
           "The number of charged units for the current or last
             connection. For incoming calls or if charging information
             is not supplied by the switch, the value of this object
             is zero."
    ::= { isdnBearerEntry  11 }

isdnSignalingGroup OBJECT IDENTIFIER ::= { isdnMibObjects  3 }

isdnSignalingGetIndex OBJECT-TYPE
    SYNTAX  TestAndIncr
    ACCESS  read-write
    STATUS  mandatory
    DESCRIPTION
           "The recommended procedure for selecting a new index for
             isdnSignalingTable row creation is to GET the value of
             this object, and then to SET the object with the same
             value. If the SET operation succeeds, the manager can use
             this value as an index to create a new row in this table."
    REFERENCE
           "RFC1903, TestAndIncr textual convention."
    ::= { isdnSignalingGroup  1 }

isdnSignalingTable OBJECT-TYPE
    SYNTAX  SEQUENCE OF IsdnSignalingEntry
    ACCESS  not-accessible
    STATUS  mandatory
    DESCRIPTION
           "ISDN signaling table containing configuration and
             operational parameters for all ISDN signaling
             channels on this managed device."
    ::= { isdnSignalingGroup  2 }

isdnSignalingEntry OBJECT-TYPE
    SYNTAX  IsdnSignalingEntry
    ACCESS  not-accessible
    STATUS  mandatory
    DESCRIPTION
           "An entry in the ISDN Signaling Table. To create a new
             entry, only isdnSignalingProtocol needs to be specified
             before isdnSignalingStatus can become active(1)."
    INDEX   { isdnSignalingIndex }
    ::= { isdnSignalingTable  1 }

IsdnSignalingEntry ::=
    SEQUENCE {
        isdnSignalingIndex
            INTEGER,

        isdnSignalingIfIndex
            InterfaceIndex,

        isdnSignalingProtocol
            IsdnSignalingProtocol,

        isdnSignalingCallingAddress
            DisplayString,

        isdnSignalingSubAddress
            DisplayString,

        isdnSignalingBchannelCount
            INTEGER (-2147483648..2147483647),

        isdnSignalingInfoTrapEnable
            INTEGER,

        isdnSignalingStatus
            INTEGER
    }

isdnSignalingIndex OBJECT-TYPE
    SYNTAX  INTEGER
    ACCESS  not-accessible
    STATUS  mandatory
    DESCRIPTION
           "The index value which uniquely identifies an entry
             in the isdnSignalingTable."
    ::= { isdnSignalingEntry  1 }

isdnSignalingIfIndex OBJECT-TYPE
    SYNTAX  InterfaceIndex
    ACCESS  read-only
    STATUS  mandatory
    DESCRIPTION
           "The ifIndex value of the interface associated with this
             signaling channel."
    ::= { isdnSignalingEntry  2 }

isdnSignalingProtocol OBJECT-TYPE
    SYNTAX  IsdnSignalingProtocol
    ACCESS  read-write
    STATUS  mandatory
    DESCRIPTION
           "The particular protocol type supported by the
             switch providing access to the ISDN network
             to which this signaling channel is connected."
    ::= { isdnSignalingEntry  3 }

isdnSignalingCallingAddress OBJECT-TYPE
    SYNTAX  DisplayString
    ACCESS  read-write
    STATUS  mandatory
    DESCRIPTION
           "The ISDN Address to be assigned to this signaling
             channel. More specifically, this is the 'Calling Address
             information element' as being passed to the switch
             in outgoing call setup messages.


             It can be an EAZ (1TR6), a calling number (DSS1, ETSI)
             or any other number necessary to identify a signaling
             interface. If there is no such number defined or required,
             this is a zero length string. It is represented in
             DisplayString form.


             Incoming calls can also be identified by this number.
             If the Directory Number, i.e. the Called Number in
             incoming calls, is different to this number, the
             isdnDirectoryTable has to be used to specify all
             possible Directory Numbers.


             The format of this information largely depends on the type
             of switch or PBX the device is connected to. Therefore,
             the detailed format of this information is not
             specified and is implementation dependent.


             If possible, the agent should implement this information
             using the E.164 number format. In this case, the number
             must start with '+'. Otherwise, IA5 number digits must
             be used."
    REFERENCE
           "ITU-T E.164, Q.931 chapter 4.5.10"
    DEFVAL  { "" }
    ::= { isdnSignalingEntry  4 }

isdnSignalingSubAddress OBJECT-TYPE
    SYNTAX  DisplayString
    ACCESS  read-write
    STATUS  mandatory
    DESCRIPTION
           "Supplementary information to the ISDN address assigned
             to this signaling channel. Usually, this is the
             subaddress as defined in Q.931.
             If there is no such number defined or required, this is
             a zero length string.
             The subaddress is used for incoming calls as well as
             for outgoing calls.
             The subaddress is an user supplied string of up to 20
             IA5 characters and is transmitted transparently through
             the network."
    REFERENCE
           "ITU-T I.330, Q.931 chapter 4.5.11"
    DEFVAL  { "" }
    ::= { isdnSignalingEntry  5 }

isdnSignalingBchannelCount OBJECT-TYPE
    SYNTAX  INTEGER (-2147483648..2147483647)
    ACCESS  read-write
    STATUS  mandatory
    DESCRIPTION
           "The total number of B channels (bearer channels)
             managed by this signaling channel. The default value
             of this object depends on the physical interface type
             and is either 2 for Basic Rate interfaces or
             24 (30) for Primary Rate interfaces."
    ::= { isdnSignalingEntry  6 }

isdnSignalingInfoTrapEnable OBJECT-TYPE
    SYNTAX  INTEGER {
                 enabled(1),
                 disabled(2)
               }
    ACCESS  read-write
    STATUS  mandatory
    DESCRIPTION
           "Indicates whether isdnMibCallInformation traps
             should be generated for calls on this signaling
             channel."
    DEFVAL  { disabled }
    ::= { isdnSignalingEntry  7 }

isdnSignalingStatus OBJECT-TYPE
    SYNTAX  INTEGER (1..6)
    ACCESS  read-write
    STATUS  mandatory
    DESCRIPTION
           "This object is used to create and delete rows in the
             isdnSignalingTable."
    ::= { isdnSignalingEntry  8 }

isdnSignalingStatsTable OBJECT-TYPE
    SYNTAX  SEQUENCE OF IsdnSignalingStatsEntry
    ACCESS  not-accessible
    STATUS  mandatory
    DESCRIPTION
           "ISDN signaling table containing statistics
             information for all ISDN signaling channels
             on this managed device.
             Only statistical information which is not already being
             counted in the ifTable is being defined in this table."
    ::= { isdnSignalingGroup  3 }

isdnSignalingStatsEntry OBJECT-TYPE
    SYNTAX  IsdnSignalingStatsEntry
    ACCESS  not-accessible
    STATUS  mandatory
    DESCRIPTION
           "An entry in the ISDN Signaling statistics Table."
-- AUGMENTS { isdnSignalingEntry } 
-- plim added INDEX value since mibcomp complaint all entry should have INDEX
    INDEX { ifIndex }
    ::= { isdnSignalingStatsTable  1 }

IsdnSignalingStatsEntry ::=
    SEQUENCE {
        isdnSigStatsInCalls
            Counter,

        isdnSigStatsInConnected
            Counter,

        isdnSigStatsOutCalls
            Counter,

        isdnSigStatsOutConnected
            Counter,

        isdnSigStatsChargedUnits
            Counter
    }

isdnSigStatsInCalls OBJECT-TYPE
    SYNTAX  Counter
    ACCESS  read-only
    STATUS  mandatory
    DESCRIPTION
           "The number of incoming calls on this interface."
    ::= { isdnSignalingStatsEntry  1 }

isdnSigStatsInConnected OBJECT-TYPE
    SYNTAX  Counter
    ACCESS  read-only
    STATUS  mandatory
    DESCRIPTION
           "The number of incoming calls on this interface
             which were actually connected."
    ::= { isdnSignalingStatsEntry  2 }

isdnSigStatsOutCalls OBJECT-TYPE
    SYNTAX  Counter
    ACCESS  read-only
    STATUS  mandatory
    DESCRIPTION
           "The number of outgoing calls on this interface."
    ::= { isdnSignalingStatsEntry  3 }

isdnSigStatsOutConnected OBJECT-TYPE
    SYNTAX  Counter
    ACCESS  read-only
    STATUS  mandatory
    DESCRIPTION
           "The number of outgoing calls on this interface
             which were actually connected."
    ::= { isdnSignalingStatsEntry  4 }

isdnSigStatsChargedUnits OBJECT-TYPE
    SYNTAX  Counter
    ACCESS  read-only
    STATUS  mandatory
    DESCRIPTION
           "The number of charging units on this interface since
             system startup.
             Only the charging units applying to the local interface,
             i.e. for originated calls or for calls with 'Reverse
             charging' being active, are counted here."
    ::= { isdnSignalingStatsEntry  5 }

isdnLapdTable OBJECT-TYPE
    SYNTAX  SEQUENCE OF IsdnLapdEntry
    ACCESS  not-accessible
    STATUS  mandatory
    DESCRIPTION
           "Table containing configuration and statistics
             information for all LAPD (D channel Data Link)
             interfaces on this managed device.
             Only statistical information which is not already being
             counted in the ifTable is being defined in this table."
    ::= { isdnSignalingGroup  4 }

isdnLapdEntry OBJECT-TYPE
    SYNTAX  IsdnLapdEntry
    ACCESS  not-accessible
    STATUS  mandatory
    DESCRIPTION
           "An entry in the LAPD Table."
    INDEX   { ifIndex }
    ::= { isdnLapdTable  1 }

IsdnLapdEntry ::=
    SEQUENCE {
        isdnLapdPrimaryChannel
            TruthValue,

        isdnLapdOperStatus
            INTEGER,

        isdnLapdPeerSabme
            Counter,

        isdnLapdRecvdFrmr
            Counter
    }

isdnLapdPrimaryChannel OBJECT-TYPE
    SYNTAX  TruthValue
    ACCESS  read-write
    STATUS  mandatory
    DESCRIPTION
           "If set to true(1), this D channel is the designated
             primary D channel if D channel backup is active.
             There must be exactly one primary D channel
             configured. If D channel backup is not used, this
             object has a value of true(1)."
    REFERENCE
           "Q.931 [8], Annex F, D channel backup procedures."
    ::= { isdnLapdEntry  1 }

isdnLapdOperStatus OBJECT-TYPE
    SYNTAX  INTEGER {
                 inactive(1),
                 l1Active(2),
                 l2Active(3)
               }
    ACCESS  read-only
    STATUS  mandatory
    DESCRIPTION
           "The operational status of this interface:


             inactive  all layers are inactive
             l1Active  layer 1 is activated,
                       layer 2 datalink not established
             l2Active  layer 1 is activated,
                       layer 2 datalink established."
    ::= { isdnLapdEntry  2 }

isdnLapdPeerSabme OBJECT-TYPE
    SYNTAX  Counter
    ACCESS  read-only
    STATUS  mandatory
    DESCRIPTION
           "The number of peer SABME frames received on this
             interface. This is the number of peer-initiated
             new connections on this interface."
    ::= { isdnLapdEntry  3 }

isdnLapdRecvdFrmr OBJECT-TYPE
    SYNTAX  Counter
    ACCESS  read-only
    STATUS  mandatory
    DESCRIPTION
           "The number of LAPD FRMR response frames received.
             This is the number of framing errors on this
             interface."
    ::= { isdnLapdEntry  4 }

isdnEndpointGroup OBJECT IDENTIFIER ::= { isdnMibObjects  4 }

isdnEndpointGetIndex OBJECT-TYPE
    SYNTAX  TestAndIncr
    ACCESS  read-write
    STATUS  mandatory
    DESCRIPTION
           "The recommended procedure for selecting a new index for
             isdnEndpointTable row creation is to GET the value of
             this object, and then to SET the object with the same
             value. If the SET operation succeeds, the manager can use
             this value as an index to create a new row in this table."
    REFERENCE
           "RFC1903, TestAndIncr textual convention."
    ::= { isdnEndpointGroup  1 }

isdnEndpointTable OBJECT-TYPE
    SYNTAX  SEQUENCE OF IsdnEndpointEntry
    ACCESS  not-accessible
    STATUS  mandatory
    DESCRIPTION
           "Table containing configuration for Terminal
             Endpoints."
    ::= { isdnEndpointGroup  2 }

isdnEndpointEntry OBJECT-TYPE
    SYNTAX  IsdnEndpointEntry
    ACCESS  not-accessible
    STATUS  mandatory
    DESCRIPTION
           "An entry in the Terminal Endpoint Table. The value
             of isdnEndpointIfType must be supplied for a row
             in this table to become active."
    INDEX   { isdnEndpointIndex }
    ::= { isdnEndpointTable  1 }

IsdnEndpointEntry ::=
    SEQUENCE {
        isdnEndpointIndex
            INTEGER,

        isdnEndpointIfIndex
            InterfaceIndex,

        isdnEndpointIfType
            INTEGER,

        isdnEndpointTeiType
            INTEGER,

        isdnEndpointTeiValue
            INTEGER,

        isdnEndpointSpid
            DisplayString,

        isdnEndpointStatus
            INTEGER
    }

isdnEndpointIndex OBJECT-TYPE
    SYNTAX  INTEGER
    ACCESS  not-accessible
    STATUS  mandatory
    DESCRIPTION
           "The index value which uniquely identifies an entry
             in the isdnEndpointTable."
    ::= { isdnEndpointEntry  1 }

isdnEndpointIfIndex OBJECT-TYPE
    SYNTAX  InterfaceIndex
    ACCESS  read-only
    STATUS  mandatory
    DESCRIPTION
           "The ifIndex value of the interface associated with this
             Terminal Endpoint."
    ::= { isdnEndpointEntry  2 }

isdnEndpointIfType OBJECT-TYPE
    SYNTAX  INTEGER(1..54)
    ACCESS  read-write
    STATUS  mandatory
    DESCRIPTION
           "The interface type for this Terminal Endpoint.
             Interface types of x25ple(40) and isdn(63) are allowed.
             The interface type is identical to the value of
             ifType in the associated ifEntry."
    ::= { isdnEndpointEntry  3 }

isdnEndpointTeiType OBJECT-TYPE
    SYNTAX  INTEGER {
                 dynamic(1),
                 static(2)
               }
    ACCESS  read-write
    STATUS  mandatory
    DESCRIPTION
           "The type of TEI (Terminal Endpoint Identifier)
             used for this Terminal Endpoint. In case of dynamic(1),
             the TEI value is selected by the switch. In
             case of static(2), a valid TEI value has to be
             entered in the isdnEndpointTeiValue object.
             The default value for this object depends on the
             interface type as well as the Terminal Endpoint type.
             On Primary Rate interfaces the default value is
             static(2). On Basic Rate interfaces the default value
             is dynamic(1) for isdn(63) Terminal Endpoints and
             static(2) for x25ple(40) Terminal Endpoints."
    ::= { isdnEndpointEntry  4 }

isdnEndpointTeiValue OBJECT-TYPE
    SYNTAX  INTEGER
    ACCESS  read-write
    STATUS  mandatory
    DESCRIPTION
           "The TEI (Terminal Endpoint Identifier) value
             for this Terminal Endpoint. If isdnEndpointTeiType
             is set to static(2), valid numbers are 0..63,
             while otherwise the value is set internally.
             The default value of this object is 0 for static
             TEI assignment.
             The default value for dynamic TEI assignment is also
             0 as long as no TEI has been assigned. After TEI
             assignment, the assigned TEI value is returned."
    ::= { isdnEndpointEntry  5 }

isdnEndpointSpid OBJECT-TYPE
    SYNTAX  DisplayString
    ACCESS  read-write
    STATUS  mandatory
    DESCRIPTION
           "The Service profile IDentifier (SPID) information
             for this Terminal Endpoint.


             The SPID is composed of 9-20 numeric characters.


             This information has to be defined in addition to
             the local number for some switch protocol types,
             e.g. Bellcore NI-1 and NI-2.


             If this object is not required, it is a
             zero length string."
    REFERENCE
           "Bellcore SR-NWT-001953, Generic Guidelines for ISDN
             Terminal Equipment on Basic Access Interfaces,
             Chapter 8.5.1."
    DEFVAL  { "" }
    ::= { isdnEndpointEntry  6 }

isdnEndpointStatus OBJECT-TYPE
    SYNTAX  INTEGER (1..6)
    ACCESS  read-write
    STATUS  mandatory
    DESCRIPTION
           "This object is used to create and delete rows in the
             isdnEndpointTable."
    ::= { isdnEndpointEntry  7 }

isdnDirectoryGroup OBJECT IDENTIFIER ::= { isdnMibObjects  5 }

isdnDirectoryTable OBJECT-TYPE
    SYNTAX  SEQUENCE OF IsdnDirectoryEntry
    ACCESS  not-accessible
    STATUS  mandatory
    DESCRIPTION
           "Table containing Directory Numbers."
    ::= { isdnDirectoryGroup  1 }

isdnDirectoryEntry OBJECT-TYPE
    SYNTAX  IsdnDirectoryEntry
    ACCESS  not-accessible
    STATUS  mandatory
    DESCRIPTION
           "An entry in the Directory Number Table. All objects
             in an entry must be set for a new row to become active."
    INDEX   { isdnDirectoryIndex }
    ::= { isdnDirectoryTable  1 }

IsdnDirectoryEntry ::=
    SEQUENCE {
        isdnDirectoryIndex
            INTEGER,

        isdnDirectoryNumber
            DisplayString,

        isdnDirectorySigIndex
            INTEGER,

        isdnDirectoryStatus
            INTEGER
    }

isdnDirectoryIndex OBJECT-TYPE
    SYNTAX  INTEGER
    ACCESS  not-accessible
    STATUS  mandatory
    DESCRIPTION
           "The index value which uniquely identifies an entry
             in the isdnDirectoryTable."
    ::= { isdnDirectoryEntry  1 }

isdnDirectoryNumber OBJECT-TYPE
    SYNTAX  DisplayString
    ACCESS  read-write
    STATUS  mandatory
    DESCRIPTION
           "A Directory Number. Directory Numbers are used
             to identify incoming calls on the signaling
             channel given in isdnDirectorySigIndex.


             The format of this information largely depends on the type
             of switch or PBX the device is connected to. Therefore,
             the detailed format of this information is not
             specified and is implementation dependent.


             If possible, the agent should implement this information
             using the E.164 number format. In this case, the number
             must start with '+'. Otherwise, IA5 number digits must
             be used."
    REFERENCE
           "ITU-T E.164, Q.931 chapter 4.5.10"
    ::= { isdnDirectoryEntry  2 }

isdnDirectorySigIndex OBJECT-TYPE
    SYNTAX  INTEGER
    ACCESS  read-write
    STATUS  mandatory
    DESCRIPTION
           "An index pointing to an ISDN signaling channel.
             Incoming calls are accepted on this
             signaling channel if the isdnDirectoryNumber is
             presented as Called Number in the SETUP message."
    ::= { isdnDirectoryEntry  3 }

isdnDirectoryStatus OBJECT-TYPE
    SYNTAX  INTEGER (1..6)
    ACCESS  read-write
    STATUS  mandatory
    DESCRIPTION
           "This object is used to create and delete rows in the
             isdnDirectoryTable."
    ::= { isdnDirectoryEntry  4 }

isdnMibTrapPrefix OBJECT IDENTIFIER ::= { isdnMib  2 }

isdnMibTraps OBJECT IDENTIFIER ::= { isdnMibTrapPrefix  0 }

isdnMibCallInformation TRAP-TYPE
    ENTERPRISE  isdnMibTraps
    VARIABLES   {
                 ifIndex,
                 isdnBearerOperStatus,
                 isdnBearerPeerAddress,
                 isdnBearerPeerSubAddress,
                 isdnBearerCallSetupTime,
                 isdnBearerInfoType,
                 isdnBearerCallOrigin
               }
    DESCRIPTION
           "This trap/inform is sent to the manager under the
             following condidions:
             - on incoming calls for each call which is rejected for
               policy reasons (e.g. unknown neighbor or access
               violation)
             - on outgoing calls whenever a call attempt is determined
               to have ultimately failed. In the event that call retry
               is active, then this will be after all retry attempts
               have failed.
             - whenever a call connects. In this case, the object
               isdnBearerCallConnectTime should be included in the
               trap.


             Only one such trap is sent in between successful or
             unsuccessful call attempts from or to a single neighbor;
             subsequent call attempts result in no trap.


             If the Dial Control MIB objects dialCtlNbrCfgId and
             dialCtlNbrCfgIndex are known by the entity generating
             this trap, both objects should be included in the trap
             as well. The receipt of this trap with no dial neighbor
             information indicates that the manager must poll the
             callHistoryTable of the Dial Control MIB to see what
             changed."
    ::= 1

isdnMibConformance OBJECT IDENTIFIER ::= { isdnMib  3 }

isdnMibCompliances OBJECT IDENTIFIER ::= { isdnMibConformance  1 }

isdnMibGroups OBJECT IDENTIFIER ::= { isdnMibConformance  2 }

isdnMibCompliance OBJECT IDENTIFIER ::= { isdnMibCompliances  1 }

isdnMibBasicRateGroup OBJECT IDENTIFIER ::= { isdnMibGroups  1 }

isdnMibBearerGroup OBJECT IDENTIFIER ::= { isdnMibGroups  2 }

isdnMibSignalingGroup OBJECT IDENTIFIER ::= { isdnMibGroups  3 }

isdnMibEndpointGroup OBJECT IDENTIFIER ::= { isdnMibGroups  4 }

isdnMibDirectoryGroup OBJECT IDENTIFIER ::= { isdnMibGroups  5 }

isdnMibNotificationsGroup OBJECT IDENTIFIER ::= { isdnMibGroups  6 }

END
