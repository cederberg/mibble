ALCATEL-IND1-IPRM-MIB DEFINITIONS ::= BEGIN

IMPORTS
   	MODULE-IDENTITY, OBJECT-TYPE, 
    IpAddress, Integer32
        FROM SNMPv2-SMI
    RowStatus
        FROM SNMPv2-TC
    MODULE-COMPLIANCE, OBJECT-GROUP
        FROM SNMPv2-CONF
    IANAipRouteProtocol
	FROM IANA-RTPROTO-MIB
    routingIND1Iprm
        FROM ALCATEL-IND1-BASE ;

alcatelIND1IPRMMIB MODULE-IDENTITY

    LAST-UPDATED  "200107051130Z"
    ORGANIZATION  "Alcatel - Architects Of An Internet World"
    CONTACT-INFO
        "Please consult with Customer Service to insure the most appropriate
         version of this document is used with the products in question:

                    Alcatel Internetworking, Incorporated
                   (Division 1, Formerly XYLAN Corporation)
                           26801 West Agoura Road
                        Agoura Hills, CA  91301-5122
                          United States Of America

        Telephone:               North America  +1 800 995 2696
                                 Latin America  +1 877 919 9526
                                 Europe         +31 23 556 0100
                                 Asia           +65 394 7933
                                 All Other      +1 818 878 4507

        Electronic Mail:         support@ind.alcatel.com
        World Wide Web:          http://www.ind.alcatel.com
        File Transfer Protocol:  ftp://ftp.ind.alcatel.com/pub/products/mibs"

    DESCRIPTION
        "This module describes an authoritative enterprise-specific Simple
         Network Management Protocol (SNMP) Management Information Base (MIB):

             This proprietary MIB contains management information for
             the configuration of PIM-SM global configuration parameters.

         The right to make changes in specification and other information
         contained in this document without prior notice is reserved.

         No liability shall be assumed for any incidental, indirect, special, or
         consequential damages whatsoever arising from or related to this
         document or the information contained herein.

         Vendors, end-users, and other interested parties are granted
         non-exclusive license to use this specification in connection with
         management of the products for which it is intended to be used.

           Copyright (C) 1995-2002 Alcatel Internetworking, Incorporated
                         ALL RIGHTS RESERVED WORLDWIDE"

    REVISION      "200107051130Z"
    DESCRIPTION
        "The latest version of this MIB Module."

    ::= { routingIND1Iprm 1 }                

alcatelIND1IPRMMIBObjects  OBJECT IDENTIFIER ::= { alcatelIND1IPRMMIB 1 }

alaIprmConfig  OBJECT IDENTIFIER ::= { alcatelIND1IPRMMIBObjects 1 }

-- Route Table

alaIprmRouteTable OBJECT-TYPE
    SYNTAX   SEQUENCE OF AlaIprmRouteEntry
    MAX-ACCESS not-accessible
    STATUS   current
    DESCRIPTION
       "IPRM's Routing table."
    ::= { alaIprmConfig 1 }

alaIprmRouteEntry OBJECT-TYPE
    SYNTAX   AlaIprmRouteEntry
    MAX-ACCESS not-accessible
    STATUS   current
    DESCRIPTION
       "A particular route to  a  particular  destination"
    INDEX {
        alaIprmRouteDest,
        alaIprmRouteMask,
        alaIprmRouteTos, 
        alaIprmRouteNextHop
        }                 
    ::= { alaIprmRouteTable 1 }
                              
AlaIprmRouteEntry ::=          
    SEQUENCE {      
        alaIprmRouteDest
            IpAddress, 
        alaIprmRouteMask
            IpAddress, 
        alaIprmRouteTos 
             Integer32,
        alaIprmRouteNextHop
            IpAddress,    
 	alaIprmRouteProto
            IANAipRouteProtocol,    
        alaIprmRouteMetric  
            Integer32,    
	alaIprmRoutePriority
	    Integer32
    }

alaIprmRouteDest OBJECT-TYPE
    SYNTAX   IpAddress
    MAX-ACCESS read-only
    STATUS   current    
    DESCRIPTION         
       "The destination IP address of this route."
    ::= { alaIprmRouteEntry 1 }                        
                                                 
alaIprmRouteMask OBJECT-TYPE   
    SYNTAX   IpAddress     
    MAX-ACCESS read-only   
    STATUS   current    
    DESCRIPTION         
	"The mask of this route"
    ::= { alaIprmRouteEntry 2 }
        
alaIprmRouteTos OBJECT-TYPE   
    SYNTAX   Integer32 (0..16)
    MAX-ACCESS read-only   
    STATUS   current    
    DESCRIPTION         
	"The TOS for this route"
    ::= { alaIprmRouteEntry 3 }
        
alaIprmRouteNextHop OBJECT-TYPE   
    SYNTAX   IpAddress     
    MAX-ACCESS read-only   
    STATUS   current    
    DESCRIPTION         
	"The Gateway for this route"
    ::= { alaIprmRouteEntry 4 }
        
alaIprmRouteProto OBJECT-TYPE   
    SYNTAX   IANAipRouteProtocol
    MAX-ACCESS read-only   
    STATUS   current    
    DESCRIPTION         
	"The protocol that this route was learned from"
    ::= { alaIprmRouteEntry 5 }
        
alaIprmRouteMetric OBJECT-TYPE   
    SYNTAX   Integer32     
    MAX-ACCESS read-only   
    STATUS   current    
    DESCRIPTION         
	"The metric for this route"
    ::= { alaIprmRouteEntry 6 }
        
alaIprmRoutePriority OBJECT-TYPE   
    SYNTAX   Integer32     
    MAX-ACCESS read-only   
    STATUS   current    
    DESCRIPTION         
	"The priority for this route"
    ::= { alaIprmRouteEntry 7 }


-- Static Route Table

alaIprmStaticRouteTable OBJECT-TYPE
    SYNTAX   SEQUENCE OF AlaIprmStaticRouteEntry
    MAX-ACCESS not-accessible
    STATUS   current
    DESCRIPTION
       "IPRM's Static Route table."
    ::= { alaIprmConfig 2 }

alaIprmStaticRouteEntry OBJECT-TYPE
    SYNTAX   AlaIprmStaticRouteEntry
    MAX-ACCESS not-accessible
    STATUS   current
    DESCRIPTION
	"A route entered by the user"
    INDEX {
        alaIprmStaticRouteDest,
        alaIprmStaticRouteMask,
        alaIprmStaticRouteNextHop
        }                 
    ::= { alaIprmStaticRouteTable 1 }
                              
AlaIprmStaticRouteEntry ::=          
    SEQUENCE {      
        alaIprmStaticRouteDest
            IpAddress, 
        alaIprmStaticRouteMask
            IpAddress, 
        alaIprmStaticRouteNextHop
            IpAddress,    
	alaIprmStaticRouteMetric
	    Integer32,
	alaIprmStaticRouteStatus
	    RowStatus
    }

alaIprmStaticRouteDest OBJECT-TYPE
    SYNTAX   IpAddress
    MAX-ACCESS read-create
    STATUS   current    
    DESCRIPTION         
       "The destination IP address of this route."
    ::= { alaIprmStaticRouteEntry 1 }                        
                                                 
alaIprmStaticRouteMask OBJECT-TYPE   
    SYNTAX   IpAddress     
    MAX-ACCESS read-create   
    STATUS   current    
    DESCRIPTION         
	"The mask of this route"
    ::= { alaIprmStaticRouteEntry 2 }
        
alaIprmStaticRouteNextHop OBJECT-TYPE   
    SYNTAX   IpAddress     
    MAX-ACCESS read-create   
    STATUS   current    
    DESCRIPTION         
	"The Gateway for this route"
    ::= { alaIprmStaticRouteEntry 3 }
        
alaIprmStaticRouteMetric OBJECT-TYPE   
    SYNTAX   Integer32     
    MAX-ACCESS read-write   
    STATUS   current    
    DESCRIPTION         
	"The metric for this route"
    ::= { alaIprmStaticRouteEntry 4 }

alaIprmStaticRouteStatus OBJECT-TYPE
    SYNTAX     RowStatus
    MAX-ACCESS read-create
    STATUS     current
    DESCRIPTION
            "The status of this entry.  Enabling causes a new
		static route to be created, disabled causes that
		static route to be deleted."
    ::= { alaIprmStaticRouteEntry 5 }

-- conformance information

alcatelIND1IPRMMIBConformance OBJECT IDENTIFIER ::= { alcatelIND1IPRMMIB 2 }
alcatelIND1IPRMMIBCompliances OBJECT IDENTIFIER ::=
                                          { alcatelIND1IPRMMIBConformance 1 }
alcatelIND1IPRMMIBGroups      OBJECT IDENTIFIER ::=
                                          { alcatelIND1IPRMMIBConformance 2 }

-- compliance statements

alaIprmCompliance MODULE-COMPLIANCE
    STATUS  current
    DESCRIPTION
            "The compliance statement for routers running IPRM
            and implementing the ALCATEL-IND1-IPRM MIB."
    MODULE  -- this module
        MANDATORY-GROUPS { alaIprmConfigMIBGroup }

    ::= { alcatelIND1IPRMMIBCompliances 1 }

-- units of conformance

alaIprmConfigMIBGroup OBJECT-GROUP
    OBJECTS { alaIprmRouteProto, alaIprmRouteMetric, alaIprmRoutePriority,
		alaIprmRouteDest, alaIprmRouteMask, alaIprmRouteTos, 
	        alaIprmRouteNextHop, alaIprmStaticRouteDest,
	        alaIprmStaticRouteMask, alaIprmStaticRouteNextHop,
		alaIprmStaticRouteMetric, alaIprmStaticRouteStatus
            }
    STATUS  current
    DESCRIPTION
            "A collection of objects to support management of global
            configuration parameters of the IPRM Module."
    ::= { alcatelIND1IPRMMIBGroups 1 }


END
