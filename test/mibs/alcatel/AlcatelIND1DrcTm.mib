ALCATEL-IND1-DRCTM-MIB DEFINITIONS ::= BEGIN

IMPORTS
    MODULE-IDENTITY, OBJECT-TYPE,
    IpAddress, Integer32
        FROM SNMPv2-SMI
    MODULE-COMPLIANCE, OBJECT-GROUP
        FROM SNMPv2-CONF
    routingIND1Tm
        FROM ALCATEL-IND1-BASE;

alcatelIND1DrcTmMIB MODULE-IDENTITY

    LAST-UPDATED  "200107051130Z"
    ORGANIZATION  "Alcatel - Architects Of An Internet World"
    CONTACT-INFO
        "Please consult with Customer Service to insure the most appropriate
         version of this document is used with the products in question:

                    Alcatel Internetworking, Incorporated
                   (Division 1, Formerly XYLAN Corporation)
                           26801 West Agoura Road
                        Agoura Hills, CA  91301-5122
                          United States Of America

        Telephone:               North America  +1 800 995 2696
                                 Latin America  +1 877 919 9526
                                 Europe         +31 23 556 0100
                                 Asia           +65 394 7933
                                 All Other      +1 818 878 4507

        Electronic Mail:         support@ind.alcatel.com
        World Wide Web:          http://www.ind.alcatel.com
        File Transfer Protocol:  ftp://ftp.ind.alcatel.com/pub/products/mibs"

    DESCRIPTION
        "This module describes an authoritative enterprise-specific Simple
         Network Management Protocol (SNMP) Management Information Base (MIB):

             This proprietary MIB contains management information for
             the configuration of PIM-SM global configuration parameters.

         The right to make changes in specification and other information
         contained in this document without prior notice is reserved.

         No liability shall be assumed for any incidental, indirect, special, o
r
         consequential damages whatsoever arising from or related to this
         document or the information contained herein.

         Vendors, end-users, and other interested parties are granted
         non-exclusive license to use this specification in connection with
         management of the products for which it is intended to be used.

           Copyright (C) 1995-2002 Alcatel Internetworking, Incorporated
                         ALL RIGHTS RESERVED WORLDWIDE"

    REVISION      "200107051130Z"
    DESCRIPTION
        "The latest version of this MIB Module."

    ::= { routingIND1Tm 1 }

alcatelIND1DrcTmMIBObjects    OBJECT IDENTIFIER ::= { alcatelIND1DrcTmMIB 1 }
alaDrcTmConfig    OBJECT IDENTIFIER ::= { alcatelIND1DrcTmMIBObjects 1 }
alaDrcTmDebug     OBJECT IDENTIFIER ::= { alcatelIND1DrcTmMIBObjects 2 }

alaDrcTmIPRouterPrimaryAddress    OBJECT-TYPE
    SYNTAX      IpAddress
    MAX-ACCESS  read-write
    STATUS      current
    DESCRIPTION
                "Defines the Primary IP Address of this Router."
    ::= {alaDrcTmConfig 1 }

alaDrcTmIPRouterId    OBJECT-TYPE
    SYNTAX      IpAddress
    MAX-ACCESS  read-write
    STATUS      current
    DESCRIPTION
                "Defines the Router-id for this Router."
    ::= {alaDrcTmConfig 2 }

alaDrcTmIPRipStatus     OBJECT-TYPE
    SYNTAX     INTEGER {
                   loaded(1),
                   not-loaded(2),
		   loading(3)
               }
    MAX-ACCESS read-write
    STATUS     current
    DESCRIPTION
		"Controls the load status of RIP on this router.
		 The value 3 (loading) is not a valid set value,
		 it is only used for gets"
    DEFVAL     { not-loaded }
    ::= {alaDrcTmConfig 3 }

alaDrcTmIPOspfStatus     OBJECT-TYPE
    SYNTAX     INTEGER {
                   loaded(1),
                   not-loaded(2),
		   loading(3)
               }
    MAX-ACCESS read-write
    STATUS     current
    DESCRIPTION
		"Controls the load status of OSPF on this router.
		 The value 3 (loading) is not a valid set value,
		 it is only used for gets"
    DEFVAL     { not-loaded }
    ::= {alaDrcTmConfig 4 }

alaDrcTmIPBgpStatus     OBJECT-TYPE
    SYNTAX     INTEGER {
                   loaded(1),
                   not-loaded(2),
		   loading(3)
               }
    MAX-ACCESS read-write
    STATUS     current
    DESCRIPTION
		"Controls the load status of BGP on this router.
		 The value 3 (loading) is not a valid set value,
		 it is only used for gets"
    DEFVAL     { not-loaded }
    ::= {alaDrcTmConfig 5 }

alaDrcTmIPDvmrpStatus     OBJECT-TYPE
    SYNTAX     INTEGER {
                   loaded(1),
                   not-loaded(2),
		   loading(3)
               }
    MAX-ACCESS read-write
    STATUS     current
    DESCRIPTION
		"Controls the load status of DVMRP on this router.
		 The value 3 (loading) is not a valid set value,
		 it is only used for gets"
    DEFVAL     { not-loaded }
    ::= {alaDrcTmConfig 6 }

alaDrcTmIPPimsmStatus     OBJECT-TYPE
    SYNTAX     INTEGER {
                   loaded(1),
                   not-loaded(2),
		   loading(3)
               }
    MAX-ACCESS read-write
    STATUS     current
    DESCRIPTION
		"Controls the load status of PIM-SM on this router.
		 The value 3 (loading) is not a valid set value,
		 it is only used for gets"
    DEFVAL     { not-loaded }
    ::= {alaDrcTmConfig 7 }

alaDrcTmIPMsdpStatus     OBJECT-TYPE
    SYNTAX     INTEGER {
                   loaded(1),
                   not-loaded(2),
		   loading(3)
               }
    MAX-ACCESS read-write
    STATUS     current
    DESCRIPTION
		"Controls the load status of MSDP on this router.
		 The value 3 (loading) is not a valid set value,
		 it is only used for gets"
    DEFVAL     { not-loaded }
    ::= {alaDrcTmConfig 8 }

-- ************************************************************************
--  DRC TM Debug Configuration
-- ************************************************************************

alaDrcTmDebugLevel     OBJECT-TYPE
    SYNTAX     Integer32 (0..255)
    MAX-ACCESS read-write
    STATUS     current
    DESCRIPTION
               "Sets the level of Debugging for the DRC TM on
                this router.  A level of 0 indicates no debugging."
    DEFVAL     { 0 }
    ::= {alaDrcTmDebug 1}

alaDrcTmDebugError     OBJECT-TYPE
    SYNTAX     INTEGER {
                   enable(1),
                   disable(2)
               }
    MAX-ACCESS read-write
    STATUS     current
    DESCRIPTION
               "Administratively enables/disables debugging for DRC TM
                Error messages if the alaDrcTmDebugLevel is greater
                than 0."
    DEFVAL     { disable }
    ::= {alaDrcTmDebug 2}


alaDrcTmDebugHealth     OBJECT-TYPE
    SYNTAX     INTEGER {
                   enable(1),
                   disable(2)
               }
    MAX-ACCESS read-write
    STATUS     current
    DESCRIPTION
               "Administratively enables/disables debugging for DRC TM
                Health messages if the alaDrcTmDebugLevel is greater
                than 0."
    DEFVAL     { disable }
    ::= {alaDrcTmDebug 3}

alaDrcTmDebugTaskInfo     OBJECT-TYPE
    SYNTAX     INTEGER {
                   enable(1),
                   disable(2)
               }
    MAX-ACCESS read-write
    STATUS     current
    DESCRIPTION
               "Administratively enables/disables debugging for DRC TM
                Task Info messages if the alaDrcTmDebugLevel is greater
                than 0."
    DEFVAL     { disable }
    ::= {alaDrcTmDebug 4}

alaDrcTmDebugEvents     OBJECT-TYPE
    SYNTAX     INTEGER {
                   enable(1),
                   disable(2)
               }
    MAX-ACCESS read-write
    STATUS     current
    DESCRIPTION
               "Administratively enables/disables debugging for DRC TM
                Event messages if the alaDrcTmDebugLevel is greater
                than 0."
    DEFVAL     { disable }
    ::= {alaDrcTmDebug 5}

alaDrcTmDebugMip     OBJECT-TYPE
    SYNTAX     INTEGER {
                   enable(1),
                   disable(2)
               }
    MAX-ACCESS read-write
    STATUS     current
    DESCRIPTION
               "Administratively enables/disables debugging for DRC TM
                MIP processing (including CLI/SNMP) if the 
                alaDrcTmDebugLevel is greater than 0."
    DEFVAL     { disable }
    ::= {alaDrcTmDebug 6}

alaDrcTmDebugExternal     OBJECT-TYPE
    SYNTAX     INTEGER {
                   enable(1),
                   disable(2)
               }
    MAX-ACCESS read-write
    STATUS     current
    DESCRIPTION
               "Administratively enables/disables debugging for DRC TM
                External messages if the alaDrcTmDebugLevel is greater
                than 0."
    DEFVAL     { disable }
    ::= {alaDrcTmDebug 7}

alaDrcTmDebugMisc     OBJECT-TYPE
    SYNTAX     INTEGER {
                   enable(1),
                   disable(2)
               }
    MAX-ACCESS read-write
    STATUS     current
    DESCRIPTION
               "Administratively enables/disables miscellaneous debugging 
			    for DRC TM messages if the alaDrcTmDebugLevel is greater
                than 0."
    DEFVAL     { disable }
    ::= {alaDrcTmDebug 8}

alaDrcTmDebugUnused1     OBJECT-TYPE
    SYNTAX     INTEGER {
                   enable(1),
                   disable(2)
               }
    MAX-ACCESS read-write
    STATUS     current
    DESCRIPTION
               "Administratively enables/disables debugging for DRC TM
                Unused1 messages if the alaDrcTmDebugLevel is greater
                than 0."
    DEFVAL     { disable }
    ::= {alaDrcTmDebug 9}

alaDrcTmDebugUnused2     OBJECT-TYPE
    SYNTAX     INTEGER {
                   enable(1),
                   disable(2)
               }
    MAX-ACCESS read-write
    STATUS     current
    DESCRIPTION
               "Administratively enables/disables debugging for DRC TM
                Unused2 messages if the alaDrcTmDebugLevel is greater
                than 0."
    DEFVAL     { disable }
    ::= {alaDrcTmDebug 10}

alaDrcTmDebugUnused3     OBJECT-TYPE
    SYNTAX     INTEGER {
                   enable(1),
                   disable(2)
               }
    MAX-ACCESS read-write
    STATUS     current
    DESCRIPTION
               "Administratively enables/disables debugging for DRC TM
                Unused3 messages if the alaDrcTmDebugLevel is greater
                than 0."
    DEFVAL     { disable }
    ::= {alaDrcTmDebug 11}

alaDrcTmDebugUnused4     OBJECT-TYPE
    SYNTAX     INTEGER {
                   enable(1),
                   disable(2)
               }
    MAX-ACCESS read-write
    STATUS     current
    DESCRIPTION
               "Administratively enables/disables debugging for DRC TM
                Unused4 messages if the alaDrcTmDebugLevel is greater
                than 0."
    DEFVAL     { disable }
    ::= {alaDrcTmDebug 12}

alaDrcTmDebugAll     OBJECT-TYPE
    SYNTAX     INTEGER {
                   enable(1),
                   disable(2)
               }
    MAX-ACCESS read-write
    STATUS     current
    DESCRIPTION
               "Administratively enables/disables all debugging for DRC TM
                messages if the alaDrcTmDebugLevel is greater than 0."
    DEFVAL     { disable }
    ::= {alaDrcTmDebug 13}

-- conformance information

alcatelIND1DrcTmMIBConformance OBJECT IDENTIFIER ::= { alcatelIND1DrcTmMIB 2 }
alcatelIND1DrcTmMIBCompliances OBJECT IDENTIFIER ::=
                                          { alcatelIND1DrcTmMIBConformance 1 }
alcatelIND1DrcTmMIBGroups      OBJECT IDENTIFIER ::=
                                          { alcatelIND1DrcTmMIBConformance 2 }

-- compliance statements

alaDrcTmCompliance MODULE-COMPLIANCE
    STATUS  current
    DESCRIPTION
            "The compliance statement for routers running DRC Task
            Manager (TM) and implementing the ALCATEL-IND1-DRCTM MIB."
    MODULE  -- this module
        MANDATORY-GROUPS { alaDrcTmConfigMIBGroup, alaDrcTmDebugMIBGroup }

    ::= { alcatelIND1DrcTmMIBCompliances 1 }

-- units of conformance

alaDrcTmConfigMIBGroup OBJECT-GROUP
    OBJECTS { alaDrcTmIPRouterPrimaryAddress,
              alaDrcTmIPRouterId, alaDrcTmIPRipStatus, 
              alaDrcTmIPOspfStatus, alaDrcTmIPBgpStatus, 
              alaDrcTmIPDvmrpStatus, alaDrcTmIPPimsmStatus, 
              alaDrcTmIPMsdpStatus
            }
    STATUS  current
    DESCRIPTION
            "A collection of objects to support management of DRC
            Task Manager."
    ::= { alcatelIND1DrcTmMIBGroups 1 }

alaDrcTmDebugMIBGroup OBJECT-GROUP
    OBJECTS { alaDrcTmDebugLevel, alaDrcTmDebugError,
              alaDrcTmDebugHealth, alaDrcTmDebugTaskInfo,
              alaDrcTmDebugEvents, alaDrcTmDebugMip,
              alaDrcTmDebugExternal, alaDrcTmDebugMisc,
              alaDrcTmDebugAll
            }
    STATUS  current
    DESCRIPTION
            "A collection of optional objects to provide debugging
             support of DRC TM."
    ::= { alcatelIND1DrcTmMIBGroups 2 }

END
