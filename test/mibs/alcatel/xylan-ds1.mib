XYLAN-DS1-MIB DEFINITIONS ::= BEGIN

     --  RCSID information

     --  $RCSfile: xylan-ds1.mib,v $
     --  $Revision: 1.3 $		$State: Exp $
     --  $Date: 1998/01/15 00:40:10 $
     --  $Author: eric $

     --  xylan-ds1.mib
     --  Revision: 1.00
     --  Date: January 16, 1997

     --  Alcatel Internetworking, Inc.
     --  26801 W. Agoura Road
     --  Calabasas, CA 91301
     --  (818) 880-3500
     --  support@ind.alcatel.com

     --  This module provides authoritative definitions for Alcatel Internetworking, Inc.
     --  enterprise-specific physical port parameters MIB.

     --  This module will be extended, as needed.


     --  Alcatel Internetworking, Inc. reserves the right to make changes in 
     --  specification and other information contained in this document 
     --  without prior notice.  The reader should consult Alcatel Internetworking,
     --  Inc. to determine whether any such changes have been made.

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1996, Alcatel Internetworking, Inc. All Rights Reserved.
     
     	IMPORTS
		Counter, TimeTicks
	         	FROM RFC1155-SMI
		OBJECT-TYPE
			FROM RFC-1212
		DisplayString 
			FROM RFC1213-MIB
	        xylanPportArch
			FROM XYLAN-BASE-MIB 
			;

        dsx1Port     OBJECT IDENTIFIER ::= { xylanPportArch 1 }

    --  T1/E1 Physical Port Configuration Table

        dsx1PortConfigTable   OBJECT-TYPE
	    SYNTAX   SEQUENCE OF Dsx1PortConfigEntry
            ACCESS   not-accessible
            STATUS   mandatory
            DESCRIPTION
            	   "A table of Dsx1 physical layer status and parameter 
                    information."
            ::= { dsx1Port 1 }

         dsx1PortConfigEntry   OBJECT-TYPE
	    SYNTAX   Dsx1PortConfigEntry
            ACCESS   not-accessible
            STATUS   mandatory
            DESCRIPTION
                   "An entry in the table, containing information about 
                    the physical layer of a Dsx1 interface."
            INDEX   { dsx1PortConfigSlotIndex, dsx1PortConfigPortIndex }
            ::= { dsx1PortConfigTable 1 }

         Dsx1PortConfigEntry ::=
             SEQUENCE {
	         dsx1PortConfigSlotIndex
                     INTEGER,
		 dsx1PortConfigPortIndex
                     INTEGER,
	         dsx1PortConfigIfType
		     INTEGER,
                 dsx1PortFdlRole
	             INTEGER,
                 dsx1PortNfasAlign
	             INTEGER,
                 dsx1PortConfigYelAlarmDetectEnable
                     INTEGER
             }

         dsx1PortConfigSlotIndex  OBJECT-TYPE
             SYNTAX   INTEGER (1..9)
             ACCESS   read-only
             STATUS   mandatory
             DESCRIPTION
                    "A unique value which identifies this HSM board slot."
             ::= { dsx1PortConfigEntry 1 }

         dsx1PortConfigPortIndex   OBJECT-TYPE
             SYNTAX   INTEGER (1..32)
             ACCESS   read-only
             STATUS   mandatory
             DESCRIPTION
                    "A unique value which identifies this port."
             ::= { dsx1PortConfigEntry 2 }

         dsx1PortConfigIfType       OBJECT-TYPE
	     SYNTAX   INTEGER {
                         t1(1),
	                 e1(2)
       	     }
             ACCESS  read-only
             STATUS  mandatory
             DESCRIPTION
                  "The type of interface."
             ::= { dsx1PortConfigEntry 3 }
             
          dsx1PortFdlRole OBJECT-TYPE
               SYNTAX   INTEGER {
                            network(1),
                            user(2)
                        }
               ACCESS  read-write
               STATUS  mandatory
               DESCRIPTION
                      "Indicates Facility Data Link port role of this
	               port.  If the port role is network and fdlMode is 
	               set to AT&T 54016, then this port periodically sends
	               AT&T  performance requests to CI."
               ::= { dsx1PortConfigEntry 4 }

          dsx1PortNfasAlign OBJECT-TYPE
               SYNTAX   INTEGER {
                           enable(1),
	                   disable(2)
                        }
               ACCESS  read-write
               STATUS  mandatory
               DESCRIPTION
                      "This object indicates if framing criterion is based on 
	               bit 2 of Time Slot 0 NOT-FAS.  This object only applies
	               to E1."
               ::= { dsx1PortConfigEntry 5 }

          dsx1PortConfigYelAlarmDetectEnable OBJECT-TYPE
               SYNTAX   INTEGER {
                           enable(1),
                           disable(2)
                         }
               ACCESS   read-write
               STATUS   mandatory
               DESCRIPTION
                        "This object indicates whether Yellow Alarm should 
                         be detected."
               ::= { dsx1PortConfigEntry 6 }

    --  T1/E1 Physical Port Statistics Table

        dsx1PortStatsTable   OBJECT-TYPE
	    SYNTAX   SEQUENCE OF Dsx1PortStatsEntry
            ACCESS   not-accessible
            STATUS   mandatory
            DESCRIPTION
            	   "A table of Dsx1 physical port statistics."
            ::= { dsx1Port 2 }

         dsx1PortStatsEntry   OBJECT-TYPE
	    SYNTAX   Dsx1PortStatsEntry
            ACCESS   not-accessible
            STATUS   mandatory
            DESCRIPTION
                   "An entry in the table, containing information about 
                    the physical port statistics of a Dsx1 interface."
            INDEX   { dsx1PortStatsSlotIndex, dsx1PortStatsPortIndex }
            ::= { dsx1PortStatsTable 1 }

         Dsx1PortStatsEntry ::= SEQUENCE {
	         dsx1PortStatsSlotIndex
                     INTEGER,
		 dsx1PortStatsPortIndex
	             INTEGER,
	         dsx1PortStatsLossOfSignal 
	             Counter,
	         dsx1PortStatsOutOfFrame
	             Counter,
	         dsx1PortStatsRedAlarmEvent
                     Counter,
	         dsx1PortStatsYellowAlarmEvent
	             Counter,
                 dsx1PortStatsSquelchAlarmEvent
                     Counter,
                 dsx1PortStatsBipolarVioEvent
	             Counter,
                 dsx1PortStatsAISEvent
	             Counter,
                 dsx1PortStatsCrcErrorEvent
                     Counter,
	         dsx1PortStatsOutOfSubMultiFrame
	             Counter,
	         dsx1PortStatsOutOfTs16MultiFrame
	             Counter,
	         dsx1PortStatsRemFrameAlarm
	             Counter,
	         dsx1PortStatsRemMultiFrameAlarm
	             Counter,
	         dsx1PortStatsFarEndBlkError
	             Counter,
	         dsx1PortStatsFramingBitError
	             Counter
         }

         dsx1PortStatsSlotIndex OBJECT-TYPE
             SYNTAX   INTEGER (1..9)
             ACCESS   read-only
             STATUS   mandatory
             DESCRIPTION
                    "A unique value which identifies this HSM board slot."
             ::= { dsx1PortStatsEntry 1 }

         dsx1PortStatsPortIndex   OBJECT-TYPE
             SYNTAX   INTEGER (1..32)
             ACCESS   read-only
             STATUS   mandatory
             DESCRIPTION
                    "A unique value which identifies this port."
             ::= { dsx1PortStatsEntry 2 }

	dsx1PortStatsLossOfSignal  OBJECT-TYPE
	    SYNTAX  Counter
	    ACCESS  read-only
	    STATUS  mandatory
	    DESCRIPTION
	       "Total number of Loss of Signals that have been detected on 
	        this port." 
	    ::= { dsx1PortStatsEntry 3 }

	dsx1PortStatsOutOfFrame    OBJECT-TYPE
	    SYNTAX  Counter
	    ACCESS  read-only
	    STATUS  mandatory
	    DESCRIPTION
	       "Total number of Out of Frames that have been detected on 
	        this port." 
	    ::= { dsx1PortStatsEntry 4 }

	dsx1PortStatsRedAlarmEvent   OBJECT-TYPE
	    SYNTAX  Counter
	    ACCESS  read-only
	    STATUS  mandatory
	    DESCRIPTION
	       "Total number of Red Alarm events that have been detected on 
	        this port." 
	    ::= { dsx1PortStatsEntry 5 }

	dsx1PortStatsYellowAlarmEvent   OBJECT-TYPE
	    SYNTAX  Counter
	    ACCESS  read-only
	    STATUS  mandatory
	    DESCRIPTION
	       "Total number of Yellow Alarm events that have been detected on 
	        this port. This object applies to T1 port only." 
	    ::= { dsx1PortStatsEntry 6 }

	dsx1PortStatsSquelchAlarmEvent   OBJECT-TYPE
	    SYNTAX  Counter
	    ACCESS  read-only
	    STATUS  mandatory
	    DESCRIPTION
	       "Total number of Squelch Alarm events that have been 
	        detected on this port." 
	    ::= { dsx1PortStatsEntry 7 }

	dsx1PortStatsBipolarVioEvent   OBJECT-TYPE
	    SYNTAX  Counter
	    ACCESS  read-only
	    STATUS  mandatory
	    DESCRIPTION
	       "Total number of Bipolar Violation events that have been 
	        detected on this port." 
	    ::= { dsx1PortStatsEntry 8 }

	dsx1PortStatsAISEvent   OBJECT-TYPE
	    SYNTAX  Counter
	    ACCESS  read-only
	    STATUS  mandatory
	    DESCRIPTION
	       "Total number of AIS events that have been detected on 
	        this port." 
	    ::= { dsx1PortStatsEntry 9 }

	dsx1PortStatsCrcErrorEvent   OBJECT-TYPE
	    SYNTAX  Counter
	    ACCESS  read-only
	    STATUS  mandatory
	    DESCRIPTION
	       "Total number of ESF CRC-6 Error events for T1 or CRC-4 Error
                Events for E1  that have been detected on this port."
	    ::= { dsx1PortStatsEntry 10 }

         dsx1PortStatsOutOfSubMultiFrame OBJECT-TYPE
	    SYNTAX  Counter
	    ACCESS  read-only
	    STATUS  mandatory
	    DESCRIPTION
	       "Total number of out of sub-multiframe events that have been
	        detected on this port.  This object only applies to E1 port."
	    ::= { dsx1PortStatsEntry 11 }

         dsx1PortStatsOutOfTs16MultiFrame OBJECT-TYPE
	    SYNTAX  Counter
	    ACCESS  read-only
	    STATUS  mandatory
	    DESCRIPTION
	       "Total number of out of TS 16 multiframe events that have 
	        been detected on this port.  This object only applies to 
	        E1 port."
	    ::= { dsx1PortStatsEntry 12 }

         dsx1PortStatsRemFrameAlarm OBJECT-TYPE
	    SYNTAX  Counter
	    ACCESS  read-only
	    STATUS  mandatory
	    DESCRIPTION
	       "Total number of Remote Frame Alarm events that have been 
                detected on this port.  This object only applies to E1 port."
	    ::= { dsx1PortStatsEntry 13 }

         dsx1PortStatsRemMultiFrameAlarm OBJECT-TYPE
	    SYNTAX  Counter
	    ACCESS  read-only
	    STATUS  mandatory
	    DESCRIPTION
	       "Total number of Remote MultifFame Alarm events that have 
	        been detected on this port.  This object only applies to 
                E1 port."
	    ::= { dsx1PortStatsEntry 14 }

         dsx1PortStatsFarEndBlkError OBJECT-TYPE
	    SYNTAX  Counter
	    ACCESS  read-only
	    STATUS  mandatory
	    DESCRIPTION
	       "Total number of Far End Block Error events that have been 
	        detected on this port.  This object only applies to E1 port."
	    ::= { dsx1PortStatsEntry 15 }

         dsx1PortStatsFramingBitError OBJECT-TYPE
	    SYNTAX  Counter
	    ACCESS  read-only
	    STATUS  mandatory
	    DESCRIPTION
	       "Total number of Framing Bit Error events that have been 
	        detected on this port."
	    ::= { dsx1PortStatsEntry 16 }

   END
