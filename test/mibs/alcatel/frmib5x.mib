-- automatically generated by mosy 7.2 #19 (yukinojo), do not edit!

FRAME-RELAY-DTE-MIB DEFINITIONS ::= BEGIN


IMPORTS
	TRAP-TYPE
		FROM RFC-1215
	OBJECT-TYPE
		FROM RFC-1212
	Counter
		FROM RFC1155-SMI
-- AKB
-- AKB Changed InterfaceIndex to local definition for now
-- AKB
-- AKB	InterfaceIndex
-- AKB		FROM IF-MIB
-- AKB

	transmission
		FROM RFC1213-MIB
	TimeTicks			-- AKB TimeStamp to TimeTicks --
		FROM RFC1155-SMI;	-- AKB TimeStamp to TimeTicks --

-- created from frameRelayDTE (9501091735Z)
-- Changed frameRelayDTE to frame-relay
frame-relay OBJECT IDENTIFIER ::= { transmission  32 }

     --
     --      the range of ifIndex
     --
     InterfaceIndex ::= INTEGER       -- 1..ifNumber


DLCI ::=
    INTEGER (-2147483648..2147483647)

frDlcmiTable OBJECT-TYPE
    SYNTAX  SEQUENCE OF FrDlcmiEntry
    ACCESS  not-accessible
    STATUS  mandatory
    DESCRIPTION
           "The Parameters for the Data Link Connection Management
            Interface for the frame relay service on this
            interface."
    REFERENCE
           "The Parameters for the Data Link Connection Management
            Interface for the frame relay service on this
            interface."
-- changed frameRelayDTE to frame-relay
    ::= { frame-relay  1 }

frDlcmiEntry OBJECT-TYPE
    SYNTAX  FrDlcmiEntry
    ACCESS  not-accessible
    STATUS  mandatory
    DESCRIPTION
           "The Parameters for a particular Data Link Connection
            Management Interface."
    INDEX   { frDlcmiIfIndex }
    ::= { frDlcmiTable  1 }

FrDlcmiEntry ::=
    SEQUENCE {
        frDlcmiIfIndex
            InterfaceIndex,

        frDlcmiState
            INTEGER,

        frDlcmiAddress
            INTEGER,

        frDlcmiAddressLen
            INTEGER,

        frDlcmiPollingInterval
            INTEGER,

        frDlcmiFullEnquiryInterval
            INTEGER,

        frDlcmiErrorThreshold
            INTEGER,

        frDlcmiMonitoredEvents
            INTEGER,

        frDlcmiMaxSupportedVCs
            INTEGER (-2147483648..2147483647),

        frDlcmiMulticast
            INTEGER,

        frDlcmiStatus
            INTEGER  -- AKB RowStatus Objects removed (comma removed)--

-- AKB RowStatus Objects removed --
-- AKB       frDlcmiRowStatus
-- AKB            RowStatus
-- AKB

    }

frDlcmiIfIndex OBJECT-TYPE
    SYNTAX  InterfaceIndex
    ACCESS  read-only
    STATUS  mandatory
    DESCRIPTION
           "The ifIndex value of the corresponding ifEntry."
    ::= { frDlcmiEntry  1 }

frDlcmiState OBJECT-TYPE
    SYNTAX  INTEGER {
    noLmiConfigured(1),
    lmiRev1(2),
    ansiT1617D(3),
    ansiT1617B(4),
    itut933A(5),
    ansiT1617D1994(6)
}
    ACCESS  read-write
    STATUS  mandatory
    DESCRIPTION
           "This variable states which Data Link Connection
            Management scheme is active (and by implication, what
            DLCI it uses) on the Frame Relay interface."
    REFERENCE
           "This variable states which Data Link Connection
            Management scheme is active (and by implication, what
            DLCI it uses) on the Frame Relay interface."
    ::= { frDlcmiEntry  2 }

frDlcmiAddress OBJECT-TYPE
    SYNTAX  INTEGER {
    q921(1),
    q922March90(2),
    q922November90(3),
    q922(4)
}
    ACCESS  read-write
    STATUS  mandatory
    DESCRIPTION
           "This variable states which address format is in use on
            the Frame Relay interface."
    ::= { frDlcmiEntry  3 }

frDlcmiAddressLen OBJECT-TYPE
    SYNTAX  INTEGER {
    twoOctets(2),
    threeOctets(3),
    fourOctets(4)
}
    ACCESS  read-write
    STATUS  mandatory
    DESCRIPTION
           "This variable states the address length in octets.  In
            the case of Q922 format, the length indicates the
            entire length of the address including the control
            portion."
    ::= { frDlcmiEntry  4 }

frDlcmiPollingInterval OBJECT-TYPE
    SYNTAX  INTEGER
    ACCESS  read-write
    STATUS  mandatory
    DESCRIPTION
           "This is the number of seconds between successive
            status enquiry messages."
    REFERENCE
           "This is the number of seconds between successive
            status enquiry messages."
    DEFVAL  { 10 }
    ::= { frDlcmiEntry  5 }

frDlcmiFullEnquiryInterval OBJECT-TYPE
    SYNTAX  INTEGER
    ACCESS  read-write
    STATUS  mandatory
    DESCRIPTION
           "Number of status enquiry intervals that pass before
            issuance of a full status enquiry message."
    REFERENCE
           "Number of status enquiry intervals that pass before
            issuance of a full status enquiry message."
    DEFVAL  { 6 }
    ::= { frDlcmiEntry  6 }

frDlcmiErrorThreshold OBJECT-TYPE
    SYNTAX  INTEGER
    ACCESS  read-write
    STATUS  mandatory
    DESCRIPTION
           "This is the maximum number of unanswered Status
            Enquiries the equipment shall accept before declaring
            the interface down."
    REFERENCE
           "This is the maximum number of unanswered Status
            Enquiries the equipment shall accept before declaring
            the interface down."
    DEFVAL  { 3 }
    ::= { frDlcmiEntry  7 }

frDlcmiMonitoredEvents OBJECT-TYPE
    SYNTAX  INTEGER
    ACCESS  read-write
    STATUS  mandatory
    DESCRIPTION
           "This is the number of status polling intervals over
            which the error threshold is counted.  For example, if
            within 'MonitoredEvents' number of events the station
            receives 'ErrorThreshold' number of errors, the
            interface is marked as down."
    REFERENCE
           "This is the number of status polling intervals over
            which the error threshold is counted.  For example, if
            within 'MonitoredEvents' number of events the station
            receives 'ErrorThreshold' number of errors, the
            interface is marked as down."
    DEFVAL  { 4 }
    ::= { frDlcmiEntry  8 }

frDlcmiMaxSupportedVCs OBJECT-TYPE
    SYNTAX  INTEGER (-2147483648..2147483647)
    ACCESS  read-write
    STATUS  mandatory
    DESCRIPTION
           "The maximum number of Virtual Circuits allowed for
            this interface.  Usually dictated by the Frame Relay
            network.

            In response to a SET, if a value less than zero or
            higher than the agent's maximal capability is
            configured, the agent should respond badValue"
    ::= { frDlcmiEntry  9 }

frDlcmiMulticast OBJECT-TYPE
    SYNTAX  INTEGER {
    nonBroadcast(1),
    broadcast(2)
}
    ACCESS  read-write
    STATUS  mandatory
    DESCRIPTION
           "This indicates whether the Frame Relay interface is
            using a multicast service."
    ::= { frDlcmiEntry  10 }

frDlcmiStatus OBJECT-TYPE
    SYNTAX  INTEGER {
    running(1),
    fault(2),
    initializing(3)
}
    ACCESS  read-only
    STATUS  mandatory
    DESCRIPTION
           "This indicates the status of the Frame Relay interface
            as determined by the performance of the dlcmi.  If no
            dlcmi is running, the Frame Relay interface will stay
            in the running state indefinitely."
    ::= { frDlcmiEntry  11 }

-- AKB RowStatus Objects removed --
-- AKB
-- AKB frDlcmiRowStatus OBJECT-TYPE
-- AKB    SYNTAX  RowStatus
-- AKB    ACCESS  read-write
-- AKB    STATUS  mandatory
-- AKB    DESCRIPTION
-- AKB           "SNMP Version 2 Row Status Variable."
-- AKB    ::= { frDlcmiEntry  12 }
-- AKB

frCircuitTable OBJECT-TYPE
    SYNTAX  SEQUENCE OF FrCircuitEntry
    ACCESS  not-accessible
    STATUS  mandatory
    DESCRIPTION
           "A table containing information about specific Data
            Link Connections (DLC) or virtual circuits."
-- Changed from frameRelayDTE to frame-relay
    ::= { frame-relay  2 }

frCircuitEntry OBJECT-TYPE
    SYNTAX  FrCircuitEntry
    ACCESS  not-accessible
    STATUS  mandatory
    DESCRIPTION
           "The information regarding a single Data Link
            Connection."
    INDEX   { frCircuitIfIndex,  frCircuitDlci }
    ::= { frCircuitTable  1 }

FrCircuitEntry ::=
    SEQUENCE {
        frCircuitIfIndex
            InterfaceIndex,

        frCircuitDlci
            DLCI,

        frCircuitState
            INTEGER,

        frCircuitReceivedFECNs
            Counter,

        frCircuitReceivedBECNs
            Counter,

        frCircuitSentFrames
            Counter,

        frCircuitSentOctets
            Counter,

        frCircuitReceivedFrames
            Counter,

        frCircuitReceivedOctets
            Counter,

        frCircuitCreationTime
            TimeTicks,  -- AKB TimeStamp to TimeTicks -- 

        frCircuitLastTimeChange
            TimeTicks,  -- AKB TimeStamp to TimeTicks -- 

        frCircuitCommittedBurst
            INTEGER (-2147483648..2147483647),

        frCircuitExcessBurst
            INTEGER (-2147483648..2147483647),

        frCircuitThroughput
            INTEGER (-2147483648..2147483647),

        frCircuitMulticast
            INTEGER,

        frCircuitType
            INTEGER,

        frCircuitDiscards
            Counter,

        frCircuitReceivedDEs
            Counter,

        frCircuitSentDEs
            Counter,

        frCircuitLogicalIfIndex
            InterfaceIndex  -- AKB RowStatus Objects removed (comma removed) --

-- AKB RowStatus Objects removed --
-- AKB        frCircuitRowStatus
-- AKB            RowStatus
-- AKB

    }

frCircuitIfIndex OBJECT-TYPE
    SYNTAX  InterfaceIndex
    ACCESS  read-only
    STATUS  mandatory
    DESCRIPTION
           "The ifIndex Value of the ifEntry this virtual circuit
            is layered onto."
    ::= { frCircuitEntry  1 }

frCircuitDlci OBJECT-TYPE
    SYNTAX  DLCI
    ACCESS  read-only
    STATUS  mandatory
    DESCRIPTION
           "The Data Link Connection Identifier for this virtual
            circuit."
    REFERENCE
           "The Data Link Connection Identifier for this virtual
            circuit."
    ::= { frCircuitEntry  2 }

frCircuitState OBJECT-TYPE
    SYNTAX  INTEGER {
    invalid(1),
    active(2),
    inactive(3)
}
    ACCESS  read-write
    STATUS  mandatory
    DESCRIPTION
           "Indicates whether the particular virtual circuit is
            operational.  In the absence of a Data Link Connection
            Management Interface, virtual circuit entries (rows)
            may be created by setting virtual circuit state to
            'active', or deleted by changing Circuit state to
            'invalid'.

            Whether or not the row actually disappears is left to
            the implementation, so this object may actually read as
            'invalid' for some arbitrary length of time.  It is
            also legal to set the state of a virtual circuit to
            'inactive' to temporarily disable a given circuit.

            The use of 'invalid' is deprecated in this SNMP Version
            2 MIB, in favor of frCircuitRowStatus."
    DEFVAL  { active }
    ::= { frCircuitEntry  3 }

frCircuitReceivedFECNs OBJECT-TYPE
    SYNTAX  Counter
    ACCESS  read-only
    STATUS  mandatory
    DESCRIPTION
           "Number of frames received from the network indicating
            forward congestion since the virtual circuit was
            created.  This occurs when the remote DTE sets the FECN
            flag, or when a switch in the network enqueues the
            frame to a trunk whose transmission queue is
            congested."
    REFERENCE
           "Number of frames received from the network indicating
            forward congestion since the virtual circuit was
            created.  This occurs when the remote DTE sets the FECN
            flag, or when a switch in the network enqueues the
            frame to a trunk whose transmission queue is
            congested."
    ::= { frCircuitEntry  4 }

frCircuitReceivedBECNs OBJECT-TYPE
    SYNTAX  Counter
    ACCESS  read-only
    STATUS  mandatory
    DESCRIPTION
           "Number of frames received from the network indicating
            backward congestion since the virtual circuit was
            created.  This occurs when the remote DTE sets the BECN
            flag, or when a switch in the network receives the
            frame from a trunk whose transmission queue is
            congested."
    REFERENCE
           "Number of frames received from the network indicating
            backward congestion since the virtual circuit was
            created.  This occurs when the remote DTE sets the BECN
            flag, or when a switch in the network receives the
            frame from a trunk whose transmission queue is
            congested."
    ::= { frCircuitEntry  5 }

frCircuitSentFrames OBJECT-TYPE
    SYNTAX  Counter
    ACCESS  read-only
    STATUS  mandatory
    DESCRIPTION
           "The number of frames sent from this virtual circuit
            since it was created."
    ::= { frCircuitEntry  6 }

frCircuitSentOctets OBJECT-TYPE
    SYNTAX  Counter
    ACCESS  read-only
    STATUS  mandatory
    DESCRIPTION
           "The number of octets sent from this virtual circuit
            since it was created."
    ::= { frCircuitEntry  7 }

frCircuitReceivedFrames OBJECT-TYPE
    SYNTAX  Counter
    ACCESS  read-only
    STATUS  mandatory
    DESCRIPTION
           "Number of frames received over this virtual circuit
            since it was created."
    ::= { frCircuitEntry  8 }

frCircuitReceivedOctets OBJECT-TYPE
    SYNTAX  Counter
    ACCESS  read-only
    STATUS  mandatory
    DESCRIPTION
           "Number of octets received over this virtual circuit
            since it was created."
    ::= { frCircuitEntry  9 }

frCircuitCreationTime OBJECT-TYPE
    SYNTAX  TimeTicks  -- AKB TimeStamp to TimeTicks --
    ACCESS  read-only
    STATUS  mandatory
    DESCRIPTION
           "The value of sysUpTime when the virtual circuit was
            created, whether by the Data Link Connection Management
            Interface or by a SetRequest."
    ::= { frCircuitEntry  10 }

frCircuitLastTimeChange OBJECT-TYPE
    SYNTAX  TimeTicks  -- AKB TimeStamp to TimeTicks --
    ACCESS  read-only
    STATUS  mandatory
    DESCRIPTION
           "The value of sysUpTime when last there was a change in
            the virtual circuit state"
    ::= { frCircuitEntry  11 }

frCircuitCommittedBurst OBJECT-TYPE
    SYNTAX  INTEGER (-2147483648..2147483647)
    ACCESS  read-write
    STATUS  mandatory
    DESCRIPTION
           "This variable indicates the maximum amount of data, in
            bits, that the network agrees to transfer under normal
            conditions, during the measurement interval."
    REFERENCE
           "This variable indicates the maximum amount of data, in
            bits, that the network agrees to transfer under normal
            conditions, during the measurement interval."
    DEFVAL  { 0 }
    ::= { frCircuitEntry  12 }

frCircuitExcessBurst OBJECT-TYPE
    SYNTAX  INTEGER (-2147483648..2147483647)
    ACCESS  read-write
    STATUS  mandatory
    DESCRIPTION
           "This variable indicates the maximum amount of
            uncommitted data bits that the network will attempt to
            deliver over the measurement interval.

            By default, if not configured when creating the entry,
            the Excess Information Burst Size is set to the value
            of ifSpeed."
    REFERENCE
           "This variable indicates the maximum amount of
            uncommitted data bits that the network will attempt to
            deliver over the measurement interval.

            By default, if not configured when creating the entry,
            the Excess Information Burst Size is set to the value
            of ifSpeed."
    ::= { frCircuitEntry  13 }

frCircuitThroughput OBJECT-TYPE
    SYNTAX  INTEGER (-2147483648..2147483647)
    ACCESS  read-write
    STATUS  mandatory
    DESCRIPTION
           "Throughput is the average number of 'Frame Relay
            Information Field' bits transferred per second across a
            user network interface in one direction, measured over
            the measurement interval.

            If the configured committed burst rate and throughput
            are both non-zero, the measurement interval

                T=frCircuitCommittedBurst/frCircuitThroughput.

            If the configured committed burst rate and throughput
            are both zero, the measurement interval
                       T=frCircuitExcessBurst/ifSpeed."
    REFERENCE
           "Throughput is the average number of 'Frame Relay
            Information Field' bits transferred per second across a
            user network interface in one direction, measured over
            the measurement interval.

            If the configured committed burst rate and throughput
            are both non-zero, the measurement interval

                T=frCircuitCommittedBurst/frCircuitThroughput.

            If the configured committed burst rate and throughput
            are both zero, the measurement interval
                       T=frCircuitExcessBurst/ifSpeed."
    DEFVAL  { 0 }
    ::= { frCircuitEntry  14 }

frCircuitMulticast OBJECT-TYPE
    SYNTAX  INTEGER {
    unicast(1),
    multicast(2)
}
    ACCESS  read-only
    STATUS  mandatory
    DESCRIPTION
           "This indicates whether this VC is used as a multicast
            VC or a single destination"
    ::= { frCircuitEntry  15 }

frCircuitType OBJECT-TYPE
    SYNTAX  INTEGER {
    static(1),
    dynamic(2)
}
    ACCESS  read-only
    STATUS  mandatory
    DESCRIPTION
           "Indication of whether the VC was manually created
            (static), or dynamically created (dynamic) via the data
            link control management interface."
    ::= { frCircuitEntry  16 }

frCircuitDiscards OBJECT-TYPE
    SYNTAX  Counter
    ACCESS  read-only
    STATUS  mandatory
    DESCRIPTION
           "The number of inbound frames dropped because of format
            errors, or because the VC is inactive."
    ::= { frCircuitEntry  17 }

frCircuitReceivedDEs OBJECT-TYPE
    SYNTAX  Counter
    ACCESS  read-only
    STATUS  mandatory
    DESCRIPTION
           "Number of frames received from the network indicating
            that they were eligible for discard since the virtual
            circuit was created.  This occurs when the remote DTE
            sets the DE flag, or when in remote DTE's switch
            detects that the frame was received as Excess Burst
            data."
    REFERENCE
           "Number of frames received from the network indicating
            that they were eligible for discard since the virtual
            circuit was created.  This occurs when the remote DTE
            sets the DE flag, or when in remote DTE's switch
            detects that the frame was received as Excess Burst
            data."
    ::= { frCircuitEntry  18 }

frCircuitSentDEs OBJECT-TYPE
    SYNTAX  Counter
    ACCESS  read-only
    STATUS  mandatory
    DESCRIPTION
           "Number of frames sent to the network in- dicating
            that  they  were eligible for discard since the virtual
            circuit  was  created.   This occurs when the local DTE
            sets the DE flag, indicating that during Network
            congestion situations those frames should be discarded
            in preference of other frames sent without the DE bit
            set."
    REFERENCE
           "Number of frames sent to the network in- dicating
            that  they  were eligible for discard since the virtual
            circuit  was  created.   This occurs when the local DTE
            sets the DE flag, indicating that during Network
            congestion situations those frames should be discarded
            in preference of other frames sent without the DE bit
            set."
    ::= { frCircuitEntry  19 }

frCircuitLogicalIfIndex OBJECT-TYPE
    SYNTAX  InterfaceIndex
    ACCESS  read-write
    STATUS  mandatory
    DESCRIPTION
           "Normally the same value as frDlcmiIfIndex, but
            different when an implementation associates a virtual
            ifEntry with a DLC or set of DLCs in order to associate
            higher layer objects such as the ipAddrEntry with a
            subset of the virtual circuits on a Frame Relay
            interface. The type of such ifEntries is defined by the
            higher layer object; for example, if PPP/Frame Relay is
            implemented, the ifType of this ifEntry would be PPP.
            If it is not so defined, as would be the case with an
            ipAddrEntry, it should be of type Other."
    ::= { frCircuitEntry  20 }

-- AKB RowStatus Objects removed --
-- AKB
-- AKB frCircuitRowStatus OBJECT-TYPE
-- AKB    SYNTAX  RowStatus
-- AKB    ACCESS  read-write
-- AKB    STATUS  mandatory
-- AKB    DESCRIPTION
-- AKB           " This object is used to create a new row or modify or
-- AKB            destroy an existing row in the manner described in the
-- AKB            definition of the RowStatus textual convention."
-- AKB    ::= { frCircuitEntry  21 }
-- AKB

frErrTable OBJECT-TYPE
    SYNTAX  SEQUENCE OF FrErrEntry
    ACCESS  not-accessible
    STATUS  mandatory
    DESCRIPTION
           "A table containing information about Errors on the
            Frame Relay interface."
-- changed from frameRelayDte to frame-relay
    ::= { frame-relay  3 }

frErrEntry OBJECT-TYPE
    SYNTAX  FrErrEntry
    ACCESS  not-accessible
    STATUS  mandatory
    DESCRIPTION
           "The error information for a single frame relay
            interface."
    INDEX   { frErrIfIndex }
    ::= { frErrTable  1 }

FrErrEntry ::=
    SEQUENCE {
        frErrIfIndex
            InterfaceIndex,

        frErrType
            INTEGER,

        frErrData
            OCTET STRING,

        frErrTime
            TimeTicks,  -- AKB TimeStamp to TimeTicks --

        frErrFaults
            Counter,

        frErrFaultTime
            TimeTicks   -- AKB TimeStamp to TimeTicks --
    }

frErrIfIndex OBJECT-TYPE
    SYNTAX  InterfaceIndex
    ACCESS  read-only
    STATUS  mandatory
    DESCRIPTION
           "The ifIndex Value of the corresponding ifEntry."
    ::= { frErrEntry  1 }

frErrType OBJECT-TYPE
    SYNTAX  INTEGER {
    unknownError(1),
    receiveShort(2),
    receiveLong(3),
    illegalAddress(4),
    unknownAddress(5),
    dlcmiProtoErr(6),
    dlcmiUnknownIE(7),
    dlcmiSequenceErr(8),
    dlcmiUnknownRpt(9),
    noErrorSinceReset(10)
}
    ACCESS  read-only
    STATUS  mandatory
    DESCRIPTION
           "The type of error that was last seen  on  this interface:

     receiveShort: frame was not long enough to allow
             demultiplexing - the address field was incomplete, or for
             virtual circuits using Multiprotocol over Frame Relay, the protocol
             identifier was missing or incomplete.

     receiveLong: frame exceeded maximum length configured for this interface.

     illegalAddress: address field did not match configured format.

     unknownAddress: frame received on a virtual circuit which was not active
                     or administratively disabled.

     dlcmiProtoErr: unspecified error occurred when attempting to interpret link
                     maintenance frame.

     dlcmiUnknownIE: link maintenance frame contained an Information Element
                     type which is not valid for the configured link maintenance
                     protocol.

     dlcmiSequenceErr: link maintenance frame contained a sequence number
                     number other than the expected value.

     dlcmiUnknownRpt: link maintenance frame contained a Report Type Information
                     Element whose value was not valid for the configured
                     link maintenance protocol.

     noErrorSinceReset: no errors have been detected since the last
                     cold start or warm start."
    ::= { frErrEntry  2 }

frErrData OBJECT-TYPE
    SYNTAX  OCTET STRING
    ACCESS  read-only
    STATUS  mandatory
    DESCRIPTION
           "An octet string containing as much of the error packet
            as possible.  As a minimum, it must contain the Q.922
            Address or as much as was delivered.  It is desirable
            to include all header and demultiplexing information."
    ::= { frErrEntry  3 }

frErrTime OBJECT-TYPE
    SYNTAX  TimeTicks  -- AKB TimeStamp to TimeTicks --
    ACCESS  read-only
    STATUS  mandatory
    DESCRIPTION
           "The value of sysUpTime at which the error was
            detected."
    ::= { frErrEntry  4 }

frErrFaults OBJECT-TYPE
    SYNTAX  Counter
    ACCESS  read-only
    STATUS  mandatory
    DESCRIPTION
           "The number of times the interface has gone down since
            it was initialized."
    ::= { frErrEntry  5 }

frErrFaultTime OBJECT-TYPE
    SYNTAX  TimeTicks  -- AKB TimeStamp to Time Ticks --
    ACCESS  read-only
    STATUS  mandatory
    DESCRIPTION
           "The value of sysUpTime at the time when the interface
            was taken down due to excessive errors.  Excessive
            errors is defined as the time when a DLCMI exceeds the
            frDlcmiErrorThreshold number of errors within
            frDlcmiMonitoredEvents. See FrDlcmiEntry for further
            details."
    ::= { frErrEntry  6 }

-- changed from frameRelayDTE to frame-relay
frameRelayTrapControl OBJECT IDENTIFIER ::= { frame-relay  4 }

frameRelayTraps OBJECT IDENTIFIER ::= { frame-relay  5 }

frTrapState OBJECT-TYPE
    SYNTAX  INTEGER {
    enabled(1),
    disabled(2)
}
    ACCESS  read-write
    STATUS  mandatory
    DESCRIPTION
           "This variable indicates whether the system produces
            the frDLCIStatusChange trap."
    DEFVAL  { disabled }
    ::= { frameRelayTrapControl  1 }

frDLCIStatusChange TRAP-TYPE
-- AKB Modified enteprise and variable to support v1 traps
    ENTERPRISE  frame-relay
    VARIABLES   { frCircuitIfIndex, frCircuitDlci, frCircuitState }
    DESCRIPTION
           "This trap indicates that the indicated Virtual Circuit
            has changed state.  It has either been created or
            invalidated, or has toggled between the active and
            inactive states.  If, however, the reason for the state
            change is due to the DLCMI going down, per-DLCI traps
            should not be generated."
    ::= 1

-- changed from frameRelayDTE to frame-relay
frConformance OBJECT IDENTIFIER ::= { frame-relay  6 }

frGroups OBJECT IDENTIFIER ::= { frConformance  1 }

frCompliances OBJECT IDENTIFIER ::= { frConformance  2 }

frCompliance OBJECT IDENTIFIER ::= { frCompliances  1 }

frPortGroup OBJECT IDENTIFIER ::= { frGroups  1 }

frCircuitGroup OBJECT IDENTIFIER ::= { frGroups  2 }

frTrapGroup OBJECT IDENTIFIER ::= { frGroups  4 }

END
