-- automatically generated by mosy 7.2 #166 (yukinojo), do not edit!

-- This mib is equivalent to RFC 1850 except that it has been converted to
-- Version 1 for Xylan.

OSPF-MIB DEFINITIONS ::= BEGIN

IMPORTS
--    TruthValue
--        FROM RFC1253-MIB
    OBJECT-TYPE
        FROM RFC-1212
    Counter, IpAddress
        FROM RFC1155-SMI
    mib-2
        FROM RFC1213-MIB
    RowStatus
        FROM SNMPv2-TC
    Gauge32
        FROM SNMPv2-SMI;

-- created from ospf (9501201225Z)

ospf OBJECT IDENTIFIER ::= { mib-2  14 }

AreaID ::=
    IpAddress

RouterID ::=
    IpAddress

Metric ::=
    INTEGER (-2147483648..2147483647)

BigMetric ::=
    INTEGER (-2147483648..2147483647)

TruthValue ::=
	INTEGER { true (1), false (2) }

Status ::=
    INTEGER {
 enabled(1),
 disabled(2)
 }

PositiveInteger ::=
    INTEGER (-2147483648..2147483647)

HelloRange ::=
    INTEGER (-2147483648..2147483647)

UpToMaxAge ::=
    INTEGER (-2147483648..2147483647)

InterfaceIndex ::=
    INTEGER  

DesignatedRouterPriority ::=
    INTEGER (-2147483648..2147483647)

TOSType ::=
    INTEGER (-2147483648..2147483647)

ospfGeneralGroup OBJECT IDENTIFIER ::= { ospf  1 }

ospfRouterId OBJECT-TYPE
    SYNTAX  RouterID
    ACCESS  read-write
    STATUS  mandatory
    DESCRIPTION
           "A  32-bit  integer  uniquely  identifying  the
           router in the Autonomous System.


           By  convention,  to  ensure  uniqueness,   this
           should  default  to  the  value  of  one of the
           router's IP interface addresses."
    REFERENCE
           "OSPF Version 2, C.1 Global parameters"
    ::= { ospfGeneralGroup  1 }

ospfAdminStat OBJECT-TYPE
    SYNTAX  Status
    ACCESS  read-write
    STATUS  mandatory
    DESCRIPTION
           "The  administrative  status  of  OSPF  in  the
           router.   The  value 'enabled' denotes that the
           OSPF Process is active on at least  one  inter-
           face;  'disabled'  disables  it  on  all inter-
           faces."
    ::= { ospfGeneralGroup  2 }

ospfVersionNumber OBJECT-TYPE
    SYNTAX  INTEGER {
                 version2(2)
               }
    ACCESS  read-only
    STATUS  mandatory
    DESCRIPTION
           "The current version number of the OSPF  proto-
           col is 2."
    REFERENCE
           "OSPF Version 2, Title"
    ::= { ospfGeneralGroup  3 }

ospfAreaBdrRtrStatus OBJECT-TYPE
    SYNTAX  TruthValue
    ACCESS  read-only
    STATUS  mandatory
    DESCRIPTION
           "A flag to note whether this router is an  area
           border router."
    REFERENCE
           "OSPF Version 2, Section 3 Splitting the AS into
          Areas"
    ::= { ospfGeneralGroup  4 }

ospfASBdrRtrStatus OBJECT-TYPE
    SYNTAX  TruthValue
    ACCESS  read-write
    STATUS  mandatory
    DESCRIPTION
           "A flag to note whether this router is  config-
           ured as an Autonomous System border router."
    REFERENCE
           "OSPF Version 2, Section 3.3  Classification  of
          routers"
    ::= { ospfGeneralGroup  5 }

ospfExternLsaCount OBJECT-TYPE
    SYNTAX  Gauge32
    ACCESS  read-only
    STATUS  mandatory
    DESCRIPTION
           "The number of external (LS type 5)  link-state
           advertisements in the link-state database."
    REFERENCE
           "OSPF Version 2, Appendix A.4.5 AS external link
          advertisements"
    ::= { ospfGeneralGroup  6 }

ospfExternLsaCksumSum OBJECT-TYPE
    SYNTAX  INTEGER (-2147483648..2147483647)
    ACCESS  read-only
    STATUS  mandatory
    DESCRIPTION
           "The 32-bit unsigned sum of the LS checksums of
           the  external  link-state  advertisements  con-
           tained in the link-state  database.   This  sum
           can  be  used  to determine if there has been a
           change in a router's link state  database,  and
           to  compare  the  link-state  database  of  two
           routers."
    ::= { ospfGeneralGroup  7 }

ospfTOSSupport OBJECT-TYPE
    SYNTAX  TruthValue
    ACCESS  read-write
    STATUS  mandatory
    DESCRIPTION
           "The router's support for type-of-service rout-
           ing."
    REFERENCE
           "OSPF Version 2,  Appendix  F.1.2  Optional  TOS
          support"
    ::= { ospfGeneralGroup  8 }

ospfOriginateNewLsas OBJECT-TYPE
    SYNTAX  Counter
    ACCESS  read-only
    STATUS  mandatory
    DESCRIPTION
           "The number of  new  link-state  advertisements
           that  have been originated.  This number is in-
           cremented each time the router originates a new
           LSA."
    ::= { ospfGeneralGroup  9 }

ospfRxNewLsas OBJECT-TYPE
    SYNTAX  Counter
    ACCESS  read-only
    STATUS  mandatory
    DESCRIPTION
           "The number of  link-state  advertisements  re-
           ceived  determined  to  be  new instantiations.
           This number does not include  newer  instantia-
           tions  of self-originated link-state advertise-
           ments."
    ::= { ospfGeneralGroup  10 }

ospfExtLsdbLimit OBJECT-TYPE
    SYNTAX  INTEGER (-2147483648..2147483647)
    ACCESS  read-write
    STATUS  mandatory
    DESCRIPTION
           "The  maximum   number   of   non-default   AS-
           external-LSAs entries that can be stored in the
           link-state database.  If the value is -1,  then
           there is no limit.


           When the number of non-default AS-external-LSAs
           in   a  router's  link-state  database  reaches
           ospfExtLsdbLimit, the router  enters  Overflow-
           State.   The   router  never  holds  more  than
           ospfExtLsdbLimit  non-default  AS-external-LSAs
           in  its  database. OspfExtLsdbLimit MUST be set
           identically in all routers attached to the OSPF
           backbone  and/or  any regular OSPF area. (i.e.,
           OSPF stub areas and NSSAs are excluded)."
    DEFVAL  { -1 }
    ::= { ospfGeneralGroup  11 }

ospfMulticastExtensions OBJECT-TYPE
    SYNTAX  INTEGER (-2147483648..2147483647)
    ACCESS  read-write
    STATUS  mandatory
    DESCRIPTION
           "A Bit Mask indicating whether  the  router  is
           forwarding  IP  multicast  (Class  D) datagrams
           based on the algorithms defined in  the  Multi-
           cast Extensions to OSPF.


           Bit 0, if set, indicates that  the  router  can
           forward  IP multicast datagrams in the router's
           directly attached areas (called intra-area mul-
           ticast routing).


           Bit 1, if set, indicates that  the  router  can
           forward  IP  multicast  datagrams  between OSPF
           areas (called inter-area multicast routing).


           Bit 2, if set, indicates that  the  router  can
           forward  IP  multicast  datagrams between Auto-
           nomous Systems (called inter-AS multicast rout-
           ing).


           Only certain combinations of bit  settings  are
           allowed,  namely: 0 (no multicast forwarding is
           enabled), 1 (intra-area multicasting  only),  3
           (intra-area  and  inter-area  multicasting),  5
           (intra-area and inter-AS  multicasting)  and  7
           (multicasting  everywhere). By default, no mul-
           ticast forwarding is enabled."
    DEFVAL  { 0 }
    ::= { ospfGeneralGroup  12 }

ospfExitOverflowInterval OBJECT-TYPE
    SYNTAX  PositiveInteger
    ACCESS  read-write
    STATUS  mandatory
    DESCRIPTION
           "The number of  seconds  that,  after  entering
           OverflowState,  a  router will attempt to leave
           OverflowState. This allows the router to  again
           originate  non-default  AS-external-LSAs.  When
           set to 0, the router will not  leave  Overflow-
           State until restarted."
    DEFVAL  { 0 }
    ::= { ospfGeneralGroup  13 }

ospfDemandExtensions OBJECT-TYPE
    SYNTAX  TruthValue
    ACCESS  read-write
    STATUS  mandatory
    DESCRIPTION
           "The router's support for demand routing."
    REFERENCE
           "OSPF Version 2, Appendix on Demand Routing"
    ::= { ospfGeneralGroup  14 }

ospfAreaTable OBJECT-TYPE
    SYNTAX  SEQUENCE OF OspfAreaEntry
    ACCESS  not-accessible
    STATUS  mandatory
    DESCRIPTION
           "Information describing the configured  parame-
           ters  and cumulative statistics of the router's
           attached areas."
    REFERENCE
           "OSPF Version 2, Section 6  The Area Data Struc-
          ture"
    ::= { ospf  2 }

ospfAreaEntry OBJECT-TYPE
    SYNTAX  OspfAreaEntry
    ACCESS  not-accessible
    STATUS  mandatory
    DESCRIPTION
           "Information describing the configured  parame-
           ters  and  cumulative  statistics of one of the
           router's attached areas."
    INDEX   { ospfAreaId }
    ::= { ospfAreaTable  1 }

OspfAreaEntry ::=
    SEQUENCE {
        ospfAreaId
            AreaID,

        ospfAuthType
            INTEGER (-2147483648..2147483647),

        ospfImportAsExtern
            INTEGER,

        ospfSpfRuns
            Counter,

        ospfAreaBdrRtrCount
            Gauge32,

        ospfAsBdrRtrCount
            Gauge32,

        ospfAreaLsaCount
            Gauge32,

        ospfAreaLsaCksumSum
            INTEGER (-2147483648..2147483647),

        ospfAreaSummary
            INTEGER,

        ospfAreaStatus
            RowStatus
    }

ospfAreaId OBJECT-TYPE
    SYNTAX  AreaID
    ACCESS  read-only
    STATUS  mandatory
    DESCRIPTION
           "A 32-bit integer uniquely identifying an area.
           Area ID 0.0.0.0 is used for the OSPF backbone."
    REFERENCE
           "OSPF Version 2, Appendix C.2 Area parameters"
    ::= { ospfAreaEntry  1 }

ospfAuthType OBJECT-TYPE
    SYNTAX  INTEGER (-2147483648..2147483647)
    ACCESS  read-write
    STATUS  obsolete
    DESCRIPTION
           "The authentication type specified for an area.
           Additional authentication types may be assigned
           locally on a per Area basis. No Authentication (0), 
           Simple password (1) and MD5 crypto checksum (2) are 
           currently the only valid values."
    REFERENCE
           "OSPF Version 2, Appendix E Authentication"
    DEFVAL  { 0 }
    ::= { ospfAreaEntry  2 }

ospfImportAsExtern OBJECT-TYPE
    SYNTAX  INTEGER {
                 importExternal(1),
                 importNoExternal(2),
                 importNssa(3)
               }
    ACCESS  read-write
    STATUS  mandatory
    DESCRIPTION
           "The area's support for importing  AS  external
           link- state advertisements."
    REFERENCE
           "OSPF Version 2, Appendix C.2 Area parameters"
    DEFVAL  { importExternal }
    ::= { ospfAreaEntry  3 }

ospfSpfRuns OBJECT-TYPE
    SYNTAX  Counter
    ACCESS  read-only
    STATUS  mandatory
    DESCRIPTION
           "The number of times that the intra-area  route
           table  has  been  calculated  using this area's
           link-state database.  This  is  typically  done
           using Dijkstra's algorithm."
    ::= { ospfAreaEntry  4 }

ospfAreaBdrRtrCount OBJECT-TYPE
    SYNTAX  Gauge32
    ACCESS  read-only
    STATUS  mandatory
    DESCRIPTION
           "The total number of area border routers reach-
           able within this area.  This is initially zero,
           and is calculated in each SPF Pass."
    ::= { ospfAreaEntry  5 }

ospfAsBdrRtrCount OBJECT-TYPE
    SYNTAX  Gauge32
    ACCESS  read-only
    STATUS  mandatory
    DESCRIPTION
           "The total number of Autonomous  System  border
           routers  reachable  within  this area.  This is
           initially zero, and is calculated in  each  SPF
           Pass."
    ::= { ospfAreaEntry  6 }

ospfAreaLsaCount OBJECT-TYPE
    SYNTAX  Gauge32
    ACCESS  read-only
    STATUS  mandatory
    DESCRIPTION
           "The total number of link-state  advertisements
           in  this  area's link-state database, excluding
           AS External LSA's."
    ::= { ospfAreaEntry  7 }

ospfAreaLsaCksumSum OBJECT-TYPE
    SYNTAX  INTEGER (-2147483648..2147483647)
    ACCESS  read-only
    STATUS  mandatory
    DESCRIPTION
           "The 32-bit unsigned sum of the link-state  ad-
           vertisements'  LS  checksums  contained in this
           area's link-state database.  This sum  excludes
           external (LS type 5) link-state advertisements.
           The sum can be used to determine if  there  has
           been  a  change  in a router's link state data-
           base, and to compare the link-state database of
           two routers."
    DEFVAL  { 0 }
    ::= { ospfAreaEntry  8 }

ospfAreaSummary OBJECT-TYPE
    SYNTAX  INTEGER {
                 noAreaSummary(1),
                 sendAreaSummary(2)
               }
    ACCESS  read-write
    STATUS  mandatory
    DESCRIPTION
           "The variable ospfAreaSummary controls the  im-
           port  of  summary LSAs into stub areas.  It has
           no effect on other areas.


           If it is noAreaSummary, the router will neither
           originate  nor  propagate summary LSAs into the
           stub area.  It will rely entirely  on  its  de-
           fault route.


           If it is sendAreaSummary, the router will  both
           summarize and propagate summary LSAs."
    DEFVAL  { noAreaSummary }
    ::= { ospfAreaEntry  9 }

ospfAreaStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfAreaEntry  10 }

ospfStubAreaTable OBJECT-TYPE
    SYNTAX  SEQUENCE OF OspfStubAreaEntry
    ACCESS  not-accessible
    STATUS  mandatory
    DESCRIPTION
           "The set of metrics that will be advertised  by
           a default Area Border Router into a stub area."
    REFERENCE
           "OSPF Version 2, Appendix C.2, Area Parameters"
    ::= { ospf  3 }

ospfStubAreaEntry OBJECT-TYPE
    SYNTAX  OspfStubAreaEntry
    ACCESS  not-accessible
    STATUS  mandatory
    DESCRIPTION
           "The metric for a given Type  of  Service  that
           will  be  advertised  by  a default Area Border
           Router into a stub area."
    REFERENCE
           "OSPF Version 2, Appendix C.2, Area Parameters"
    INDEX   { ospfStubAreaId,  ospfStubTOS }
    ::= { ospfStubAreaTable  1 }

OspfStubAreaEntry ::=
    SEQUENCE {
        ospfStubAreaId
            AreaID,

        ospfStubTOS
            TOSType,

        ospfStubMetric
            BigMetric,

        ospfStubStatus
            RowStatus,

        ospfStubMetricType
            INTEGER
    }

ospfStubAreaId OBJECT-TYPE
    SYNTAX  AreaID
    ACCESS  read-only
    STATUS  mandatory
    DESCRIPTION
           "The 32 bit identifier for the Stub  Area.   On
           creation,  this  can  be  derived  from the in-
           stance."
    ::= { ospfStubAreaEntry  1 }

ospfStubTOS OBJECT-TYPE
    SYNTAX  TOSType
    ACCESS  read-only
    STATUS  mandatory
    DESCRIPTION
           "The  Type  of  Service  associated  with   the
           metric.   On creation, this can be derived from
           the instance."
    ::= { ospfStubAreaEntry  2 }

ospfStubMetric OBJECT-TYPE
    SYNTAX  BigMetric
    ACCESS  read-write
    STATUS  mandatory
    DESCRIPTION
           "The metric value applied at the indicated type
           of  service.  By default, this equals the least
           metric at the type of service among the  inter-
           faces to other areas."
    ::= { ospfStubAreaEntry  3 }

ospfStubStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfStubAreaEntry  4 }

ospfStubMetricType OBJECT-TYPE
    SYNTAX  INTEGER {
                 ospfMetric(1),
                 comparableCost(2),
                 nonComparable(3)
               }
    ACCESS  read-write
    STATUS  mandatory
    DESCRIPTION
           "This variable displays the type of metric  ad-
           vertised as a default route."
    DEFVAL  { ospfMetric }
    ::= { ospfStubAreaEntry  5 }

ospfLsdbTable OBJECT-TYPE
    SYNTAX  SEQUENCE OF OspfLsdbEntry
    ACCESS  not-accessible
    STATUS  mandatory
    DESCRIPTION
           "The OSPF Process's Link State Database."
    REFERENCE
           "OSPF Version 2, Section 12  Link  State  Adver-
          tisements"
    ::= { ospf  4 }

ospfLsdbEntry OBJECT-TYPE
    SYNTAX  OspfLsdbEntry
    ACCESS  not-accessible
    STATUS  mandatory
    DESCRIPTION
           "A single Link State Advertisement."
    INDEX   {
                 ospfLsdbAreaId,
                 ospfLsdbType,
                 ospfLsdbLsid,
                 ospfLsdbRouterId
               }
    ::= { ospfLsdbTable  1 }

OspfLsdbEntry ::=
    SEQUENCE {
        ospfLsdbAreaId
            AreaID,

        ospfLsdbType
            INTEGER,

        ospfLsdbLsid
            IpAddress,

        ospfLsdbRouterId
            RouterID,

        ospfLsdbSequence
            INTEGER (-2147483648..2147483647),

        ospfLsdbAge
            INTEGER (-2147483648..2147483647),

        ospfLsdbChecksum
            INTEGER (-2147483648..2147483647),

        ospfLsdbAdvertisement
            OCTET STRING
    }

ospfLsdbAreaId OBJECT-TYPE
    SYNTAX  AreaID
    ACCESS  read-only
    STATUS  mandatory
    DESCRIPTION
           "The 32 bit identifier of the Area  from  which
           the LSA was received."
    REFERENCE
           "OSPF Version 2, Appendix C.2 Area parameters"
    ::= { ospfLsdbEntry  1 }

ospfLsdbType OBJECT-TYPE
    SYNTAX  INTEGER {
                 routerLink(1),
                 networkLink(2),
                 summaryLink(3),
                 asSummaryLink(4),
                 asExternalLink(5),
                 multicastLink(6),
                 nssaExternalLink(7)
               }
    ACCESS  read-only
    STATUS  mandatory
    DESCRIPTION
           "The type  of  the  link  state  advertisement.
           Each  link state type has a separate advertise-
           ment format."
    REFERENCE
           "OSPF Version 2, Appendix A.4.1 The  Link  State
          Advertisement header"
    ::= { ospfLsdbEntry  2 }

ospfLsdbLsid OBJECT-TYPE
    SYNTAX  IpAddress
    ACCESS  read-only
    STATUS  mandatory
    DESCRIPTION
           "The Link State ID is an LS Type Specific field
           containing either a Router ID or an IP Address;
           it identifies the piece of the  routing  domain
           that is being described by the advertisement."
    REFERENCE
           "OSPF Version 2, Section 12.1.4 Link State ID"
    ::= { ospfLsdbEntry  3 }

ospfLsdbRouterId OBJECT-TYPE
    SYNTAX  RouterID
    ACCESS  read-only
    STATUS  mandatory
    DESCRIPTION
           "The 32 bit number that uniquely identifies the
           originating router in the Autonomous System."
    REFERENCE
           "OSPF Version 2, Appendix C.1 Global parameters"
    ::= { ospfLsdbEntry  4 }

ospfLsdbSequence OBJECT-TYPE
    SYNTAX  INTEGER (-2147483648..2147483647)
    ACCESS  read-only
    STATUS  mandatory
    DESCRIPTION
           "The sequence number field is a  signed  32-bit
           integer.   It  is used to detect old and dupli-
           cate link state advertisements.  The  space  of
           sequence  numbers  is  linearly  ordered.   The
           larger the sequence number the more recent  the
           advertisement."
    REFERENCE
           "OSPF Version  2,  Section  12.1.6  LS  sequence
          number"
    ::= { ospfLsdbEntry  5 }

ospfLsdbAge OBJECT-TYPE
    SYNTAX  INTEGER (-2147483648..2147483647)
    ACCESS  read-only
    STATUS  mandatory
    DESCRIPTION
           "This field is the age of the link state adver-
           tisement in seconds."
    REFERENCE
           "OSPF Version 2, Section 12.1.1 LS age"
    ::= { ospfLsdbEntry  6 }

ospfLsdbChecksum OBJECT-TYPE
    SYNTAX  INTEGER (-2147483648..2147483647)
    ACCESS  read-only
    STATUS  mandatory
    DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
    REFERENCE
           "OSPF Version 2, Section 12.1.7 LS checksum"
    ::= { ospfLsdbEntry  7 }

ospfLsdbAdvertisement OBJECT-TYPE
    SYNTAX  OCTET STRING
    ACCESS  read-only
    STATUS  mandatory
    DESCRIPTION
           "The entire Link State Advertisement, including
           its header."
    REFERENCE
           "OSPF Version 2, Section 12  Link  State  Adver-
          tisements"
    ::= { ospfLsdbEntry  8 }

ospfAreaRangeTable OBJECT-TYPE
    SYNTAX  SEQUENCE OF OspfAreaRangeEntry
    ACCESS  not-accessible
    STATUS  obsolete
    DESCRIPTION
           "A range if IP addresses  specified  by  an  IP
           address/IP  network  mask  pair.   For example,
           class B address range of X.X.X.X with a network
           mask  of  255.255.0.0 includes all IP addresses
           from X.X.0.0 to X.X.255.255"
    REFERENCE
           "OSPF Version 2, Appendix C.2  Area parameters"
    ::= { ospf  5 }

ospfAreaRangeEntry OBJECT-TYPE
    SYNTAX  OspfAreaRangeEntry
    ACCESS  not-accessible
    STATUS  obsolete
    DESCRIPTION
           "A range if IP addresses  specified  by  an  IP
           address/IP  network  mask  pair.   For example,
           class B address range of X.X.X.X with a network
           mask  of  255.255.0.0 includes all IP addresses
           from X.X.0.0 to X.X.255.255"
    REFERENCE
           "OSPF Version 2, Appendix C.2  Area parameters"
    INDEX   { ospfAreaRangeAreaId,  ospfAreaRangeNet }
    ::= { ospfAreaRangeTable  1 }

OspfAreaRangeEntry ::=
    SEQUENCE {
        ospfAreaRangeAreaId
            AreaID,

        ospfAreaRangeNet
            IpAddress,

        ospfAreaRangeMask
            IpAddress,

        ospfAreaRangeStatus
            RowStatus,

        ospfAreaRangeEffect
            INTEGER
    }

ospfAreaRangeAreaId OBJECT-TYPE
    SYNTAX  AreaID
    ACCESS  read-only
    STATUS  obsolete
    DESCRIPTION
           "The Area the Address  Range  is  to  be  found
           within."
    REFERENCE
           "OSPF Version 2, Appendix C.2 Area parameters"
    ::= { ospfAreaRangeEntry  1 }

ospfAreaRangeNet OBJECT-TYPE
    SYNTAX  IpAddress
    ACCESS  read-only
    STATUS  obsolete
    DESCRIPTION
           "The IP Address of the Net or Subnet  indicated
           by the range."
    REFERENCE
           "OSPF Version 2, Appendix C.2 Area parameters"
    ::= { ospfAreaRangeEntry  2 }

ospfAreaRangeMask OBJECT-TYPE
    SYNTAX  IpAddress
    ACCESS  read-write
    STATUS  obsolete
    DESCRIPTION
           "The Subnet Mask that pertains to  the  Net  or
           Subnet."
    REFERENCE
           "OSPF Version 2, Appendix C.2 Area parameters"
    ::= { ospfAreaRangeEntry  3 }

ospfAreaRangeStatus OBJECT-TYPE
    SYNTAX  RowStatus
    ACCESS  read-write
    STATUS  obsolete
    DESCRIPTION
           "This variable displays the status of  the  en-
           try.  Setting it to 'invalid' has the effect of
           rendering it inoperative.  The internal  effect
           (row removal) is implementation dependent."
    ::= { ospfAreaRangeEntry  4 }

ospfAreaRangeEffect OBJECT-TYPE
    SYNTAX  INTEGER {
                 advertiseMatching(1),
                 doNotAdvertiseMatching(2)
               }
    ACCESS  read-write
    STATUS  obsolete
    DESCRIPTION
           "Subnets subsumed by ranges either trigger  the
           advertisement  of the indicated summary (adver-
           tiseMatching), or result in  the  subnet's  not
           being advertised at all outside the area."
    DEFVAL  { advertiseMatching }
    ::= { ospfAreaRangeEntry  5 }

ospfHostTable OBJECT-TYPE
    SYNTAX  SEQUENCE OF OspfHostEntry
    ACCESS  not-accessible
    STATUS  mandatory
    DESCRIPTION
           "The list of Hosts, and their metrics, that the
           router will advertise as host routes."
    REFERENCE
           "OSPF Version 2, Appendix C.6  Host route param-
          eters"
    ::= { ospf  6 }

ospfHostEntry OBJECT-TYPE
    SYNTAX  OspfHostEntry
    ACCESS  not-accessible
    STATUS  mandatory
    DESCRIPTION
           "A metric to be advertised, for a given type of
           service, when a given host is reachable."
    INDEX   { ospfHostIpAddress,  ospfHostTOS }
    ::= { ospfHostTable  1 }

OspfHostEntry ::=
    SEQUENCE {
        ospfHostIpAddress
            IpAddress,

        ospfHostTOS
            TOSType,

        ospfHostMetric
            Metric,

        ospfHostStatus
            RowStatus,

        ospfHostAreaID
            AreaID
    }

ospfHostIpAddress OBJECT-TYPE
    SYNTAX  IpAddress
    ACCESS  read-only
    STATUS  mandatory
    DESCRIPTION
           "The IP Address of the Host."
    REFERENCE
           "OSPF Version 2, Appendix C.6 Host route parame-
          ters"
    ::= { ospfHostEntry  1 }

ospfHostTOS OBJECT-TYPE
    SYNTAX  TOSType
    ACCESS  read-only
    STATUS  mandatory
    DESCRIPTION
           "The Type of Service of the route being config-
           ured."
    REFERENCE
           "OSPF Version 2, Appendix C.6 Host route parame-
          ters"
    ::= { ospfHostEntry  2 }

ospfHostMetric OBJECT-TYPE
    SYNTAX  Metric
    ACCESS  read-write
    STATUS  mandatory
    DESCRIPTION
           "The Metric to be advertised."
    REFERENCE
           "OSPF Version 2, Appendix C.6 Host route parame-
          ters"
    ::= { ospfHostEntry  3 }

ospfHostStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfHostEntry  4 }

ospfHostAreaID OBJECT-TYPE
    SYNTAX  AreaID
    ACCESS  read-only
    STATUS  mandatory
    DESCRIPTION
           "The Area the Host Entry is to be found within.
           By  default, the area that a subsuming OSPF in-
           terface is in, or 0.0.0.0"
    REFERENCE
           "OSPF Version 2, Appendix C.2 Area parameters"
    ::= { ospfHostEntry  5 }

ospfIfTable OBJECT-TYPE
    SYNTAX  SEQUENCE OF OspfIfEntry
    ACCESS  not-accessible
    STATUS  mandatory
    DESCRIPTION
           "The OSPF Interface Table describes the  inter-
           faces from the viewpoint of OSPF."
    REFERENCE
           "OSPF Version 2, Appendix C.3  Router  interface
          parameters"
    ::= { ospf  7 }

ospfIfEntry OBJECT-TYPE
    SYNTAX  OspfIfEntry
    ACCESS  not-accessible
    STATUS  mandatory
    DESCRIPTION
           "The OSPF Interface Entry describes one  inter-
           face from the viewpoint of OSPF."
    INDEX   { ospfIfIpAddress,  ospfAddressLessIf }
    ::= { ospfIfTable  1 }

OspfIfEntry ::=
    SEQUENCE {
        ospfIfIpAddress
            IpAddress,

        ospfAddressLessIf
            INTEGER (-2147483648..2147483647),

        ospfIfAreaId
            AreaID,

        ospfIfType
            INTEGER,

        ospfIfAdminStat
            Status,

        ospfIfRtrPriority
            DesignatedRouterPriority,

        ospfIfTransitDelay
            UpToMaxAge,

        ospfIfRetransInterval
            UpToMaxAge,

        ospfIfHelloInterval
            HelloRange,

        ospfIfRtrDeadInterval
            PositiveInteger,

        ospfIfPollInterval
            PositiveInteger,

        ospfIfState
            INTEGER,

        ospfIfDesignatedRouter
            IpAddress,

        ospfIfBackupDesignatedRouter
            IpAddress,

        ospfIfEvents
            Counter,

        ospfIfAuthType
            INTEGER,

        ospfIfAuthKey
            OCTET STRING,

        ospfIfStatus
            RowStatus,

        ospfIfMulticastForwarding
            INTEGER,

        ospfIfDemand
            TruthValue
    }

ospfIfIpAddress OBJECT-TYPE
    SYNTAX  IpAddress
    ACCESS  read-only
    STATUS  mandatory
    DESCRIPTION
           "The IP address of this OSPF interface."
    ::= { ospfIfEntry  1 }

ospfAddressLessIf OBJECT-TYPE
    SYNTAX  INTEGER (-2147483648..2147483647)
    ACCESS  read-only
    STATUS  mandatory
    DESCRIPTION
           "For the purpose of easing  the  instancing  of
           addressed   and  addressless  interfaces;  This
           variable takes the value 0 on  interfaces  with
           IP  Addresses,  and  the corresponding value of
           ifIndex for interfaces having no IP Address."
    ::= { ospfIfEntry  2 }

ospfIfAreaId OBJECT-TYPE
    SYNTAX  AreaID
    ACCESS  read-write
    STATUS  mandatory
    DESCRIPTION
           "A 32-bit integer uniquely identifying the area
           to  which  the  interface  connects.   Area  ID
           0.0.0.0 is used for the OSPF backbone."
    DEFVAL  { 0 }
    ::= { ospfIfEntry  3 }

ospfIfType OBJECT-TYPE
    SYNTAX  INTEGER {
                 broadcast(1),
                 nbma(2),
                 pointToPoint(3),
                 pointToMultipoint(5)
               }
    ACCESS  read-write
    STATUS  mandatory
    DESCRIPTION
           "The OSPF interface type.


           By way of a default, this field may be intuited
           from the corresponding value of ifType.  Broad-
           cast LANs, such as  Ethernet  and  IEEE  802.5,
           take  the  value  'broadcast', X.25 and similar
           technologies take the value 'nbma',  and  links
           that  are  definitively point to point take the
           value 'pointToPoint'."
    ::= { ospfIfEntry  4 }

ospfIfAdminStat OBJECT-TYPE
    SYNTAX  Status
    ACCESS  read-write
    STATUS  mandatory
    DESCRIPTION
           "The OSPF  interface's  administrative  status.
           The  value formed on the interface, and the in-
           terface will be advertised as an internal route
           to  some  area.   The  value 'disabled' denotes
           that the interface is external to OSPF."
    DEFVAL  { enabled }
    ::= { ospfIfEntry  5 }

ospfIfRtrPriority OBJECT-TYPE
    SYNTAX  DesignatedRouterPriority
    ACCESS  read-write
    STATUS  mandatory
    DESCRIPTION
           "The  priority  of  this  interface.   Used  in
           multi-access  networks,  this  field is used in
           the designated router election algorithm.   The
           value 0 signifies that the router is not eligi-
           ble to become the  designated  router  on  this
           particular  network.   In the event of a tie in
           this value, routers will use their Router ID as
           a tie breaker."
    DEFVAL  { 1 }
    ::= { ospfIfEntry  6 }

ospfIfTransitDelay OBJECT-TYPE
    SYNTAX  UpToMaxAge
    ACCESS  read-write
    STATUS  mandatory
    DESCRIPTION
           "The estimated number of seconds  it  takes  to
           transmit  a  link state update packet over this
           interface."
    DEFVAL  { 1 }
    ::= { ospfIfEntry  7 }

ospfIfRetransInterval OBJECT-TYPE
    SYNTAX  UpToMaxAge
    ACCESS  read-write
    STATUS  mandatory
    DESCRIPTION
           "The number of seconds between  link-state  ad-
           vertisement  retransmissions,  for  adjacencies
           belonging to this  interface.   This  value  is
           also used when retransmitting database descrip-
           tion and link-state request packets."
    DEFVAL  { 5 }
    ::= { ospfIfEntry  8 }

ospfIfHelloInterval OBJECT-TYPE
    SYNTAX  HelloRange
    ACCESS  read-write
    STATUS  mandatory
    DESCRIPTION
           "The length of time, in  seconds,  between  the
           Hello  packets that the router sends on the in-
           terface.  This value must be the same  for  all
           routers attached to a common network."
    DEFVAL  { 10 }
    ::= { ospfIfEntry  9 }

ospfIfRtrDeadInterval OBJECT-TYPE
    SYNTAX  PositiveInteger
    ACCESS  read-write
    STATUS  mandatory
    DESCRIPTION
           "The number of seconds that  a  router's  Hello
           packets  have  not been seen before it's neigh-
           bors declare the router down.  This  should  be
           some  multiple  of  the  Hello  interval.  This
           value must be the same for all routers attached
           to a common network."
    DEFVAL  { 40 }
    ::= { ospfIfEntry  10 }

ospfIfPollInterval OBJECT-TYPE
    SYNTAX  PositiveInteger
    ACCESS  read-write
    STATUS  mandatory
    DESCRIPTION
           "The larger time interval, in seconds,  between
           the  Hello  packets  sent  to  an inactive non-
           broadcast multi- access neighbor."
    DEFVAL  { 120 }
    ::= { ospfIfEntry  11 }

ospfIfState OBJECT-TYPE
    SYNTAX  INTEGER {
                 down(1),
                 loopback(2),
                 waiting(3),
                 pointToPoint(4),
                 designatedRouter(5),
                 backupDesignatedRouter(6),
                 otherDesignatedRouter(7)
               }
    ACCESS  read-only
    STATUS  mandatory
    DESCRIPTION
           "The OSPF Interface State."
    DEFVAL  { down }
    ::= { ospfIfEntry  12 }

ospfIfDesignatedRouter OBJECT-TYPE
    SYNTAX  IpAddress
    ACCESS  read-only
    STATUS  mandatory
    DESCRIPTION
           "The IP Address of the Designated Router."
    DEFVAL  { 0 }
    ::= { ospfIfEntry  13 }

ospfIfBackupDesignatedRouter OBJECT-TYPE
    SYNTAX  IpAddress
    ACCESS  read-only
    STATUS  mandatory
    DESCRIPTION
           "The  IP  Address  of  the  Backup   Designated
           Router."
    DEFVAL  { 0 }
    ::= { ospfIfEntry  14 }

ospfIfEvents OBJECT-TYPE
    SYNTAX  Counter
    ACCESS  read-only
    STATUS  mandatory
    DESCRIPTION
           "The number of times this  OSPF  interface  has
           changed its state, or an error has occurred."
    ::= { ospfIfEntry  15 }

ospfIfAuthKey OBJECT-TYPE
    SYNTAX  OCTET STRING
    ACCESS  read-write
    STATUS  mandatory
    DESCRIPTION
           "The Authentication Key.  If the Area's Author-
           ization  Type  is  simplePassword,  and the key
           length is shorter than 8 octets, the agent will
           left adjust and zero fill to 8 octets.


           Note that unauthenticated  interfaces  need  no
           authentication key, and simple password authen-
           tication cannot use a key of more  than  8  oc-
           tets.  Larger keys are useful only with authen-
           tication mechanisms not specified in this docu-
           ment.


           When read, ospfIfAuthKey always returns an  Oc-
           tet String of length zero."
    REFERENCE
           "OSPF Version 2, Section 9  The  Interface  Data
          Structure"
--    DEFVAL  { 0 }
    ::= { ospfIfEntry  16 }

ospfIfStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfIfEntry  17 }

ospfIfMulticastForwarding OBJECT-TYPE
    SYNTAX  INTEGER {
                 blocked(1),
                 multicast(2),
                 unicast(3)
               }
    ACCESS  read-write
    STATUS  mandatory
    DESCRIPTION
           "The way multicasts should  forwarded  on  this
           interface;  not  forwarded,  forwarded  as data
           link multicasts, or forwarded as data link uni-
           casts.   Data link multicasting is not meaning-
           ful on point to point and NBMA interfaces,  and
           setting ospfMulticastForwarding to 0 effective-
           ly disables all multicast forwarding."
    DEFVAL  { blocked }
    ::= { ospfIfEntry  18 }

ospfIfDemand OBJECT-TYPE
    SYNTAX  TruthValue
    ACCESS  read-write
    STATUS  mandatory
    DESCRIPTION
           "Indicates whether Demand OSPF procedures (hel-
           lo supression to FULL neighbors and setting the
           DoNotAge flag on proogated LSAs) should be per-
           formed on this interface."
    DEFVAL  { false }
    ::= { ospfIfEntry  19 }

ospfIfAuthType OBJECT-TYPE
    SYNTAX  INTEGER 
    ACCESS  read-write
    STATUS  mandatory
    DESCRIPTION
           "The authentication type specified for  an  in-
           terface.   Additional  authentication types may
           be assigned locally. No Authentication (0), 
           Simple password (1) and MD5 crypto checksum (2) 
           are currently the only valid values."
    REFERENCE
           "OSPF Version 2, Appendix E Authentication"
    DEFVAL  { 0 }
    ::= { ospfIfEntry  20 }

ospfIfMetricTable OBJECT-TYPE
    SYNTAX  SEQUENCE OF OspfIfMetricEntry
    ACCESS  not-accessible
    STATUS  mandatory
    DESCRIPTION
           "The TOS metrics for  a  non-virtual  interface
           identified by the interface index."
    REFERENCE
           "OSPF Version 2, Appendix C.3  Router  interface
          parameters"
    ::= { ospf  8 }

ospfIfMetricEntry OBJECT-TYPE
    SYNTAX  OspfIfMetricEntry
    ACCESS  not-accessible
    STATUS  mandatory
    DESCRIPTION
           "A particular TOS metric for a non-virtual  in-
           terface identified by the interface index."
    REFERENCE
           "OSPF Version 2, Appendix C.3  Router  interface
          parameters"
    INDEX   {
                 ospfIfMetricIpAddress,
                 ospfIfMetricAddressLessIf,
                 ospfIfMetricTOS
               }
    ::= { ospfIfMetricTable  1 }

OspfIfMetricEntry ::=
    SEQUENCE {
        ospfIfMetricIpAddress
            IpAddress,

        ospfIfMetricAddressLessIf
            INTEGER (-2147483648..2147483647),

        ospfIfMetricTOS
            TOSType,

        ospfIfMetricValue
            Metric,

        ospfIfMetricStatus
            RowStatus
    }

ospfIfMetricIpAddress OBJECT-TYPE
    SYNTAX  IpAddress
    ACCESS  read-only
    STATUS  mandatory
    DESCRIPTION
           "The IP address of this OSPF interface.  On row
           creation,  this  can  be  derived  from the in-
           stance."
    ::= { ospfIfMetricEntry  1 }

ospfIfMetricAddressLessIf OBJECT-TYPE
    SYNTAX  INTEGER (-2147483648..2147483647)
    ACCESS  read-only
    STATUS  mandatory
    DESCRIPTION
           "For the purpose of easing  the  instancing  of
           addressed   and  addressless  interfaces;  This
           variable takes the value 0 on  interfaces  with
           IP  Addresses, and the value of ifIndex for in-
           terfaces having no IP Address.   On  row  crea-
           tion, this can be derived from the instance."
    ::= { ospfIfMetricEntry  2 }

ospfIfMetricTOS OBJECT-TYPE
    SYNTAX  TOSType
    ACCESS  read-only
    STATUS  mandatory
    DESCRIPTION
           "The type of service metric  being  referenced.
           On  row  creation, this can be derived from the
           instance."
    ::= { ospfIfMetricEntry  3 }

ospfIfMetricValue OBJECT-TYPE
    SYNTAX  Metric
    ACCESS  read-write
    STATUS  mandatory
    DESCRIPTION
           "The metric of using this type  of  service  on
           this interface.  The default value of the TOS 0
           Metric is 10^8 / ifSpeed."
    ::= { ospfIfMetricEntry  4 }

ospfIfMetricStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfIfMetricEntry  5 }

ospfVirtIfTable OBJECT-TYPE
    SYNTAX  SEQUENCE OF OspfVirtIfEntry
    ACCESS  not-accessible
    STATUS  mandatory
    DESCRIPTION
           "Information about this router's virtual inter-
           faces."
    REFERENCE
           "OSPF Version  2,  Appendix  C.4   Virtual  link
          parameters"
    ::= { ospf  9 }

ospfVirtIfEntry OBJECT-TYPE
    SYNTAX  OspfVirtIfEntry
    ACCESS  not-accessible
    STATUS  mandatory
    DESCRIPTION
           "Information about a single Virtual Interface."
    INDEX   { ospfVirtIfAreaId,  ospfVirtIfNeighbor }
    ::= { ospfVirtIfTable  1 }

OspfVirtIfEntry ::=
    SEQUENCE {
        ospfVirtIfAreaId
            AreaID,

        ospfVirtIfNeighbor
            RouterID,

        ospfVirtIfTransitDelay
            UpToMaxAge,

        ospfVirtIfRetransInterval
            UpToMaxAge,

        ospfVirtIfHelloInterval
            HelloRange,

        ospfVirtIfRtrDeadInterval
            PositiveInteger,

        ospfVirtIfState
            INTEGER,

        ospfVirtIfEvents
            Counter,

        ospfVirtIfAuthType
            INTEGER,

        ospfVirtIfAuthKey
            OCTET STRING,

        ospfVirtIfStatus
            RowStatus
    }

ospfVirtIfAreaId OBJECT-TYPE
    SYNTAX  AreaID
    ACCESS  read-only
    STATUS  mandatory
    DESCRIPTION
           "The  Transit  Area  that  the   Virtual   Link
           traverses.  By definition, this is not 0.0.0.0"
    ::= { ospfVirtIfEntry  1 }

ospfVirtIfNeighbor OBJECT-TYPE
    SYNTAX  RouterID
    ACCESS  read-only
    STATUS  mandatory
    DESCRIPTION
           "The Router ID of the Virtual Neighbor."
    ::= { ospfVirtIfEntry  2 }

ospfVirtIfTransitDelay OBJECT-TYPE
    SYNTAX  UpToMaxAge
    ACCESS  read-write
    STATUS  mandatory
    DESCRIPTION
           "The estimated number of seconds  it  takes  to
           transmit  a link- state update packet over this
           interface."
    DEFVAL  { 1 }
    ::= { ospfVirtIfEntry  3 }

ospfVirtIfRetransInterval OBJECT-TYPE
    SYNTAX  UpToMaxAge
    ACCESS  read-write
    STATUS  mandatory
    DESCRIPTION
           "The number of seconds between  link-state  ad-
           vertisement  retransmissions,  for  adjacencies
           belonging to this  interface.   This  value  is
           also used when retransmitting database descrip-
           tion  and  link-state  request  packets.   This
           value  should  be well over the expected round-
           trip time."
    DEFVAL  { 5 }
    ::= { ospfVirtIfEntry  4 }

ospfVirtIfHelloInterval OBJECT-TYPE
    SYNTAX  HelloRange
    ACCESS  read-write
    STATUS  mandatory
    DESCRIPTION
           "The length of time, in  seconds,  between  the
           Hello  packets that the router sends on the in-
           terface.  This value must be the same  for  the
           virtual neighbor."
    DEFVAL  { 10 }
    ::= { ospfVirtIfEntry  5 }

ospfVirtIfRtrDeadInterval OBJECT-TYPE
    SYNTAX  PositiveInteger
    ACCESS  read-write
    STATUS  mandatory
    DESCRIPTION
           "The number of seconds that  a  router's  Hello
           packets  have  not been seen before it's neigh-
           bors declare the router down.  This  should  be
           some  multiple  of  the  Hello  interval.  This
           value must be the same for the  virtual  neigh-
           bor."
    DEFVAL  { 60 }
    ::= { ospfVirtIfEntry  6 }

ospfVirtIfState OBJECT-TYPE
    SYNTAX  INTEGER {
                 down(1),
                 pointToPoint(4)
               }
    ACCESS  read-only
    STATUS  mandatory
    DESCRIPTION
           "OSPF virtual interface states."
    DEFVAL  { down }
    ::= { ospfVirtIfEntry  7 }

ospfVirtIfEvents OBJECT-TYPE
    SYNTAX  Counter
    ACCESS  read-only
    STATUS  mandatory
    DESCRIPTION
           "The number of state changes or error events on
           this Virtual Link"
    ::= { ospfVirtIfEntry  8 }

ospfVirtIfAuthKey OBJECT-TYPE
    SYNTAX  OCTET STRING
    ACCESS  read-write
    STATUS  mandatory
    DESCRIPTION
           "If Authentication Type is simplePassword,  the
           device  will left adjust and zero fill to 8 oc-
           tets.


           Note that unauthenticated  interfaces  need  no
           authentication key, and simple password authen-
           tication cannot use a key of more  than  8  oc-
           tets.  Larger keys are useful only with authen-
           tication mechanisms not specified in this docu-
           ment.


           When  read,  ospfVifAuthKey  always  returns  a
           string of length zero."
    REFERENCE
           "OSPF Version 2, Section 9  The  Interface  Data
          Structure"
--    DEFVAL  { 0 }
    ::= { ospfVirtIfEntry  9 }

ospfVirtIfStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfVirtIfEntry  10 }

ospfVirtIfAuthType OBJECT-TYPE
    SYNTAX  INTEGER
    ACCESS  read-write
    STATUS  mandatory
    DESCRIPTION
           "The authentication type specified for a virtu-
           al  interface.  Additional authentication types
           may be assigned locally. No Authentication (0), 
           Simple password (1) and MD5 crypto checksum (2) 
           are currently the only valid values."
    REFERENCE
           "OSPF Version 2, Appendix E Authentication"
    DEFVAL  { 0 }
    ::= { ospfVirtIfEntry  11 }

ospfNbrTable OBJECT-TYPE
    SYNTAX  SEQUENCE OF OspfNbrEntry
    ACCESS  not-accessible
    STATUS  mandatory
    DESCRIPTION
           "A table of non-virtual neighbor information."
    REFERENCE
           "OSPF Version 2, Section 10  The  Neighbor  Data
          Structure"
    ::= { ospf  10 }

ospfNbrEntry OBJECT-TYPE
    SYNTAX  OspfNbrEntry
    ACCESS  not-accessible
    STATUS  mandatory
    DESCRIPTION
           "The information regarding a single neighbor."
    REFERENCE
           "OSPF Version 2, Section 10  The  Neighbor  Data
          Structure"
    INDEX   { ospfNbrIpAddr,  ospfNbrAddressLessIndex }
    ::= { ospfNbrTable  1 }

OspfNbrEntry ::=
    SEQUENCE {
        ospfNbrIpAddr
            IpAddress,

        ospfNbrAddressLessIndex
            InterfaceIndex,

        ospfNbrRtrId
            RouterID,

        ospfNbrOptions
            INTEGER (-2147483648..2147483647),

        ospfNbrPriority
            DesignatedRouterPriority,

        ospfNbrState
            INTEGER,

        ospfNbrEvents
            Counter,

        ospfNbrLsRetransQLen
            Gauge32,

        ospfNbmaNbrStatus
            RowStatus,

        ospfNbmaNbrPermanence
            INTEGER,

        ospfNbrHelloSuppressed
            TruthValue
    }

ospfNbrIpAddr OBJECT-TYPE
    SYNTAX  IpAddress
    ACCESS  read-only
    STATUS  mandatory
    DESCRIPTION
           "The IP address this neighbor is using  in  its
           IP  Source  Address.  Note that, on addressless
           links, this will not be 0.0.0.0,  but  the  ad-
           dress of another of the neighbor's interfaces."
    ::= { ospfNbrEntry  1 }

ospfNbrAddressLessIndex OBJECT-TYPE
    SYNTAX  InterfaceIndex
    ACCESS  read-only
    STATUS  mandatory
    DESCRIPTION
           "On an interface having an  IP  Address,  zero.
           On  addressless  interfaces,  the corresponding
           value of ifIndex in the Internet Standard  MIB.
           On  row  creation, this can be derived from the
           instance."
    ::= { ospfNbrEntry  2 }

ospfNbrRtrId OBJECT-TYPE
    SYNTAX  RouterID
    ACCESS  read-only
    STATUS  mandatory
    DESCRIPTION
           "A 32-bit integer (represented as a type  IpAd-
           dress)  uniquely  identifying  the  neighboring
           router in the Autonomous System."
    DEFVAL  { 0 }
    ::= { ospfNbrEntry  3 }

ospfNbrOptions OBJECT-TYPE
    SYNTAX  INTEGER (-2147483648..2147483647)
    ACCESS  read-only
    STATUS  mandatory
    DESCRIPTION
           "A Bit Mask corresponding to the neighbor's op-
           tions field.


           Bit 0, if set, indicates that the  system  will
           operate  on  Type of Service metrics other than
           TOS 0.  If zero, the neighbor will  ignore  all
           metrics except the TOS 0 metric.


           Bit 1, if set, indicates  that  the  associated
           area  accepts and operates on external informa-
           tion; if zero, it is a stub area.


           Bit 2, if set, indicates that the system is ca-
           pable  of routing IP Multicast datagrams; i.e.,
           that it implements the Multicast Extensions  to
           OSPF.


           Bit 3, if set, indicates  that  the  associated
           area  is  an  NSSA.  These areas are capable of
           carrying type 7 external advertisements,  which
           are  translated into type 5 external advertise-
           ments at NSSA borders."
    REFERENCE
           "OSPF Version 2, Section 12.1.2 Options"
    DEFVAL  { 0 }
    ::= { ospfNbrEntry  4 }

ospfNbrPriority OBJECT-TYPE
    SYNTAX  DesignatedRouterPriority
    ACCESS  read-write
    STATUS  mandatory
    DESCRIPTION
           "The priority of this neighbor in the designat-
           ed router election algorithm.  The value 0 sig-
           nifies that the neighbor is not eligible to be-
           come  the  designated router on this particular
           network."
    DEFVAL  { 1 }
    ::= { ospfNbrEntry  5 }

ospfNbrState OBJECT-TYPE
    SYNTAX  INTEGER {
                 down(1),
                 attempt(2),
                 init(3),
                 twoWay(4),
                 exchangeStart(5),
                 exchange(6),
                 loading(7),
                 full(8)
               }
    ACCESS  read-only
    STATUS  mandatory
    DESCRIPTION
           "The State of the relationship with this Neigh-
           bor."
    REFERENCE
           "OSPF Version 2, Section 10.1 Neighbor States"
    DEFVAL  { down }
    ::= { ospfNbrEntry  6 }

ospfNbrEvents OBJECT-TYPE
    SYNTAX  Counter
    ACCESS  read-only
    STATUS  mandatory
    DESCRIPTION
           "The number of times this neighbor relationship
           has changed state, or an error has occurred."
    ::= { ospfNbrEntry  7 }

ospfNbrLsRetransQLen OBJECT-TYPE
    SYNTAX  Gauge32
    ACCESS  read-only
    STATUS  mandatory
    DESCRIPTION
           "The  current  length  of  the   retransmission
           queue."
    ::= { ospfNbrEntry  8 }

ospfNbmaNbrStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfNbrEntry  9 }

ospfNbmaNbrPermanence OBJECT-TYPE
    SYNTAX  INTEGER {
                 dynamic(1),
                 permanent(2)
               }
    ACCESS  read-only
    STATUS  mandatory
    DESCRIPTION
           "This variable displays the status of  the  en-
           try.   'dynamic'  and  'permanent' refer to how
           the neighbor became known."
    DEFVAL  { permanent }
    ::= { ospfNbrEntry  10 }

ospfNbrHelloSuppressed OBJECT-TYPE
    SYNTAX  TruthValue
    ACCESS  read-only
    STATUS  mandatory
    DESCRIPTION
           "Indicates whether Hellos are being  suppressed
           to the neighbor"
    ::= { ospfNbrEntry  11 }

ospfVirtNbrTable OBJECT-TYPE
    SYNTAX  SEQUENCE OF OspfVirtNbrEntry
    ACCESS  not-accessible
    STATUS  mandatory
    DESCRIPTION
           "A table of virtual neighbor information."
    REFERENCE
           "OSPF Version 2, Section 15  Virtual Links"
    ::= { ospf  11 }

ospfVirtNbrEntry OBJECT-TYPE
    SYNTAX  OspfVirtNbrEntry
    ACCESS  not-accessible
    STATUS  mandatory
    DESCRIPTION
           "Virtual neighbor information."
    INDEX   { ospfVirtNbrArea,  ospfVirtNbrRtrId }
    ::= { ospfVirtNbrTable  1 }

OspfVirtNbrEntry ::=
    SEQUENCE {
        ospfVirtNbrArea
            AreaID,

        ospfVirtNbrRtrId
            RouterID,

        ospfVirtNbrIpAddr
            IpAddress,

        ospfVirtNbrOptions
            INTEGER (-2147483648..2147483647),

        ospfVirtNbrState
            INTEGER,

        ospfVirtNbrEvents
            Counter,

        ospfVirtNbrLsRetransQLen
            Gauge32,

        ospfVirtNbrHelloSuppressed
            TruthValue
    }

ospfVirtNbrArea OBJECT-TYPE
    SYNTAX  AreaID
    ACCESS  read-only
    STATUS  mandatory
    DESCRIPTION
           "The Transit Area Identifier."
    ::= { ospfVirtNbrEntry  1 }

ospfVirtNbrRtrId OBJECT-TYPE
    SYNTAX  RouterID
    ACCESS  read-only
    STATUS  mandatory
    DESCRIPTION
           "A  32-bit  integer  uniquely  identifying  the
           neighboring router in the Autonomous System."
    ::= { ospfVirtNbrEntry  2 }

ospfVirtNbrIpAddr OBJECT-TYPE
    SYNTAX  IpAddress
    ACCESS  read-only
    STATUS  mandatory
    DESCRIPTION
           "The IP address this Virtual  Neighbor  is  us-
           ing."
    ::= { ospfVirtNbrEntry  3 }

ospfVirtNbrOptions OBJECT-TYPE
    SYNTAX  INTEGER (-2147483648..2147483647)
    ACCESS  read-only
    STATUS  mandatory
    DESCRIPTION
           "A Bit Mask corresponding to the neighbor's op-
           tions field.


           Bit 1, if set, indicates that the  system  will
           operate  on  Type of Service metrics other than
           TOS 0.  If zero, the neighbor will  ignore  all
           metrics except the TOS 0 metric.


           Bit 2, if set, indicates  that  the  system  is
           Network  Multicast  capable; ie, that it imple-
           ments OSPF Multicast Routing."
    ::= { ospfVirtNbrEntry  4 }

ospfVirtNbrState OBJECT-TYPE
    SYNTAX  INTEGER {
                 down(1),
                 attempt(2),
                 init(3),
                 twoWay(4),
                 exchangeStart(5),
                 exchange(6),
                 loading(7),
                 full(8)
               }
    ACCESS  read-only
    STATUS  mandatory
    DESCRIPTION
           "The state of the  Virtual  Neighbor  Relation-
           ship."
    ::= { ospfVirtNbrEntry  5 }

ospfVirtNbrEvents OBJECT-TYPE
    SYNTAX  Counter
    ACCESS  read-only
    STATUS  mandatory
    DESCRIPTION
           "The number of  times  this  virtual  link  has
           changed its state, or an error has occurred."
    ::= { ospfVirtNbrEntry  6 }

ospfVirtNbrLsRetransQLen OBJECT-TYPE
    SYNTAX  Gauge32
    ACCESS  read-only
    STATUS  mandatory
    DESCRIPTION
           "The  current  length  of  the   retransmission
           queue."
    ::= { ospfVirtNbrEntry  7 }

ospfVirtNbrHelloSuppressed OBJECT-TYPE
    SYNTAX  TruthValue
    ACCESS  read-only
    STATUS  mandatory
    DESCRIPTION
           "Indicates whether Hellos are being  suppressed
           to the neighbor"
    ::= { ospfVirtNbrEntry  8 }

ospfExtLsdbTable OBJECT-TYPE
    SYNTAX  SEQUENCE OF OspfExtLsdbEntry
    ACCESS  not-accessible
    STATUS  mandatory
    DESCRIPTION
           "The OSPF Process's Links State Database."
    REFERENCE
           "OSPF Version 2, Section 12  Link  State  Adver-
          tisements"
    ::= { ospf  12 }

ospfExtLsdbEntry OBJECT-TYPE
    SYNTAX  OspfExtLsdbEntry
    ACCESS  not-accessible
    STATUS  mandatory
    DESCRIPTION
           "A single Link State Advertisement."
    INDEX   {
                 ospfExtLsdbType,
                 ospfExtLsdbLsid,
                 ospfExtLsdbRouterId
               }
    ::= { ospfExtLsdbTable  1 }

OspfExtLsdbEntry ::=
    SEQUENCE {
        ospfExtLsdbType
            INTEGER,

        ospfExtLsdbLsid
            IpAddress,

        ospfExtLsdbRouterId
            RouterID,

        ospfExtLsdbSequence
            INTEGER (-2147483648..2147483647),

        ospfExtLsdbAge
            INTEGER (-2147483648..2147483647),

        ospfExtLsdbChecksum
            INTEGER (-2147483648..2147483647),

        ospfExtLsdbAdvertisement
            OCTET STRING
    }

ospfExtLsdbType OBJECT-TYPE
    SYNTAX  INTEGER {
                 asExternalLink(5)
               }
    ACCESS  read-only
    STATUS  mandatory
    DESCRIPTION
           "The type  of  the  link  state  advertisement.
           Each  link state type has a separate advertise-
           ment format."
    REFERENCE
           "OSPF Version 2, Appendix A.4.1 The  Link  State
          Advertisement header"
    ::= { ospfExtLsdbEntry  1 }

ospfExtLsdbLsid OBJECT-TYPE
    SYNTAX  IpAddress
    ACCESS  read-only
    STATUS  mandatory
    DESCRIPTION
           "The Link State ID is an LS Type Specific field
           containing either a Router ID or an IP Address;
           it identifies the piece of the  routing  domain
           that is being described by the advertisement."
    REFERENCE
           "OSPF Version 2, Section 12.1.4 Link State ID"
    ::= { ospfExtLsdbEntry  2 }

ospfExtLsdbRouterId OBJECT-TYPE
    SYNTAX  RouterID
    ACCESS  read-only
    STATUS  mandatory
    DESCRIPTION
           "The 32 bit number that uniquely identifies the
           originating router in the Autonomous System."
    REFERENCE
           "OSPF Version 2, Appendix C.1 Global parameters"
    ::= { ospfExtLsdbEntry  3 }

ospfExtLsdbSequence OBJECT-TYPE
    SYNTAX  INTEGER (-2147483648..2147483647)
    ACCESS  read-only
    STATUS  mandatory
    DESCRIPTION
           "The sequence number field is a  signed  32-bit
           integer.   It  is used to detect old and dupli-
           cate link state advertisements.  The  space  of
           sequence  numbers  is  linearly  ordered.   The
           larger the sequence number the more recent  the
           advertisement."
    REFERENCE
           "OSPF Version  2,  Section  12.1.6  LS  sequence
          number"
    ::= { ospfExtLsdbEntry  4 }

ospfExtLsdbAge OBJECT-TYPE
    SYNTAX  INTEGER (-2147483648..2147483647)
    ACCESS  read-only
    STATUS  mandatory
    DESCRIPTION
           "This field is the age of the link state adver-
           tisement in seconds."
    REFERENCE
           "OSPF Version 2, Section 12.1.1 LS age"
    ::= { ospfExtLsdbEntry  5 }

ospfExtLsdbChecksum OBJECT-TYPE
    SYNTAX  INTEGER (-2147483648..2147483647)
    ACCESS  read-only
    STATUS  mandatory
    DESCRIPTION
           "This field is the  checksum  of  the  complete
           contents  of  the  advertisement, excepting the
           age field.  The age field is excepted  so  that
           an   advertisement's  age  can  be  incremented
           without updating the  checksum.   The  checksum
           used  is  the same that is used for ISO connec-
           tionless datagrams; it is commonly referred  to
           as the Fletcher checksum."
    REFERENCE
           "OSPF Version 2, Section 12.1.7 LS checksum"
    ::= { ospfExtLsdbEntry  6 }

ospfExtLsdbAdvertisement OBJECT-TYPE
    SYNTAX  OCTET STRING
    ACCESS  read-only
    STATUS  mandatory
    DESCRIPTION
           "The entire Link State Advertisement, including
           its header."
    REFERENCE
           "OSPF Version 2, Section 12  Link  State  Adver-
          tisements"
    ::= { ospfExtLsdbEntry  7 }

ospfRouteGroup OBJECT IDENTIFIER ::= { ospf  13 }

ospfIntraArea OBJECT IDENTIFIER ::= { ospfRouteGroup  1 }

ospfInterArea OBJECT IDENTIFIER ::= { ospfRouteGroup  2 }

ospfExternalType1 OBJECT IDENTIFIER ::= { ospfRouteGroup  3 }

ospfExternalType2 OBJECT IDENTIFIER ::= { ospfRouteGroup  4 }

ospfAreaAggregateTable OBJECT-TYPE
    SYNTAX  SEQUENCE OF OspfAreaAggregateEntry
    ACCESS  not-accessible
    STATUS  mandatory
    DESCRIPTION
           "A range of IP addresses  specified  by  an  IP
           address/IP  network  mask  pair.   For example,
           class B address range of X.X.X.X with a network
           mask  of  255.255.0.0 includes all IP addresses
           from X.X.0.0  to  X.X.255.255.   Note  that  if
           ranges  are configured such that one range sub-
           sumes  another  range  (e.g.,   10.0.0.0   mask
           255.0.0.0  and  10.1.0.0 mask 255.255.0.0), the
           most specific match is the preferred one."
    REFERENCE
           "OSPF Version 2, Appendix C.2  Area parameters"
    ::= { ospf  14 }

ospfAreaAggregateEntry OBJECT-TYPE
    SYNTAX  OspfAreaAggregateEntry
    ACCESS  not-accessible
    STATUS  mandatory
    DESCRIPTION
           "A range of IP addresses  specified  by  an  IP
           address/IP  network  mask  pair.   For example,
           class B address range of X.X.X.X with a network
           mask  of  255.255.0.0 includes all IP addresses
           from X.X.0.0  to  X.X.255.255.   Note  that  if
           ranges are range configured such that one range
           subsumes another  range  (e.g.,  10.0.0.0  mask
           255.0.0.0  and  10.1.0.0 mask 255.255.0.0), the
           most specific match is the preferred one."
    REFERENCE
           "OSPF Version 2, Appendix C.2  Area parameters"
    INDEX   {
                 ospfAreaAggregateAreaID,
                 ospfAreaAggregateLsdbType,
                 ospfAreaAggregateNet,
                 ospfAreaAggregateMask
               }
    ::= { ospfAreaAggregateTable  1 }

OspfAreaAggregateEntry ::=
    SEQUENCE {
        ospfAreaAggregateAreaID
            AreaID,

        ospfAreaAggregateLsdbType
            INTEGER,

        ospfAreaAggregateNet
            IpAddress,

        ospfAreaAggregateMask
            IpAddress,

        ospfAreaAggregateStatus
            RowStatus,

        ospfAreaAggregateEffect
            INTEGER
    }

ospfAreaAggregateAreaID OBJECT-TYPE
    SYNTAX  AreaID
    ACCESS  read-only
    STATUS  mandatory
    DESCRIPTION
           "The Area the Address Aggregate is to be  found
           within."
    REFERENCE
           "OSPF Version 2, Appendix C.2 Area parameters"
    ::= { ospfAreaAggregateEntry  1 }

ospfAreaAggregateLsdbType OBJECT-TYPE
    SYNTAX  INTEGER {
                 summaryLink(3),
                 nssaExternalLink(7)
               }
    ACCESS  read-only
    STATUS  mandatory
    DESCRIPTION
           "The type of the Address Aggregate.  This field
           specifies  the  Lsdb type that this Address Ag-
           gregate applies to."
    REFERENCE
           "OSPF Version 2, Appendix A.4.1 The  Link  State
          Advertisement header"
    ::= { ospfAreaAggregateEntry  2 }

ospfAreaAggregateNet OBJECT-TYPE
    SYNTAX  IpAddress
    ACCESS  read-only
    STATUS  mandatory
    DESCRIPTION
           "The IP Address of the Net or Subnet  indicated
           by the range."
    REFERENCE
           "OSPF Version 2, Appendix C.2 Area parameters"
    ::= { ospfAreaAggregateEntry  3 }

ospfAreaAggregateMask OBJECT-TYPE
    SYNTAX  IpAddress
    ACCESS  read-only
    STATUS  mandatory
    DESCRIPTION
           "The Subnet Mask that pertains to  the  Net  or
           Subnet."
    REFERENCE
           "OSPF Version 2, Appendix C.2 Area parameters"
    ::= { ospfAreaAggregateEntry  4 }

ospfAreaAggregateStatus OBJECT-TYPE
    SYNTAX  RowStatus
    ACCESS  read-write
    STATUS  mandatory
    DESCRIPTION
           "This variable displays the status of  the  en-
           try.  Setting it to 'invalid' has the effect of
           rendering it inoperative.  The internal  effect
           (row removal) is implementation dependent."
    ::= { ospfAreaAggregateEntry  5 }

ospfAreaAggregateEffect OBJECT-TYPE
    SYNTAX  INTEGER {
                 advertiseMatching(1),
                 doNotAdvertiseMatching(2)
               }
    ACCESS  read-write
    STATUS  mandatory
    DESCRIPTION
           "Subnets subsumed by ranges either trigger  the
           advertisement  of  the indicated aggregate (ad-
           vertiseMatching), or result in the subnet's not
           being advertised at all outside the area."
    DEFVAL  { advertiseMatching }
    ::= { ospfAreaAggregateEntry  6 }

ospfConformance OBJECT IDENTIFIER ::= { ospf  15 }

ospfGroups OBJECT IDENTIFIER ::= { ospfConformance  1 }

ospfCompliances OBJECT IDENTIFIER ::= { ospfConformance  2 }

ospfCompliance OBJECT IDENTIFIER ::= { ospfCompliances  1 }

ospfBasicGroup OBJECT IDENTIFIER ::= { ospfGroups  1 }

ospfAreaGroup OBJECT IDENTIFIER ::= { ospfGroups  2 }

ospfStubAreaGroup OBJECT IDENTIFIER ::= { ospfGroups  3 }

ospfLsdbGroup OBJECT IDENTIFIER ::= { ospfGroups  4 }

ospfAreaRangeGroup OBJECT IDENTIFIER ::= { ospfGroups  5 }

ospfHostGroup OBJECT IDENTIFIER ::= { ospfGroups  6 }

ospfIfGroup OBJECT IDENTIFIER ::= { ospfGroups  7 }

ospfIfMetricGroup OBJECT IDENTIFIER ::= { ospfGroups  8 }

ospfVirtIfGroup OBJECT IDENTIFIER ::= { ospfGroups  9 }

ospfNbrGroup OBJECT IDENTIFIER ::= { ospfGroups  10 }

ospfVirtNbrGroup OBJECT IDENTIFIER ::= { ospfGroups  11 }

ospfExtLsdbGroup OBJECT IDENTIFIER ::= { ospfGroups  12 }

ospfAreaAggregateGroup OBJECT IDENTIFIER ::= { ospfGroups  13 }

END
