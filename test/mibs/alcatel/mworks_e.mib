MWORKS-E-MIB

        DEFINITIONS ::= BEGIN

        IMPORTS
                enterprises     FROM    RFC1155-SMI
                Counter         FROM    RFC1155-SMI
                OBJECT-TYPE     FROM    RFC-1212;


                tecElite                OBJECT IDENTIFIER ::= { enterprises 217 }
                mworkse                  OBJECT IDENTIFIER ::= { tecElite 17 }
                am501                   OBJECT IDENTIFIER ::= { mworkse 1 }
                amMem                   OBJECT IDENTIFIER ::= { am501 1 }
                amHeap                  OBJECT IDENTIFIER ::= { am501 2 }

        amMemCeiling OBJECT-TYPE
                SYNTAX  Counter
                ACCESS  read-only
                STATUS  mandatory
                DESCRIPTION
                        "bytes of memory the agent memory manager
                        will allow the agent to use."
                ::= { amMem 1 }

        amMemUsed OBJECT-TYPE
                SYNTAX  Counter
                ACCESS  read-only
                STATUS  mandatory
                DESCRIPTION
                        "bytes of memory that meterworks has malloc'ed.
                        some of this may be in free pools."
                ::= { amMem 2 }

        amHeapTotal OBJECT-TYPE
                SYNTAX  Counter
                ACCESS  read-only
                STATUS  mandatory
                DESCRIPTION
                        "bytes of memory given to the heap manager."
                ::= { amHeap 1 }

        amHeapUsed OBJECT-TYPE
                SYNTAX  Counter
                ACCESS  read-only
                STATUS  mandatory
                DESCRIPTION
                        "bytes of available memory in the heap."
                ::= { amHeap 2 }

END
