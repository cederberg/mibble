XYLAN-IWF-MIB DEFINITIONS ::= BEGIN

          IMPORTS
              OBJECT-TYPE
                    FROM RFC-1212
              DisplayString
                    FROM RFC1213-MIB
              xylanFrAtmArch
                    FROM XYLAN-BASE-MIB;


     
     frxSwitchGroup  OBJECT IDENTIFIER  ::=  { xylanFrAtmArch 1 }

     frxInterworking  OBJECT IDENTIFIER  ::=  { frxSwitchGroup 1 }



          -- This is the Xylan Corporation proprietary MIB module for 
          -- configuring FR/ATM InterWorking Functions.
          --                                                   - VK

          -- FR switching/interworking Config Tables

          frxIwfConfigTable OBJECT-TYPE
              SYNTAX  SEQUENCE OF FrxIwfConfigEntry
              ACCESS  not-accessible
              STATUS  mandatory
              DESCRIPTION
                 "The FR switching and FR/ATM InterWorking 
                  (FRF.5/FRF.8) configuration table."
               ::= { frxInterworking 1 }
 
 
          frxIwfConfigEntry OBJECT-TYPE
              SYNTAX  FrxIwfConfigEntry
              ACCESS  not-accessible
              STATUS  mandatory
              DESCRIPTION
                 "An entry in the FR/ATM IWF configuration table."
              INDEX   { frxIwfConfigAtmSlot,
                        frxIwfConfigAtmPort,
                        frxIwfConfigAtmVpi, 
                        frxIwfConfigAtmVci, 
                        frxIwfConfigFrSlot,
                        frxIwfConfigFrPort,
                        frxIwfConfigFrDlci }
               ::= { frxIwfConfigTable 1 }


          FrxIwfConfigEntry ::=
              SEQUENCE {
                   frxIwfConfigAtmSlot
                       INTEGER,

                   frxIwfConfigAtmPort
                       INTEGER,

                   frxIwfConfigAtmVpi
                       INTEGER,

                   frxIwfConfigAtmVci
                       INTEGER,

                   frxIwfConfigFrSlot
                       INTEGER,

                   frxIwfConfigFrPort
                       INTEGER,

                   frxIwfConfigFrDlci
                       INTEGER,

                   frxIwfConfigServiceType
                       INTEGER,

                   frxIwfConfigSscsDlci
                       INTEGER,

                   frxIwfConfigCIR
                       INTEGER,

                   frxIwfConfigBc
                       INTEGER,

                   frxIwfConfigBe
                       INTEGER,

                   frxIwfConfigComprAdminStatus
                       INTEGER,

                   frxIwfConfigComprPRetryTime
                       INTEGER,

                   frxIwfConfigComprPRetryCount
                       INTEGER,

                   frxIwfConfigRowStatus
                       INTEGER 
               }


          frxIwfConfigAtmSlot OBJECT-TYPE
              SYNTAX   INTEGER (1..9)
              ACCESS   read-only
              STATUS   mandatory
              DESCRIPTION
                 "A unique value which identifies the slot which has an ASM."
              ::= { frxIwfConfigEntry 1 }


          frxIwfConfigAtmPort OBJECT-TYPE
              SYNTAX   INTEGER 
              ACCESS   read-only
              STATUS   mandatory
              DESCRIPTION
                 "A unique value which identifies the ATM port in ASM."
              ::= { frxIwfConfigEntry 2 }


          frxIwfConfigAtmVpi OBJECT-TYPE
              SYNTAX   INTEGER 
              ACCESS   read-only
              STATUS   mandatory
              DESCRIPTION
                 "A unique value which identifies this ATM virtual path.
                 Several FR PVCs can be multiplexed to a single ATM vpi/vci
                 for FRF.5 service only."
              ::= { frxIwfConfigEntry 3 }


          frxIwfConfigAtmVci OBJECT-TYPE
              SYNTAX   INTEGER 
              ACCESS   read-only
              STATUS   mandatory
              DESCRIPTION
                 "A unique value which identifies this ATM virtual channel.
                 Several FR PVCs can be multiplexed to a single ATM vpi/vci
                 for FRF.5 service only."
              ::= { frxIwfConfigEntry 4 }


          frxIwfConfigFrSlot OBJECT-TYPE
              SYNTAX   INTEGER (1..9) 
              ACCESS   read-only
              STATUS   mandatory
              DESCRIPTION
                 "A unique value which identifies a WSM slot with FR port."
              ::= { frxIwfConfigEntry 5 }


          frxIwfConfigFrPort OBJECT-TYPE
              SYNTAX   INTEGER 
              ACCESS   read-only
              STATUS   mandatory
              DESCRIPTION
                 "A unique value which identifies an FR port in a WSM."
              ::= { frxIwfConfigEntry 6 }


          frxIwfConfigFrDlci OBJECT-TYPE
              SYNTAX   INTEGER 
              ACCESS   read-only
              STATUS   mandatory
              DESCRIPTION
                 "Destination DLCI onto which the FR frame is switched.
                  For FRF.5 interworking this variable will indicate the 
                  FR-SSCS DLCI. For FRF.8 interworking this will have the 
                  same value as frxIwfConfigFrDlci."
              ::= { frxIwfConfigEntry 7 }


          frxIwfConfigServiceType OBJECT-TYPE
              SYNTAX   INTEGER {
                          frf5(1),
                          frf8(2)
                       }
              ACCESS   read-write
              STATUS   mandatory
              DESCRIPTION
                 "This value indicates the type of FR/ATM 
                  interworking (FRF.5/FRF.8)."
              ::= { frxIwfConfigEntry 8 }


          frxIwfConfigSscsDlci OBJECT-TYPE
              SYNTAX   INTEGER 
              ACCESS   read-write
              STATUS   mandatory
              DESCRIPTION
                 "For FRF.5 interworking this variable will indicate the 
                  FR-SSCS DLCI. For FRF.8 interworking this will have the 
                  same value as frxIwfConfigFrDlci."
              ::= { frxIwfConfigEntry 9 }


          frxIwfConfigCIR OBJECT-TYPE
              SYNTAX   INTEGER 
              ACCESS   read-write
              STATUS   mandatory
              DESCRIPTION
                 "Committed Information Rate for the Frame Relay PVC."
              ::= { frxIwfConfigEntry 10 }


          frxIwfConfigBc OBJECT-TYPE
              SYNTAX   INTEGER 
              ACCESS   read-write
              STATUS   mandatory
              DESCRIPTION
                 "Committed Burst Size for the Frame Relay PVC."
              ::= { frxIwfConfigEntry 11 }


          frxIwfConfigBe OBJECT-TYPE
              SYNTAX   INTEGER 
              ACCESS   read-write
              STATUS   mandatory
              DESCRIPTION
                 "Excess Burst Size for the Frame Relay PVC."
              ::= { frxIwfConfigEntry 12 }


          frxIwfConfigComprAdminStatus OBJECT-TYPE
              SYNTAX   INTEGER {
                         enable(1),
                         disable(2)
                         }
              ACCESS   read-write
              STATUS   mandatory
              DESCRIPTION
                 "Compression Administrative State. Virtual Circuit will
                  attempt to negotiate for compression if this variable is
                  enabled."
              ::= { frxIwfConfigEntry 13 }


          frxIwfConfigComprPRetryTime OBJECT-TYPE
              SYNTAX   INTEGER (1..10)
              ACCESS   read-write
              STATUS   mandatory
              DESCRIPTION
                 "The default P-Retry-Time for negotiating
                  mode 1 compression as described in Frame
                  Relay Forum Data Compression Implementation Agreement
                  FRF.9.
                 
                  This object represents the time in seconds
                  between retransmission of Data Compression
                  Negotiation Control messages."
              ::= { frxIwfConfigEntry 14 }


          frxIwfConfigComprPRetryCount OBJECT-TYPE
              SYNTAX   INTEGER (3..255)
              ACCESS   read-write
              STATUS   mandatory
              DESCRIPTION
                 "The default P-Retry-Count for negotiating
                  mode 1 compression as described in Frame
                  Relay Forum Data Compression Implementation Agreement
                  FRF.9
                 
                  This object represents the number of retries
                  before giving up on the negotiation phase
                  and not running compression on the virtual circuit."
              ::= { frxIwfConfigEntry 15 }


          frxIwfConfigRowStatus OBJECT-TYPE
              SYNTAX  INTEGER  {
                         create(1),
                         inactive(2),
                         active(3),
                         delete(4)
                      }
              ACCESS  read-write
              STATUS  mandatory
              DESCRIPTION
                 "This variable indicates the status of an entry in the table.
                  
                  When this variable is set to create(1), an entry in the table 
                  is created with default values. These values can be changed
                  and/or the entry can be set to active(3).

                  The entry is deleted by setting the RowStatus to delete(4).
                  
                  The entry is made active only if the RowStatus is set to
                  active(3)."
              ::= { frxIwfConfigEntry 16 }


          --  FR/ATM InterWorking Functions (FRF.5/FRF.8) Tables.

          
          frxIwfMappingTable OBJECT-TYPE
              SYNTAX  SEQUENCE OF FrxIwfMapEntry
              ACCESS  not-accessible
              STATUS  mandatory
              DESCRIPTION
                 "The FR/ATM InterWorking (FRF.5/FRF.8) mapping table.
                  When an entry is created in frxIwfConfigTable, a
                  corresponding entry in this table is created."
               ::= { frxInterworking 2 }


          frxIwfMapEntry OBJECT-TYPE
              SYNTAX  FrxIwfMapEntry
              ACCESS  not-accessible
              STATUS  mandatory
              DESCRIPTION
                 "An entry in the FR/ATM IWF mapping table."
              INDEX   { frxIwfMapAtmSlot, 
                        frxIwfMapAtmPort,
                        frxIwfMapAtmVpi,
                        frxIwfMapAtmVci
                       }
               ::= { frxIwfMappingTable 1 }


          FrxIwfMapEntry ::=
              SEQUENCE {
                   frxIwfMapAtmSlot
                       INTEGER,

                   frxIwfMapAtmPort
                       INTEGER,

                   frxIwfMapAtmVpi
                       INTEGER,

                   frxIwfMapAtmVci
                       INTEGER,

                   frxIwfMapDescription
                       DisplayString,

                   frxIwfMapType
                       INTEGER,

                   frxIwfMapDeClpMapping
                       INTEGER,

                   frxIwfMapDefaultClpValue
                       INTEGER,

                   frxIwfMapCongestionMapping
                       INTEGER,

                   frxIwfMapUlpEncapMapping
                       INTEGER,

                   frxIwfMapUlpEncapMode
                       INTEGER,

                   frxIwfMapLmiUserN391
                       INTEGER,

                   frxIwfMapLmiUserN392
                       INTEGER,

                   frxIwfMapLmiUserN393
                       INTEGER,

                   frxIwfMapLmiUserT391
                       INTEGER,

                   frxIwfMapLmiNetN392
                       INTEGER,

                   frxIwfMapLmiNetN393
                       INTEGER,

                   frxIwfMapLmiNetT392
                       INTEGER,

                   frxIwfMapOperStatus
                       INTEGER,

                   frxIwfMapAdminStatus
                       INTEGER,

                   frxIwfMapFrPvcStatus
		       INTEGER
               }


          frxIwfMapAtmSlot OBJECT-TYPE
              SYNTAX   INTEGER (1..9)
              ACCESS   read-only
              STATUS   mandatory
              DESCRIPTION
                 "A unique value which identifies this HSM board slot."
              ::= { frxIwfMapEntry 1 }


          frxIwfMapAtmPort OBJECT-TYPE
              SYNTAX   INTEGER (1..2)
              ACCESS   read-only
              STATUS   mandatory
              DESCRIPTION
                 "A unique value which identifies this ATM submodule port."
              ::= { frxIwfMapEntry 2 }


          frxIwfMapAtmVpi OBJECT-TYPE
              SYNTAX   INTEGER 
              ACCESS   read-only
              STATUS   mandatory
              DESCRIPTION
                 "A unique value which identifies this ATM virtual path.
                 Several FR PVCs can be multiplexed to a single ATM vpi/vci
                 for FRF.5 service only."
              ::= { frxIwfMapEntry 3 }


          frxIwfMapAtmVci OBJECT-TYPE
              SYNTAX   INTEGER (1..1023)
              ACCESS   read-only
              STATUS   mandatory
              DESCRIPTION
                 "A unique value which identifies this ATM virtual channel.
                 Several FR PVCs can be multiplexed to a single ATM vpi/vci
                 for FRF.5 service only."
              ::= { frxIwfMapEntry 4 }


          frxIwfMapDescription OBJECT-TYPE
              SYNTAX  DisplayString
              ACCESS  read-write
              STATUS  mandatory
              DESCRIPTION
                 "The name in ascii characters describing the interface" 
              ::= { frxIwfMapEntry 5 }


          frxIwfMapType OBJECT-TYPE
              SYNTAX   INTEGER {
                          frf5(1),
                          frf8(2)
                       }
              ACCESS   read-only
              STATUS   mandatory
              DESCRIPTION
                 "A value that indicates the type of Interworking Function,
                 whether FRF.5/FRF.8."
              ::= { frxIwfMapEntry 6 }


          frxIwfMapDeClpMapping OBJECT-TYPE
              SYNTAX  INTEGER  {
                         enable(1),
                         disable(2)
                      }
              ACCESS  read-write
              STATUS  mandatory
              DESCRIPTION
                 "A value that indicates whether the mapping
                 between FR Discard Eligibility (DE) and the
                 ATM Cell Loss Priority (CLP) is enabled or not."
              ::= { frxIwfMapEntry 7 }


          frxIwfMapDefaultClpValue OBJECT-TYPE
              SYNTAX   INTEGER (0..1)
              ACCESS   read-write
              STATUS   mandatory
              DESCRIPTION
                 "The value to be set in the Cell Loss Priority (CLP)
                 bit of the ATM cells. This is valid only in the 
                 Frame Relay to ATM direction."
              ::= { frxIwfMapEntry 8 }


          frxIwfMapCongestionMapping OBJECT-TYPE
              SYNTAX  INTEGER  {
                         enable(1),
                         disable(2)
                      }
              ACCESS  read-write
              STATUS  mandatory
              DESCRIPTION
                 "A value that indicates whether the mapping
                 between FR FECN and the ATM EFCI is enabled or not."
              ::= { frxIwfMapEntry 9 }


          frxIwfMapUlpEncapMapping OBJECT-TYPE
              SYNTAX  INTEGER  {
                         enable(1),
                         disable(2)
                      }
              ACCESS  read-write
              STATUS  mandatory
              DESCRIPTION
                 "A value that indicates whether the mapping
                 of the Upper Layer Protocol (ULP) encapsulation
                 should be enabled or not."
              ::= { frxIwfMapEntry 10 }


          frxIwfMapUlpEncapMode OBJECT-TYPE
              SYNTAX  INTEGER  {
                         transparent (1),
                         translation (2)
                      }
              ACCESS  read-write
              STATUS  mandatory
              DESCRIPTION
                 "A value that indicates the mode of encapsulation."
              ::= { frxIwfMapEntry 11 }


          frxIwfMapLmiUserN391 OBJECT-TYPE
              SYNTAX   INTEGER 
              ACCESS  read-write
              STATUS  mandatory
              DESCRIPTION
                 "The value of this object identifies the User-side
                 N391 full status polling cycle value for this
                 UNI/NNI logical port.  If the logical port is not
                 performing user-side procedures, then this value
                 is equal to noSuchName. "
              DEFVAL  { 6 }
              ::= { frxIwfMapEntry 12 }

          frxIwfMapLmiUserN392 OBJECT-TYPE
              SYNTAX   INTEGER 
              ACCESS  read-write
              STATUS  mandatory
              DESCRIPTION
                 "The value of this object identifies the User-side
                 N392 error threshold value for this UNI/NNI
                 logical port.  If the logical port is not
                 performing user-side procedures, then this value
                 is equal to noSuchName. "
              DEFVAL  { 3 }
              ::= { frxIwfMapEntry 13 }

          frxIwfMapLmiUserN393 OBJECT-TYPE
              SYNTAX   INTEGER 
              ACCESS  read-write
              STATUS  mandatory
              DESCRIPTION
                 "The value of this object identifies the User-side
                 N393 monitored events count value for this UNI/NNI
                 logical port.  If the logical port is not
                 performing user-side procedures, then this value
                 is equal to noSuchName. "
              DEFVAL  { 4 }
              ::= { frxIwfMapEntry 14 }

          frxIwfMapLmiUserT391 OBJECT-TYPE
              SYNTAX   INTEGER 
              ACCESS  read-write
              STATUS  mandatory
              DESCRIPTION
                 "The value of this object identifies the User-side
                 T391 link integrity verification polling timer
                 value for this UNI/NNI logical port.  If the
                 logical port is not performing user-side
                 procedures, then this value is equal to
                 noSuchName. "
              DEFVAL  { 10 }
              ::= { frxIwfMapEntry 15 }

          frxIwfMapLmiNetN392 OBJECT-TYPE
              SYNTAX   INTEGER 
              ACCESS  read-write
              STATUS  mandatory
              DESCRIPTION
                 "The value of this object identifies the Network-
                 side N392 error threshold value for this UNI/NNI 
                 logical port.  If the logical port is not
                 performing network-side procedures, then this
                 value is equal to noSuchName. "
              DEFVAL  { 3 }
              ::= { frxIwfMapEntry 16 }

          frxIwfMapLmiNetN393 OBJECT-TYPE
              SYNTAX   INTEGER 
              ACCESS  read-write
              STATUS  mandatory
              DESCRIPTION
                 "The value of this object identifies the Network-
                 side N393 monitored events count value 
                 for this UNI/NNI logical port.  If the
                 logical port is not performing network-side
                 procedures, then this value is equal to
                 noSuchName. "
              DEFVAL  { 4 }
              ::= { frxIwfMapEntry 17 }

          frxIwfMapLmiNetT392 OBJECT-TYPE
              SYNTAX   INTEGER 
              ACCESS  read-write
              STATUS  mandatory
              DESCRIPTION
                 "The value of this object identifies the Network-
                 side T392 polling verification timer value 
                 for this UNI/NNI logical port.  If the
                 logical port is not performing network-side
                 procedures, then this value is equal to
                 noSuchName. "
              DEFVAL  { 15 }
              ::= { frxIwfMapEntry 18 }

          frxIwfMapOperStatus OBJECT-TYPE
              SYNTAX  INTEGER  {
                         active(1),
                         inactive(2)
                      }
              ACCESS  read-only
              STATUS  mandatory
              DESCRIPTION
                 "A value that indicates the operation status of the
                 IWF connection."
              ::= { frxIwfMapEntry 19 }


          frxIwfMapAdminStatus OBJECT-TYPE
              SYNTAX  INTEGER  {
                         underCreation(1),
                         inactive(2),
                         active(3),
                         delete(4)
                      }
              ACCESS  read-write
              STATUS  mandatory
              DESCRIPTION
                 "This variable indicates the administrative status of 
                  an IWF connection.
                  
                  The status will be underCreation(1) when the 
                  frxIwfConfigRowStatus is set to create. None of the 
                  variables can be set in this state.
                  
                  This variable, frxIwfMapAdminStatus should be changed to 
                  inactive(2) from active state in order to change the values 
                  of other fields in this table.
                  
                  An entry in this table is created with default values and
                  made active(3) when frxSwitchRowStatus is set to active.
                  When the IWF is in active(3) state, only the 
                  frxIwfMapAdminStatus can be set.
                  
                  The entry or the iwf connection is deleted by setting 
                  this variable to delete(4)."
              ::= { frxIwfMapEntry 20 }


        frxIwfMapFrPvcStatus OBJECT-TYPE
            SYNTAX  INTEGER  {
                        inactive(0),
                        active(2),
                        deleted(4),
                        new(8)
                    }
              ACCESS  read-only
              STATUS  mandatory
              DESCRIPTION
                 "This variable indicates the status of FR-SSCS PVC."
             ::= { frxIwfMapEntry 21 }


          --  FR/ATM InterWorking Functions Statistics Tables.

          
          frxIwfStatsTable OBJECT-TYPE
              SYNTAX  SEQUENCE OF FrxIwfStatsEntry
              ACCESS  not-accessible
              STATUS  mandatory
              DESCRIPTION
                 "The FR/ATM InterWorking (FRF.5/FRF.8) configuration table."
               ::= { frxInterworking 3 }


          frxIwfStatsEntry OBJECT-TYPE
              SYNTAX  FrxIwfStatsEntry
              ACCESS  not-accessible
              STATUS  mandatory
              DESCRIPTION
                 "An entry in the FR/ATM IWF configuration table."
              INDEX   { frxIwfStatsSlotIndex, 
                        frxIwfStatsPortIndex,
                        frxIwfStatsVpiIndex,
                        frxIwfStatsVciIndex }
               ::= { frxIwfStatsTable 1 }


          FrxIwfStatsEntry ::=
              SEQUENCE {
                   frxIwfStatsSlotIndex
                       INTEGER,

                   frxIwfStatsPortIndex
                       INTEGER,

                   frxIwfStatsVpiIndex
                       INTEGER,

                   frxIwfStatsVciIndex
                       INTEGER,

                   frxIwfStatsFramesIn
                       INTEGER,

                   frxIwfStatsOctetsOut
                       INTEGER,

                   frxIwfStatsOctetsIn
                       INTEGER,

                   frxIwfStatsFramesOut
                       INTEGER,

                   frxIwfStatsFr2AtmEthernet
                       INTEGER,

                   frxIwfStatsFr2Atm8025
                       INTEGER,

                   frxIwfStatsFr2AtmFddi
                       INTEGER,

                   frxIwfStatsFr2AtmIp
                       INTEGER,

                   frxIwfStatsFr2AtmIpx
                       INTEGER,

                   frxIwfStatsFr2AtmBpdu
                       INTEGER,

                   frxIwfStatsFr2AtmArp
                       INTEGER,

                   frxIwfStatsFr2AtmInArp
                       INTEGER,

                   frxIwfStatsFr2AtmIso
                       INTEGER,

                   frxIwfStatsFr2Atm8026
                       INTEGER,

                   frxIwfStatsAtm2FrEthernet
                       INTEGER,

                   frxIwfStatsAtm2Fr8025
                       INTEGER,

                   frxIwfStatsAtm2FrFddi
                       INTEGER,

                   frxIwfStatsAtm2FrIp
                       INTEGER,

                   frxIwfStatsAtm2FrIpx
                       INTEGER,

                   frxIwfStatsAtm2FrBpdu
                       INTEGER,

                   frxIwfStatsAtm2FrArp
                       INTEGER,

                   frxIwfStatsAtm2FrInArp
                       INTEGER,

                   frxIwfStatsAtm2FrIso
                       INTEGER,

                   frxIwfStatsAtm2Fr8026
                       INTEGER,

                   frxIwfStatsFr2AtmMgmt
                       INTEGER,

                   frxIwfStatsAtm2FrMgmt
                       INTEGER
               }


          frxIwfStatsSlotIndex OBJECT-TYPE
              SYNTAX   INTEGER (1..9)
              ACCESS   read-only
              STATUS   mandatory
              DESCRIPTION
                 "A unique value which identifies the slot which has an
                 ASM with an IWF ."
              ::= { frxIwfStatsEntry 1 }


          frxIwfStatsPortIndex OBJECT-TYPE
              SYNTAX   INTEGER (1..2)
              ACCESS   read-only
              STATUS   mandatory
              DESCRIPTION
                 "A unique value which identifies this ATM submodule port."
              ::= { frxIwfStatsEntry 2 }


          frxIwfStatsVpiIndex OBJECT-TYPE
              SYNTAX   INTEGER (0..0)
              ACCESS   read-only
              STATUS   mandatory
              DESCRIPTION
                 "The virtual path identifier associated with this
                 virtual connection."
              ::= { frxIwfStatsEntry 3 }


          frxIwfStatsVciIndex OBJECT-TYPE
              SYNTAX   INTEGER (1..1023)
              ACCESS   read-only
              STATUS   mandatory
              DESCRIPTION
                 "A unique value which identifies this ATM virtual channel.
                 Several FR PVCs can be multiplexed to a single ATM vpi/vci
                 for FRF.5 service only."
              ::= { frxIwfStatsEntry 4 }


          frxIwfStatsFramesIn OBJECT-TYPE
              SYNTAX   INTEGER 
              ACCESS   read-only
              STATUS   mandatory
              DESCRIPTION
                 "The number of FR frames received by the IWF in FR to ATM
                 direction."
              ::= { frxIwfStatsEntry 5 }


          frxIwfStatsOctetsOut OBJECT-TYPE
              SYNTAX   INTEGER 
              ACCESS   read-only
              STATUS   mandatory
              DESCRIPTION
                 "The number of ATM octets sent out by the IWF in FR to ATM
                 direction."
              ::= { frxIwfStatsEntry 6 }


          frxIwfStatsOctetsIn OBJECT-TYPE
              SYNTAX   INTEGER 
              ACCESS   read-only
              STATUS   mandatory
              DESCRIPTION
                 "The number of ATM octets received by the IWF in ATM to FR
                 direction."
              ::= { frxIwfStatsEntry 7 }


          frxIwfStatsFramesOut OBJECT-TYPE
              SYNTAX   INTEGER 
              ACCESS   read-only
              STATUS   mandatory
              DESCRIPTION
                 "The number of FR frames sent out by the IWF in ATM to FR
                 direction."
              ::= { frxIwfStatsEntry 8 }


          frxIwfStatsFr2AtmEthernet OBJECT-TYPE
              SYNTAX   INTEGER 
              ACCESS   read-only
              STATUS   mandatory
              DESCRIPTION
                 "The number of ethernet frames through the IWF in FR to ATM
                 direction."
              ::= { frxIwfStatsEntry 9 }


          frxIwfStatsFr2Atm8025 OBJECT-TYPE
              SYNTAX   INTEGER 
              ACCESS   read-only
              STATUS   mandatory
              DESCRIPTION
                 "The number of IEEE 802.5 frames through the IWF in FR to ATM
                 direction."
              ::= { frxIwfStatsEntry 10 }


          frxIwfStatsFr2AtmFddi OBJECT-TYPE
              SYNTAX   INTEGER 
              ACCESS   read-only
              STATUS   mandatory
              DESCRIPTION
                 "The number of Fddi frames through the IWF in FR to ATM
                 direction."
              ::= { frxIwfStatsEntry 11 }


          frxIwfStatsFr2AtmIp OBJECT-TYPE
              SYNTAX   INTEGER 
              ACCESS   read-only
              STATUS   mandatory
              DESCRIPTION
                 "The number of IP frames through the IWF in FR to ATM
                 direction."
              ::= { frxIwfStatsEntry 12 }


          frxIwfStatsFr2AtmIpx OBJECT-TYPE
              SYNTAX   INTEGER 
              ACCESS   read-only
              STATUS   mandatory
              DESCRIPTION
                 "The number of IPX frames through the IWF in FR to ATM
                 direction."
              ::= { frxIwfStatsEntry 13 }


          frxIwfStatsFr2AtmBpdu OBJECT-TYPE
              SYNTAX   INTEGER 
              ACCESS   read-only
              STATUS   mandatory
              DESCRIPTION
                 "The number of IPX frames through the IWF in FR to ATM
                 direction."
              ::= { frxIwfStatsEntry 14 }


          frxIwfStatsFr2AtmArp OBJECT-TYPE
              SYNTAX   INTEGER 
              ACCESS   read-only
              STATUS   mandatory
              DESCRIPTION
                 "The number of ARP frames through the IWF in FR to ATM
                 direction."
              ::= { frxIwfStatsEntry 15 }


          frxIwfStatsFr2AtmInArp OBJECT-TYPE
              SYNTAX   INTEGER 
              ACCESS   read-only
              STATUS   mandatory
              DESCRIPTION
                 "The number of InARP frames through the IWF in FR to ATM
                 direction."
              ::= { frxIwfStatsEntry 16 }


          frxIwfStatsFr2AtmIso OBJECT-TYPE
              SYNTAX   INTEGER 
              ACCESS   read-only
              STATUS   mandatory
              DESCRIPTION
                 "The number of ISO (CLNP/ISIS) frames through the IWF 
                  in FR to ATM direction."
              ::= { frxIwfStatsEntry 17 }


          frxIwfStatsFr2Atm8026 OBJECT-TYPE
              SYNTAX   INTEGER 
              ACCESS   read-only
              STATUS   mandatory
              DESCRIPTION
                 "The number of IEEE 802.6 frames through the IWF 
                  in FR to ATM direction."
              ::= { frxIwfStatsEntry 18 }


          frxIwfStatsAtm2FrEthernet OBJECT-TYPE
              SYNTAX   INTEGER 
              ACCESS   read-only
              STATUS   mandatory
              DESCRIPTION
                 "The number of ethernet frames through the IWF in ATM to FR
                 direction."
              ::= { frxIwfStatsEntry 19 }


          frxIwfStatsAtm2Fr8025 OBJECT-TYPE
              SYNTAX   INTEGER 
              ACCESS   read-only
              STATUS   mandatory
              DESCRIPTION
                 "The number of IEEE 802.5 frames through the IWF in ATM to FR
                 direction."
              ::= { frxIwfStatsEntry 20 }


          frxIwfStatsAtm2FrFddi OBJECT-TYPE
              SYNTAX   INTEGER 
              ACCESS   read-only
              STATUS   mandatory
              DESCRIPTION
                 "The number of Fddi frames through the IWF in ATM to FR
                 direction."
              ::= { frxIwfStatsEntry 21 }


          frxIwfStatsAtm2FrIp OBJECT-TYPE
              SYNTAX   INTEGER 
              ACCESS   read-only
              STATUS   mandatory
              DESCRIPTION
                 "The number of IP frames through the IWF in ATM to FR
                 direction."
              ::= { frxIwfStatsEntry 22 }


          frxIwfStatsAtm2FrIpx OBJECT-TYPE
              SYNTAX   INTEGER 
              ACCESS   read-only
              STATUS   mandatory
              DESCRIPTION
                 "The number of IPX frames through the IWF in ATM to FR
                 direction."
              ::= { frxIwfStatsEntry 23 }


          frxIwfStatsAtm2FrBpdu OBJECT-TYPE
              SYNTAX   INTEGER 
              ACCESS   read-only
              STATUS   mandatory
              DESCRIPTION
                 "The number of IPX frames through the IWF in ATM to FR
                 direction."
              ::= { frxIwfStatsEntry 24 }


          frxIwfStatsAtm2FrArp OBJECT-TYPE
              SYNTAX   INTEGER 
              ACCESS   read-only
              STATUS   mandatory
              DESCRIPTION
                 "The number of ARP frames through the IWF in ATM to FR
                 direction."
              ::= { frxIwfStatsEntry 25 }


          frxIwfStatsAtm2FrInArp OBJECT-TYPE
              SYNTAX   INTEGER 
              ACCESS   read-only
              STATUS   mandatory
              DESCRIPTION
                 "The number of InARP frames through the IWF in ATM to FR
                 direction."
              ::= { frxIwfStatsEntry 26 }


          frxIwfStatsAtm2FrIso OBJECT-TYPE
              SYNTAX   INTEGER 
              ACCESS   read-only
              STATUS   mandatory
              DESCRIPTION
                 "The number of ISO (CLNP/ISIS) frames through the IWF 
                 in ATM to FR direction."
              ::= { frxIwfStatsEntry 27 }


          frxIwfStatsAtm2Fr8026 OBJECT-TYPE
              SYNTAX   INTEGER 
              ACCESS   read-only
              STATUS   mandatory
              DESCRIPTION
                 "The number of IEEE 802.6 frames through the IWF 
                 in ATM to FR direction."
              ::= { frxIwfStatsEntry 28 }


          frxIwfStatsFr2AtmMgmt OBJECT-TYPE
              SYNTAX   INTEGER 
              ACCESS   read-only
              STATUS   mandatory
              DESCRIPTION
                 "The number of Management frames through IWF in FR to
                 ATM direction."
              ::= { frxIwfStatsEntry 29 }


          frxIwfStatsAtm2FrMgmt OBJECT-TYPE
              SYNTAX   INTEGER 
              ACCESS   read-only
              STATUS   mandatory
              DESCRIPTION
                 "The number of Management frames through IWF in ATM to
                 FR direction."
              ::= { frxIwfStatsEntry 30 }


END
