ALCATEL-IND1-RIP-MIB DEFINITIONS ::= BEGIN

    IMPORTS
        MODULE-IDENTITY, OBJECT-IDENTITY, OBJECT-TYPE, IpAddress, TimeTicks
            FROM SNMPv2-SMI
        DisplayString, RowStatus
            FROM SNMPv2-TC
        MODULE-COMPLIANCE, OBJECT-GROUP
            FROM SNMPv2-CONF
	    routingIND1Rip
		    FROM ALCATEL-IND1-BASE;
		
		
    alcatelIND1RIPMIB MODULE-IDENTITY
        LAST-UPDATED "200109181335Z"
        ORGANIZATION "Alcatel - Architects Of An Internet World"
        CONTACT-INFO
                " Please consult with Customer Service to insure the most appropriate
                  version of this document is used with the products in question:
             
                            Alcatel Internetworking, Incorporated
                           (Division 1, Formerly XYLAN Corporation)
                                   26801 West Agoura Road
                                Agoura Hills, CA  91301-5122
                                  United States Of America
            
                Telephone:               North America  +1 800 995 2696
                                         Latin America  +1 877 919 9526
                                         Europe         +31 23 556 0100
                                         Asia           +65 394 7933
                                         All Other      +1 818 878 4507
            
                Electronic Mail:         support@ind.alcatel.com
                World Wide Web:          http://www.ind.alcatel.com
                File Transfer Protocol:  ftp://ftp.ind.alcatel.com/pub/products/mibs"
    
        DESCRIPTION
                "This module describes an authoritative enterprise-specific Simple
                 Network Management Protocol (SNMP) Management Information Base (MIB):
             
                     For the Birds Of Prey Product Line
                     Configuration Of Global RIP Configuration Parameters.
             
                 The right to make changes in specification and other information
                 contained in this document without prior notice is reserved.
             
                 No liability shall be assumed for any incidental, indirect, special, or
                 consequential damages whatsoever arising from or related to this
                 document or the information contained herein.
             
                 Vendors, end-users, and other interested parties are granted
                 non-exclusive license to use this specification in connection with
                 management of the products for which it is intended to be used.
             
                   Copyright (C) 1995-2002 Alcatel Internetworking, Incorporated
                                 ALL RIGHTS RESERVED WORLDWIDE"
    
        REVISION         "200109181335Z"
        DESCRIPTION
            "The latest version of this MIB Module."
    
        ::= { routingIND1Rip 1 } 		
    
    alcatelIND1RIPMIBObjects OBJECT-IDENTITY
        STATUS current
        DESCRIPTION
            "Branch for Routing Information Protocol (RIP)
             Subsystem Managed Objects."
        ::= { alcatelIND1RIPMIB 1 }
    
    
    alcatelIND1RIPMIBConformance OBJECT-IDENTITY
        STATUS current
        DESCRIPTION
            "Branch for Routing Information Protocol (RIP)
             Subsystem Conformance Information."
        ::= { alcatelIND1RIPMIB 2 }
    
    
    alcatelIND1RIPMIBGroups OBJECT-IDENTITY
        STATUS current
        DESCRIPTION
            "Branch for Routing Information Protocol (RIP)
             Subsystem Units Of Conformance."
        ::= { alcatelIND1RIPMIBConformance 1 }
    
    
    alcatelIND1RIPMIBCompliances OBJECT-IDENTITY
        STATUS current
        DESCRIPTION
            "Branch for Routing Information Protocol (RIP)
             Subsystem Compliance Statements."
        ::= { alcatelIND1RIPMIBConformance 2 }
    
    
-- ************************************************************************
--  RIP Global Protocol configuration
-- ************************************************************************
    
    alaProtocolRip	OBJECT IDENTIFIER ::= { alcatelIND1RIPMIBObjects 1 }
       
    alaRipProtoStatus OBJECT-TYPE
        SYNTAX  INTEGER {
                        enable(1),
                        disable(2)
                    }
        MAX-ACCESS  read-write
        STATUS  current
        DESCRIPTION
            "Global administration status of RIP."
        DEFVAL { disable }
        ::= { alaProtocolRip 1 }
    
    alaRipHostRouteSupport OBJECT-TYPE
        SYNTAX  INTEGER {
                            enable(1),
                            disable(2)
                        }
        MAX-ACCESS  read-write
        STATUS  current
        DESCRIPTION
            "Enable or disable support for host routes."
        DEFVAL { enable }
        ::= { alaProtocolRip 2 }

    alaRipRedistAdminStatus OBJECT-TYPE
        SYNTAX  INTEGER {
                    enable(1),
                    disable(2)
                }
        MAX-ACCESS  read-write
        STATUS  current
        DESCRIPTION
            "Enable or disable redistribution of routes into RIP."
        DEFVAL { 2 }
    ::= { alaProtocolRip 3 }
    
    alaRipRedistRouteTag OBJECT-TYPE
        SYNTAX  INTEGER ( 0 .. 2147483647 )
        MAX-ACCESS  read-write
        STATUS  current
        DESCRIPTION
            "A 32-bit value tagged to each RIP internal route while
        it is redistributed in to other routing protocol domains. The
        lower 16-bits typically indicate the autonomous system number."
        DEFVAL { 0 }
    ::= { alaProtocolRip 4 }
    
    alaRipForceHolddownTimer OBJECT-TYPE
        SYNTAX INTEGER ( 0 .. 120 )
        MAX-ACCESS read-write
        STATUS current
        DESCRIPTION
            "Interval in seconds during which routing information regarding 
        better paths is suppressed. A route enters into a forced holddown 
        state when an update packet is received that indicates the route is 
        unreachable and when this timer value is nonzero. After this timer 
        has expired, if the value is less that 120 - the route enters a 
        holddown state for the rest of the period until 120. During this time
        advertisements for better paths are accepted if any."
        ::= { alaProtocolRip 5 }

    alaRipRouteNumber OBJECT-TYPE
        SYNTAX  INTEGER ( 0 .. 2147483647 )
        MAX-ACCESS  read-only
        STATUS  current
        DESCRIPTION
            "The number of network routes in RIP routing table."
        ::= { alaProtocolRip 6 }


-- ************************************************************************
--  RIP Redistribution Protocol configuration 
-- ************************************************************************

	alaRipRedistProtoTable  OBJECT-TYPE
		SYNTAX    SEQUENCE OF AlaRipRedistProtoEntry
		MAX-ACCESS    not-accessible
		STATUS    current
		DESCRIPTION
			"Protocol based configuration for route redistribution using RIP."
		::= { alaProtocolRip 7 }
    
    alaRipRedistProtoEntry OBJECT-TYPE
        SYNTAX    AlaRipRedistProtoEntry
        MAX-ACCESS    not-accessible
        STATUS    current
        DESCRIPTION
            "A range of routes from a protocol to be redistributed using RIP."
        INDEX   { alaRipRedistProtoId }
    ::= { alaRipRedistProtoTable 1 }
    
    AlaRipRedistProtoEntry ::=
        SEQUENCE {
            alaRipRedistProtoId          INTEGER,
            alaRipRedistProtoMetric      INTEGER,
            alaRipRedistProtoStatus      RowStatus
        }
    
    alaRipRedistProtoId   OBJECT-TYPE
        SYNTAX  INTEGER 
                {
                   other(1),      -- not specified
                   local(2),      -- local interfaces on which OSPF is not enabled
                   directHost(3), -- hosts on a directly connected network
                   netmgmt(4),    -- static routes
                   rip(5),        -- Routing Information Protocol
                   ospf(6),       -- Open Shortest Path First
                   isis(7),       -- IS-IS
                   bgp(8)         -- Border Gateway Protocol
                 }
        MAX-ACCESS  read-only
        STATUS  current
        DESCRIPTION
            "The routing mechanism via which the routes, to be redistributed
        using RIP, are learned."
        ::= { alaRipRedistProtoEntry 1 }
    
    alaRipRedistProtoMetric   OBJECT-TYPE
         SYNTAX   INTEGER (0 .. 15 )
         MAX-ACCESS   read-write
         STATUS   current
         DESCRIPTION
             "Default metric to be used for redistributing routes."
         DEFVAL    { 0 }
         ::= { alaRipRedistProtoEntry 2 }
    
    alaRipRedistProtoStatus OBJECT-TYPE
        SYNTAX  RowStatus 
        MAX-ACCESS  read-write
        STATUS  current
        DESCRIPTION
             "Add or Delete entries."
        DEFVAL  { notInService }
        ::= { alaRipRedistProtoEntry 3 }
    

-- ************************************************************************
--  RIP Debug Configuration 
-- ************************************************************************
     
     alaRipDebug OBJECT IDENTIFIER ::= { alcatelIND1RIPMIBObjects 2 }

     alaRipDebugLevel OBJECT-TYPE
         SYNTAX  INTEGER (0..255)
         MAX-ACCESS  read-write
         STATUS  current
         DESCRIPTION
               "Sets the level of Debugging for DRC RIP on
                this router.  A level of 0 indicates no debugging."
         DEFVAL { 0 }
         ::= { alaRipDebug 1 }
     
	 alaRipDebugError OBJECT-TYPE
		SYNTAX  INTEGER 
					{
						enable(1),
						disable(2)
			   		}
		MAX-ACCESS read-write
		STATUS     current
		DESCRIPTION
			"Administratively enables/disables debugging for DRC RIP
			ERROR messages if the alaRipDebugLevel is greater than 0."
		DEFVAL     { disable }
			::= { alaRipDebug 2}

	 alaRipDebugWarn OBJECT-TYPE
		SYNTAX  INTEGER 
					{
						enable(1),
						disable(2)
			   		}
		MAX-ACCESS read-write
		STATUS     current
		DESCRIPTION
			"Administratively enables/disables debugging for DRC RIP
			Warning messages if the alaRipDebugLevel is greater than 0." 
		DEFVAL     { disable }
			::= { alaRipDebug 3}

	 alaRipDebugRecv OBJECT-TYPE
		SYNTAX  INTEGER 
					{
						enable(1),
						disable(2)
			   		}
		MAX-ACCESS read-write
		STATUS     current
		DESCRIPTION
			"Administratively enables/disables debugging for DRC RIP 
			RECV messages if the alaRipDebugLevel is greater than 0"  
		DEFVAL     { disable }
			::= { alaRipDebug 4}

	 alaRipDebugSend OBJECT-TYPE
		SYNTAX  INTEGER 
					{
						enable(1),
						disable(2)
			   		}
		MAX-ACCESS read-write
		STATUS     current
		DESCRIPTION
			"Administratively enables/disables debugging for DRC RIP 
			SEND messages if the alaRipDebugLevel is greater than 0"
		DEFVAL     { disable }
			::= { alaRipDebug 5}

	 alaRipDebugRdb OBJECT-TYPE
		SYNTAX  INTEGER 
					{
						enable(1),
						disable(2)
			   		}
		MAX-ACCESS read-write
		STATUS     current
		DESCRIPTION
			"Administratively enables/disables debugging for DRC RIP 
			Routing DataBase messages if the alaRipDebugLevel is 
			greater than 0"
		DEFVAL     { disable }
			::= { alaRipDebug 6}

	 alaRipDebugAge OBJECT-TYPE
		SYNTAX  INTEGER 
					{
						enable(1),
						disable(2)
			   		}
		MAX-ACCESS read-write
		STATUS     current
		DESCRIPTION
			"Administratively enables/disables debugging for DRC RIP 
			Database aging messages if the alaRipDebugLevel is greater 
			than 0" 
		DEFVAL     { disable }
			::= { alaRipDebug 7}

	 alaRipDebugConfig OBJECT-TYPE
		SYNTAX  INTEGER 
					{
						enable(1),
						disable(2)
			   		}
		MAX-ACCESS read-write
		STATUS     current
		DESCRIPTION
			"Administratively enables/disables debugging for DRC RIP  
			configuration messages if the alaRipDebugLevel is greater than 0"
		DEFVAL     { disable }
			::= { alaRipDebug 8}

	 alaRipDebugRedist OBJECT-TYPE
		SYNTAX  INTEGER 
					{
						enable(1),
						disable(2)
			   		}
		MAX-ACCESS read-write
		STATUS     current
		DESCRIPTION
			"Administratively enables/disables debugging for DRC RIP 
			Redistribution messages if the alaRipDebugLevel is greater than 0"	
		DEFVAL     { disable }
			::= { alaRipDebug 9}

	 alaRipDebugInfo OBJECT-TYPE
		SYNTAX  INTEGER 
					{
						enable(1),
						disable(2)
			   		}
		MAX-ACCESS read-write
		STATUS     current
		DESCRIPTION
			"Administratively enables/disables debugging for DRC RIP
			Information messages if the alaRipDebugLevel is greater than 0" 
		DEFVAL     { disable }
			::= { alaRipDebug 10}

	 alaRipDebugSetup OBJECT-TYPE
		SYNTAX  INTEGER 
					{
						enable(1),
						disable(2)
			   		}
		MAX-ACCESS read-write
		STATUS     current
		DESCRIPTION
			"Administratively enables/disables debugging for DRC RIP 
			Setup messages if the alaRipDebugLevel is greater than 0" 
		DEFVAL     { disable }
			::= { alaRipDebug 11}

	 alaRipDebugTime OBJECT-TYPE
		SYNTAX  INTEGER 
					{
						enable(1),
						disable(2)
			   		}
		MAX-ACCESS read-write
		STATUS     current
		DESCRIPTION
			"Administratively enables/disables debugging for DRC RIP
			Timer related messages if the alaRipDebugLevel is greater than 0" 
		DEFVAL     { disable }
			::= { alaRipDebug 12}

	 alaRipDebugAll OBJECT-TYPE
		SYNTAX  INTEGER 
					{
						enable(1),
						disable(2)
			   		}
		MAX-ACCESS read-write
		STATUS     current
		DESCRIPTION
			"Administratively enables/disables all debugging for DRC RIP 
			if the alaRipDebugLevel is greater than 0"
		DEFVAL     { disable }
			::= { alaRipDebug 13}


-- ************************************************************************
--  RIP route table statistics  
-- ************************************************************************
     
     alaRipRouteTable OBJECT-TYPE
         SYNTAX    SEQUENCE OF AlaRipRouteEntry
         MAX-ACCESS    not-accessible
         STATUS    current
         DESCRIPTION
             "RIP routing table which contains the network routes."
         ::= { alaProtocolRip 9 }
     
     alaRipRouteEntry OBJECT-TYPE
         SYNTAX   AlaRipRouteEntry
         MAX-ACCESS   not-accessible
         STATUS   current
         DESCRIPTION
             "RIP routing table which contains the network routes."
         INDEX {
                 alaRipRouteDest,
                 alaRipRouteMask
               }
         ::= { alaRipRouteTable 1 }
     
     AlaRipRouteEntry ::=
         SEQUENCE {
             alaRipRouteDest
                 IpAddress,
             alaRipRouteMask
                 IpAddress,
             alaRipRouteNextHop
                 IpAddress,
             alaRipRouteType
                 INTEGER,
             alaRipRouteAge
                 TimeTicks,
             alaRipRouteTag
                 INTEGER,
             alaRipRouteMetric
                 INTEGER,
             alaRipRouteStatus
                 RowStatus
         }
     
     alaRipRouteDest OBJECT-TYPE
         SYNTAX   IpAddress
         MAX-ACCESS   read-only
         STATUS   current
         DESCRIPTION
            "The destination IP address of this route."
         ::= { alaRipRouteEntry 1 }
     
     alaRipRouteMask OBJECT-TYPE
         SYNTAX   IpAddress
         MAX-ACCESS   read-only
         STATUS   current
         DESCRIPTION
            "The network mask for this route."
         ::= { alaRipRouteEntry 2 }
     
     alaRipRouteNextHop OBJECT-TYPE
         SYNTAX   IpAddress
         MAX-ACCESS   read-only
         STATUS   current
         DESCRIPTION
            "The address of the next hop to reach this route."
         ::= { alaRipRouteEntry 3 }
     
     alaRipRouteType OBJECT-TYPE
         SYNTAX   INTEGER 
                  {
                     local  (1), -- local route
                     remote (2), -- remote route
                     redistribute (3)  -- redistributed route
                  }
         MAX-ACCESS   read-only
         STATUS   current
         DESCRIPTION
            "The type of route."
         ::= { alaRipRouteEntry 4 }
     
     alaRipRouteAge OBJECT-TYPE
         SYNTAX   TimeTicks
         MAX-ACCESS   read-only
         STATUS   current
         DESCRIPTION
            "The number of seconds  since  this  route  was last
            updated  or  otherwise  determined  to be correct."
         ::= { alaRipRouteEntry 5 }
     
     alaRipRouteTag OBJECT-TYPE
         SYNTAX   INTEGER ( 0 .. 2147483647 )
         MAX-ACCESS   read-only
         STATUS   current
         DESCRIPTION
            "The associated route tag"
         DEFVAL { 0 }
         ::= { alaRipRouteEntry 6 }
    
     alaRipRouteMetric OBJECT-TYPE
         SYNTAX   INTEGER ( 0 .. 15 )
         MAX-ACCESS   read-only
         STATUS   current
         DESCRIPTION
            "The routing  metric  for  this  route."
         ::= { alaRipRouteEntry 7 }
     
     alaRipRouteStatus OBJECT-TYPE
         SYNTAX   RowStatus
         MAX-ACCESS read-only
         STATUS    current
         DESCRIPTION
            "The row status variable, used according to
            row installation and removal conventions."
         ::= { alaRipRouteEntry 8 }
    

-- ************************************************************************
--  RIP Redistribution filter configuration 
-- ************************************************************************
     
    alaRipRedistRouteTable OBJECT-TYPE
        SYNTAX    SEQUENCE OF AlaRipRedistRouteEntry
        MAX-ACCESS    not-accessible
        STATUS    current
        DESCRIPTION
            "A configuration table which controls the routes to be 
        redistributed by RIP from other routing protocols."
        ::= { alaProtocolRip 10 }
    
    alaRipRedistRouteEntry OBJECT-TYPE
        SYNTAX   AlaRipRedistRouteEntry
        MAX-ACCESS   not-accessible
        STATUS   current
        DESCRIPTION
            "An entry of alaRipRedistRouteTable which specifies a route or
        set of routes to be redistributed by RIP from another routing protocol."
        INDEX {
                alaRipRedistRouteProto,
                alaRipRedistRouteDest,
                alaRipRedistRouteMask
              }
        ::= { alaRipRedistRouteTable 1 }
    
    AlaRipRedistRouteEntry ::=
        SEQUENCE {
            alaRipRedistRouteProto
                INTEGER,
            alaRipRedistRouteDest
                IpAddress,
            alaRipRedistRouteMask
                IpAddress,
            alaRipRedistRouteMetric
                INTEGER,
            alaRipRedistRouteControl
                INTEGER,
            alaRipRedistRouteTagMatch
                INTEGER,
            alaRipRedistRouteEffect
                INTEGER,
            alaRipRedistRouteStatus
                RowStatus
        }
    
    alaRipRedistRouteProto OBJECT-TYPE
        SYNTAX   INTEGER 
                 {
                     other(1),   -- not specified
                     local(2),   -- local routes 
                     directHost(3), -- hosts on a directly connected network
                     netmgmt(4), -- static routes
                     ospf(6),    -- Open Shortest Path First
                     isis(7),    -- IS-IS
                     bgp(8)      -- Border Gateway Protocol
                 }
        MAX-ACCESS   read-only
        STATUS   current
        DESCRIPTION
           "Protocol from which this route is to be imported into RIP."
        ::= { alaRipRedistRouteEntry 1 }
    
    alaRipRedistRouteDest OBJECT-TYPE
        SYNTAX   IpAddress
        MAX-ACCESS   read-only
        STATUS   current
        DESCRIPTION
           "The destination IP address of this route."
        ::= { alaRipRedistRouteEntry 2 }
    
    alaRipRedistRouteMask OBJECT-TYPE
        SYNTAX   IpAddress
        MAX-ACCESS   read-only
        STATUS   current
        DESCRIPTION
           "The network mask for this route."
        ::= { alaRipRedistRouteEntry 3 }
    
    alaRipRedistRouteMetric OBJECT-TYPE
        SYNTAX   INTEGER ( 0 .. 15 )
        MAX-ACCESS   read-write
        STATUS   current
        DESCRIPTION
           "The metric to be used for the redistributed route. A value
        of 0 means that the metric used should be the value configured
        in alaRipRedistProtoMetric for this protocol."
        DEFVAL { 0 }
        ::= { alaRipRedistRouteEntry 4 }
    
    alaRipRedistRouteControl OBJECT-TYPE
        SYNTAX   INTEGER 
                 {
                     redistribute-all-subnets(1),
                     redistribute-as-aggregate(2),
                     redistribute-exact-match(3)
                 }
        MAX-ACCESS   read-write
        STATUS   current
        DESCRIPTION
           "Specifies how routes matching this entry are to be redistributed
        into RIP. The different mechanisms possible are to redistribute all
        the subnet routes, redistribute an aggregated route if there are
        one or more actual routes which match this entry or redistribute
        only an exactly matching route."
        DEFVAL { redistribute-all-subnets }
        ::= { alaRipRedistRouteEntry 5 }
    
    alaRipRedistRouteTagMatch OBJECT-TYPE
        SYNTAX   INTEGER ( -2147483648 .. 2147483647 )
        MAX-ACCESS   read-write
        STATUS   current
        DESCRIPTION
           "Redistribute the route only when the route tag matches with this
        value. It defaults to -1 which matches all route tags."
        DEFVAL { -1 }
        ::= { alaRipRedistRouteEntry 6 }
    
    alaRipRedistRouteEffect  OBJECT-TYPE
        SYNTAX  INTEGER 
                {
                    redistribute(1),
                    doNotRedistribute(2)
                }
        MAX-ACCESS  read-write
        STATUS  current
        DESCRIPTION
            "Specifies whether the redistribution of routes in this range
        is allowed or denied."
        DEFVAL { redistribute }
        ::= { alaRipRedistRouteEntry 7 }
    
    alaRipRedistRouteStatus OBJECT-TYPE
        SYNTAX    RowStatus
        MAX-ACCESS    read-write
        STATUS    current
        DESCRIPTION
           "The row status variable, used according to
           row installation and removal conventions."
        ::= { alaRipRedistRouteEntry 8 }
    
    
--
-- Compliance Statements
--
    
     alcatelIND1RIPMIBCompliance MODULE-COMPLIANCE
        STATUS current
        DESCRIPTION
            "Compliance statement for 
             Routing Information Protocol (RIP) Subsystem."
        MODULE -- this module
    
            MANDATORY-GROUPS
            {
               alaRipMiscellaneousGroup,
               alaRipRedistProtoGroup,
               alaRipDebugGroup,
               alaRipRouteGroup,
               alaRipRedistRouteGroup
            }
    
        ::= { alcatelIND1RIPMIBCompliances 1 }
    
    
--
-- Units of Conformance
--
    
     alaRipMiscellaneousGroup OBJECT-GROUP
        OBJECTS
        {
           alaRipRedistAdminStatus,
           alaRipRedistRouteTag,
           alaRipForceHolddownTimer,
           alaRipRouteNumber
        }
        STATUS current
        DESCRIPTION
            "Collection of Miscellaneous objects for management of RIP."
        ::= { alcatelIND1RIPMIBGroups 1 }
    
    
     alaRipRedistProtoGroup OBJECT-GROUP
        OBJECTS
        {
           alaRipRedistProtoId,           -- Route Redistribution Protocol table
           alaRipRedistProtoMetric,
           alaRipRedistProtoStatus
        }
        STATUS current
        DESCRIPTION
            "Collection of objects for management of Route Redistribution Protocol."
        ::= { alcatelIND1RIPMIBGroups 2 }
    
     alaRipDebugGroup OBJECT-GROUP
        OBJECTS
        {
            alaRipDebugLevel, 
	        alaRipDebugError, 
	        alaRipDebugWarn, 
	        alaRipDebugRecv,
	        alaRipDebugSend,
	        alaRipDebugRdb,
	        alaRipDebugAge,
	        alaRipDebugConfig,
	        alaRipDebugRedist,
	        alaRipDebugInfo,
	        alaRipDebugSetup,
	        alaRipDebugTime,
	        alaRipDebugAll
        }
        STATUS current
        DESCRIPTION
            "Collection of objects for management of 
             Debug Information."
        ::= { alcatelIND1RIPMIBGroups 3 }
    
     alaRipRouteGroup OBJECT-GROUP
        OBJECTS
        {
           alaRipRouteNumber,
           alaRipRouteDest,
           alaRipRouteMask,
           alaRipRouteNextHop,
           alaRipRouteType,
           alaRipRouteAge,
           alaRipRouteTag,
           alaRipRouteMetric, 
           alaRipRouteStatus
        }
        STATUS current
        DESCRIPTION
            "Collection of objects for management of Network Route configuration."
        ::= { alcatelIND1RIPMIBGroups 4 }
    
     alaRipRedistRouteGroup OBJECT-GROUP
        OBJECTS
        {
           alaRipRedistRouteTag,
           alaRipRedistRouteProto,
           alaRipRedistRouteDest,
           alaRipRedistRouteMask,
           alaRipRedistRouteMetric,
           alaRipRedistRouteControl,
           alaRipRedistRouteTagMatch,
           alaRipRedistRouteEffect,
           alaRipRedistRouteStatus
        }
        STATUS current
        DESCRIPTION
            "Collection of objects for management of 
             Route Redistribution configuration."
        ::= { alcatelIND1RIPMIBGroups 5 }

END
