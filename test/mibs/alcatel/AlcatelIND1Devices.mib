ALCATEL-IND1-DEVICES DEFINITIONS ::= BEGIN


IMPORTS
    MODULE-IDENTITY, OBJECT-IDENTITY
FROM
    SNMPv2-SMI

    hardwareIND1Devices
FROM
    ALCATEL-IND1-BASE;


alcatelIND1DevicesMIB MODULE-IDENTITY

    LAST-UPDATED  "200112200000Z"
    ORGANIZATION  "Alcatel - Architects Of An Internet World"
    CONTACT-INFO
        "Please consult with Customer Service to insure the most appropriate
         version of this document is used with the products in question:
         
                    Alcatel Internetworking, Incorporated
                   (Division 1, Formerly XYLAN Corporation)
                           26801 West Agoura Road
                        Agoura Hills, CA  91301-5122
                          United States Of America
        
        Telephone:               North America  +1 800 995 2696
                                 Latin America  +1 877 919 9526
                                 Europe         +31 23 556 0100
                                 Asia           +65 394 7933
                                 All Other      +1 818 878 4507
        
        Electronic Mail:         support@ind.alcatel.com
        World Wide Web:          http://www.ind.alcatel.com
        File Transfer Protocol:  ftp://ftp.ind.alcatel.com/pub/products/mibs"
    
    DESCRIPTION
        "This module describes an authoritative enterprise-specific Simple
         Network Management Protocol (SNMP) Management Information Base (MIB):
         
             This module provides Object Indentifier definitions for
             Chassis and Modules of the Alcatel Internetworking
             OmniSwitch 8000/7000/4000 Series Product Lines.
         
         The right to make changes in specification and other information
         contained in this document without prior notice is reserved.
         
         No liability shall be assumed for any incidental, indirect, special, or
         consequential damages whatsoever arising from or related to this
         document or the information contained herein.
         
         Vendors, end-users, and other interested parties are granted
         non-exclusive license to use this specification in connection with
         management of the products for which it is intended to be used.
         
           Copyright (C) 1995-2002 Alcatel Internetworking, Incorporated
                         ALL RIGHTS RESERVED WORLDWIDE"

    REVISION      "200112200000Z"
    DESCRIPTION
        "Initial version of this MIB Module."

    ::= { hardwareIND1Devices 1 }



familyOmniSwitch7000 OBJECT-IDENTITY
    STATUS current
    DESCRIPTION
        "Branch For OmniSwitch 7000 Series Product Family."
    ::= { alcatelIND1DevicesMIB 1 }




chassisOmniSwitch7000 OBJECT-IDENTITY
    STATUS current
    DESCRIPTION
        "Branch For OmniSwitch 7000 Series Chassis."
    ::= { familyOmniSwitch7000 1 }


deviceOmniSwitch7700 OBJECT-IDENTITY
    STATUS current
    DESCRIPTION
        "OmniSwitch 7700 10-Slot Chassis.
        Model Name: OS7700
        Assembly:   901749-10
        sysObjectID:  1.3.6.1.4.1.6486.800.1.1.2.1.1.1.1"
    ::= { chassisOmniSwitch7000 1 }


deviceOmniSwitch7800 OBJECT-IDENTITY
    STATUS current
    DESCRIPTION
        "OmniSwitch 7800 18-Slot Chassis.
        Model Name: OS7800
        Assembly:   901748-10
        sysObjectID:  1.3.6.1.4.1.6486.800.1.1.2.1.1.1.2"
    ::= { chassisOmniSwitch7000 2 }




fansOmniSwitch7000 OBJECT-IDENTITY
    STATUS current
    DESCRIPTION
        "Branch For OmniSwitch 7000 Series Fan Trays."
    ::= { familyOmniSwitch7000 2 }


fansOmniSwitch7000FT OBJECT-IDENTITY
    STATUS current
    DESCRIPTION
        "OmniSwitch 7000 Series Fan Tray.
        Model Name: OS7000-FT
        Assembly:   901752-10
        sysObjectID:  1.3.6.1.4.1.6486.800.1.1.2.1.1.2.1"
    ::= { fansOmniSwitch7000 1 }




powersOmniSwitch7000 OBJECT-IDENTITY
    STATUS current
    DESCRIPTION
        "Branch For OmniSwitch 7000 Series Power Supplies."
    ::= { familyOmniSwitch7000 3 }


powersOmniSwitch7000PS600AC OBJECT-IDENTITY
    STATUS current
    DESCRIPTION
        "OmniSwitch 7000 Series 600 Watt A/C Power Supply.
        Model Name: OS7-PS-0600AC
        Assembly:   901750-10
        sysObjectID:  1.3.6.1.4.1.6486.800.1.1.2.1.1.3.1"
    ::= { powersOmniSwitch7000 1 }


powersOmniSwitch7000PS600DC OBJECT-IDENTITY
    STATUS current
    DESCRIPTION
        "OmniSwitch 7000 Series 600 Watt D/C Power Supply.
        Model Name: OS7-PS-0600DC
        Assembly:   902076-10
        sysObjectID:  1.3.6.1.4.1.6486.800.1.1.2.1.1.3.2"
    ::= { powersOmniSwitch7000 2 }


powersOmniSwitch7000PDShelf OBJECT-IDENTITY
    STATUS current
    DESCRIPTION
        "OmniSwitch 7000 Series Inline Power Shelf.
        Model Name: OS7-PD-Shelf
        Assembly:   902067-10
        sysObjectID:  1.3.6.1.4.1.6486.800.1.1.2.1.1.3.3"
    ::= { powersOmniSwitch7000 3 }


powersOmniSwitch7000PDPS600AC OBJECT-IDENTITY
    STATUS current
    DESCRIPTION
        "OmniSwitch 7000 Series 600 Watt A/C Inline Power Supply.
        Model Name: OS7-PDPS-0900AC
        Assembly:   902068-10
        sysObjectID:  1.3.6.1.4.1.6486.800.1.1.2.1.1.3.4"
    ::= { powersOmniSwitch7000 4 }


powersOmniSwitch7000PDPS900DC OBJECT-IDENTITY
    STATUS current
    DESCRIPTION
        "OmniSwitch 7000 Series 900 Watt D/C Inline Power Supply.
        Model Name: OS7-PDPS-0900DC
        Assembly:   902069-10
        sysObjectID:  1.3.6.1.4.1.6486.800.1.1.2.1.1.3.5"
    ::= { powersOmniSwitch7000 5 }




modulesOmniSwitch7000 OBJECT-IDENTITY
    STATUS current
    DESCRIPTION
        "Branch For OmniSwitch 7000 Series Modules."
    ::= { familyOmniSwitch7000 4 }




modulesOmniSwitch7000CM OBJECT-IDENTITY
    STATUS current
    DESCRIPTION
        "Branch For OmniSwitch 7000 Series Chassis Management (CM) Modules."
    ::= { modulesOmniSwitch7000 1 }



cmmOmniSwitch7700 OBJECT-IDENTITY
    STATUS current
    DESCRIPTION
        "OmniSwitch 7700 Series Chassis Management Module.
        Model Name: OS7700-CMM
        Assembly:   901750-10
        sysObjectID:  1.3.6.1.4.1.6486.800.1.1.2.1.1.4.1.1"
    ::= { modulesOmniSwitch7000CM 1 }


cmmOmniSwitch7700PROC OBJECT-IDENTITY
    STATUS current
    DESCRIPTION
        "OmniSwitch 7700 Series Chassis Management Module Processor.
        Model Name: OS7700-CMM Processor
        Assembly:   050358-06
        sysObjectID:  1.3.6.1.4.1.6486.800.1.1.2.1.1.4.1.1.1"
    ::= { cmmOmniSwitch7700 1 }


cmmOmniSwitch7700BBUS OBJECT-IDENTITY
    STATUS current
    DESCRIPTION
        "OmniSwitch 7700 Series Chassis Management Module BBUS Bridge.
        Model Name: OS7700-CMM BBUS Bridge
        Assembly:   050373-06
        sysObjectID:  1.3.6.1.4.1.6486.800.1.1.2.1.1.4.1.1.2"
    ::= { cmmOmniSwitch7700 2 }



cmmOmniSwitch7800 OBJECT-IDENTITY
    STATUS current
    DESCRIPTION
        "OmniSwitch 7800 Series Chassis Management Module.
        Model Name: OS7800-CMM
        Assembly:   901953-10
        sysObjectID:  1.3.6.1.4.1.6486.800.1.1.2.1.1.4.1.2"
    ::= { modulesOmniSwitch7000CM 2 }


cmmOmniSwitch7800PROC OBJECT-IDENTITY
    STATUS current
    DESCRIPTION
        "OmniSwitch 7800 Series Chassis Management Module Processor.
        Model Name: OS7800-CMM Processor
        Assembly:   050358-06
        sysObjectID:  1.3.6.1.4.1.6486.800.1.1.2.1.1.4.1.2.1"
    ::= { cmmOmniSwitch7800 1 }


cmmOmniSwitch7800BBUS OBJECT-IDENTITY
    STATUS current
    DESCRIPTION
        "OmniSwitch 7800 Series Chassis Management Module BBUS Bridge.
        Model Name: OS7800-CMM BBUS Bridge
        Assembly:   050352-06
        sysObjectID:  1.3.6.1.4.1.6486.800.1.1.2.1.1.4.1.2.2"
    ::= { cmmOmniSwitch7800 2 }




modulesOmniSwitch7000NI OBJECT-IDENTITY
    STATUS current
    DESCRIPTION
        "OmniSwitch 7000 Series Network Interface (NI) Modules."
    ::= { modulesOmniSwitch7000 2 }




niOmniSwitch7000ENI OBJECT-IDENTITY
    STATUS current
    DESCRIPTION
        "OmniSwitch 7000 Series 10/100BaseX Ethernet Network Interface (ENI) Modules."
    ::= { modulesOmniSwitch7000NI 1 }


eniOmniSwitch7000C24 OBJECT-IDENTITY
    STATUS current
    DESCRIPTION
        "OmniSwitch 7000 Series Copper 24-Port 10/100BaseTX Ethernet Network Interface Module.
        Model Name: OS7-ENI-C24
        Assembly:   901765-10
        sysObjectID:  1.3.6.1.4.1.6486.800.1.1.2.1.1.4.2.1.1"
    ::= { niOmniSwitch7000ENI 1 }


eniOmniSwitch7000FM12 OBJECT-IDENTITY
    STATUS current
    DESCRIPTION
        "OmniSwitch 7000 Series Fiber 12-Port 10/100BaseFX Ethernet Network Interface Module.
        Model Name: OS7-ENI-FM12
        Assembly:   901766-10
        sysObjectID:  1.3.6.1.4.1.6486.800.1.1.2.1.1.4.2.1.2"
    ::= { niOmniSwitch7000ENI 2 }

eniOmniSwitch7000PDPS24ENI OBJECT-IDENTITY
    STATUS current
    DESCRIPTION
        "OmniSwitch 7000 Series 24 Port ENI Inline Power Supply.
        Model Name: OS7-PDPS-0900DC
        Assembly:   902066-10
        sysObjectID:  1.3.6.1.4.1.6486.800.1.1.2.1.1.4.2.1.3"
    ::= { niOmniSwitch7000ENI 3 }


niOmniSwitch7000GNI OBJECT-IDENTITY
    STATUS current
    DESCRIPTION
        "OmniSwitch 7000 Series 1000BaseX Ethernet Network Interface (GNI) Modules."
    ::= { modulesOmniSwitch7000NI 2 }



gniOmniSwitch7000U2 OBJECT-IDENTITY
    STATUS current
    DESCRIPTION
        "OmniSwitch 7000 Series Universal 2-Port 1000BaseX Ethernet Network Interface Module.
        Model Name: OS7-GNI-U2
        Assembly:   901759-10
        sysObjectID:  1.3.6.1.4.1.6486.800.1.1.2.1.1.4.2.2.1"
    ::= { niOmniSwitch7000GNI 1 }


gni2OmniSwitch7000C12 OBJECT-IDENTITY
    STATUS current
    DESCRIPTION
        "OmniSwitch 7000 Series Copper 12-Port 10/100BaseTX/1000BaseCX Ethernet Network Interface Module.
        Model Name: OS7-GNI2-C12
        Assembly:   902063-10
        sysObjectID:  1.3.6.1.4.1.6486.800.1.1.2.1.1.4.2.2.2"
    ::= { niOmniSwitch7000GNI 2 }


gni2OmniSwitch7000U12 OBJECT-IDENTITY
    STATUS current
    DESCRIPTION
        "OmniSwitch 7000 Series Universal 12-Port 1000BaseX Ethernet Network Interface Module.
        Model Name: OS7-GNI2-U12
        Assembly:   902064-10
        sysObjectID:  1.3.6.1.4.1.6486.800.1.1.2.1.1.4.2.2.3"
    ::= { niOmniSwitch7000GNI 3 }



niOmniSwitch7000IC OBJECT-IDENTITY
    STATUS current
    DESCRIPTION
        "OmniSwitch 7000 Series Network Interface Module Interface Cards (IC)."
    ::= { modulesOmniSwitch7000NI 3 }



icOmniSwitch7000GIC OBJECT-IDENTITY
    STATUS current
    DESCRIPTION
        "OmniSwitch 7000 Series 1000BaseX Interface Cards (IC)."
    ::= { niOmniSwitch7000IC 1 }


gicOmniSwitch7000LH70 OBJECT-IDENTITY
    STATUS current
    DESCRIPTION
        "OmniSwitch 7000 Series Long Haul 70km Fiber 1000BaseX Interface Card.
        Model Name: GBIC-LH-70
        Assembly:   901953-10
        sysObjectID:  1.3.6.1.4.1.6486.800.1.1.2.1.1.4.3.1.1"
    ::= { icOmniSwitch7000GIC 1 }


gicOmniSwitch7000LX OBJECT-IDENTITY
    STATUS current
    DESCRIPTION
        "OmniSwitch 7000 Series Single Mode Fiber 1000BaseLX Interface Card.
        Model Name: GBIC-LX
        Assembly:   901952-10
        sysObjectID:  1.3.6.1.4.1.6486.800.1.1.2.1.1.4.3.1.2"
    ::= { icOmniSwitch7000GIC 2 }


gicOmniSwitch7000SX OBJECT-IDENTITY
    STATUS current
    DESCRIPTION
        "OmniSwitch 7000 Series Multi Mode Fiber 1000BaseSX Interface Card.
        Model Name: GBIC-SX
        Assembly:   901951-10
        sysObjectID:  1.3.6.1.4.1.6486.800.1.1.2.1.1.4.3.1.3"
    ::= { icOmniSwitch7000GIC 3 }


gicOmniSwitch7000C OBJECT-IDENTITY
    STATUS current
    DESCRIPTION
        "OmniSwitch 7000 Series Copper 1000BaseCX Interface Card.
        Model Name: GBIC-C
        Assembly:   902088-11
        sysObjectID:  1.3.6.1.4.1.6486.800.1.1.2.1.1.4.3.1.4"
    ::= { icOmniSwitch7000GIC 4 }




familyOmniSwitch8000 OBJECT-IDENTITY
    STATUS current
    DESCRIPTION
        "OmniSwitch 8000 Series Product Family."
    ::= { alcatelIND1DevicesMIB 2 }




chassisOmniSwitch8000 OBJECT-IDENTITY
    STATUS current
    DESCRIPTION
        "Branch For OmniSwitch 8000 Series Chassis."
    ::= { familyOmniSwitch8000 1 }


deviceOmniSwitch8800 OBJECT-IDENTITY
    STATUS current
    DESCRIPTION
        "OmniSwitch 8800 18-Slot Chassis.
        Model Name: OS8800
        Assembly:   901977-10
        sysObjectID:  1.3.6.1.4.1.6486.800.1.1.2.1.2.1.1"
    ::= { chassisOmniSwitch8000 1 }




fansOmniSwitch8000 OBJECT-IDENTITY
    STATUS current
    DESCRIPTION
        "Branch For OmniSwitch 8000 Series Fan Trays."
    ::= { familyOmniSwitch8000 2 }


fansOmniSwitch8800CFT OBJECT-IDENTITY
    STATUS current
    DESCRIPTION
        "OmniSwitch 8800 Series Chassis Fan Tray.
        Model Name: OS8800-CFT
        Assembly:   902074-10
        sysObjectID:  1.3.6.1.4.1.6486.800.1.1.2.1.2.2.1"
    ::= { fansOmniSwitch8000 1 }


fansOmniSwitch8800FFT OBJECT-IDENTITY
    STATUS current
    DESCRIPTION
        "OmniSwitch 8800 Series Fabric Fan Tray.
        Model Name: OS8800-FFT
        Assembly:   902075-10
        sysObjectID:  1.3.6.1.4.1.6486.800.1.1.2.1.2.2.2"
    ::= { fansOmniSwitch8000 2 }



powersOmniSwitch8000 OBJECT-IDENTITY
    STATUS current
    DESCRIPTION
        "Branch For OmniSwitch 8000 Series Power Supplies."
    ::= { familyOmniSwitch8000 3 }


powersOmniSwitch8000PS1375AC OBJECT-IDENTITY
    STATUS current
    DESCRIPTION
        "OmniSwitch 8000 Series 1375 Watt A/C Power Supply.
        Model Name: OS8-PS-1375AC
        Assembly:   901978-10
        sysObjectID:  1.3.6.1.4.1.6486.800.1.1.2.1.2.3.1"
    ::= { powersOmniSwitch8000 1 }


powersOmniSwitch8000PS1375DC OBJECT-IDENTITY
    STATUS current
    DESCRIPTION
        "OmniSwitch 8000 Series 1375 Watt D/C Power Supply.
        Model Name: OS8-PS-1375DC
        Assembly:   902054-10
        sysObjectID:  1.3.6.1.4.1.6486.800.1.1.2.1.2.3.2"
    ::= { powersOmniSwitch8000 2 }




modulesOmniSwitch8000 OBJECT-IDENTITY
    STATUS current
    DESCRIPTION
        "Branch For OmniSwitch 8000 Series Modules."
    ::= { familyOmniSwitch8000 4 }




modulesOmniSwitch8000CM OBJECT-IDENTITY
    STATUS current
    DESCRIPTION
        "Branch For OmniSwitch 8000 Series Chassis Management (CM) Modules."
    ::= { modulesOmniSwitch8000 1 }



cmmOmniSwitch8800 OBJECT-IDENTITY
    STATUS current
    DESCRIPTION
        "OmniSwitch 8800 Series Chassis Management Module.
        Model Name: OS8800-CMM
        Assembly:   901980-10
        sysObjectID:  1.3.6.1.4.1.6486.800.1.1.2.1.2.4.1.1"
    ::= { modulesOmniSwitch8000CM 1 }


cmmOmniSwitch8800PROC OBJECT-IDENTITY
    STATUS current
    DESCRIPTION
        "OmniSwitch 8800 Series Chassis Management Module Processor.
        Model Name: OS8800-CMM Processor
        Assembly:   050358-06
        sysObjectID:  1.3.6.1.4.1.6486.800.1.1.2.1.2.4.1.1.1"
    ::= { cmmOmniSwitch8800 1 }


cmmOmniSwitch8800BBUS OBJECT-IDENTITY
    STATUS current
    DESCRIPTION
        "OmniSwitch 8800 Series Chassis Management Module BBUS Bridge.
        Model Name: OS8800-CMM BBUS Bridge
        Assembly:   050386-06
        sysObjectID:  1.3.6.1.4.1.6486.800.1.1.2.1.2.4.1.1.2"
    ::= { cmmOmniSwitch8800 2 }




modulesOmniSwitch8000NI OBJECT-IDENTITY
    STATUS current
    DESCRIPTION
        "OmniSwitch 8000 Series Network Interface (NI) Modules."
    ::= { modulesOmniSwitch8000 2 }




niOmniSwitch8000ENI OBJECT-IDENTITY
    STATUS current
    DESCRIPTION
        "OmniSwitch 8000 Series 10/100BaseX Ethernet Network Interface (ENI) Modules."
    ::= { modulesOmniSwitch8000NI 1 }


eniOmniSwitch8000C24 OBJECT-IDENTITY
    STATUS current
    DESCRIPTION
        "OmniSwitch 8000 Series Copper 24-Port 10/100BaseTX Ethernet Network Interface Module.
        Model Name: OS8-ENI-C24
        Assembly:   902055-10
        sysObjectID:  1.3.6.1.4.1.6486.800.1.1.2.1.2.4.2.1.1"
    ::= { niOmniSwitch8000ENI 1 }




niOmniSwitch8000GNI OBJECT-IDENTITY
    STATUS current
    DESCRIPTION
        "OmniSwitch 8000 Series 1000BaseX Ethernet Network Interface (GNI) Modules."
    ::= { modulesOmniSwitch8000NI 2 }



gniOmniSwitch8000U8 OBJECT-IDENTITY
    STATUS current
    DESCRIPTION
        "OmniSwitch 8000 Series Universal 8-Port 1000BaseX Ethernet Network Interface Module.
        Model Name: OS8-GNI-U8
        Assembly:   901981-10
        sysObjectID:  1.3.6.1.4.1.6486.800.1.1.2.1.2.4.2.2.1"
    ::= { niOmniSwitch8000GNI 1 }


gniOmniSwitch8000C8 OBJECT-IDENTITY
    STATUS current
    DESCRIPTION
        "OmniSwitch 8000 Series Copper 8-Port 1000BaseCX Ethernet Network Interface Module.
        Model Name: OS8-GNI-C8
        Assembly:   902057-10
        sysObjectID:  1.3.6.1.4.1.6486.800.1.1.2.1.2.4.2.2.2"
    ::= { niOmniSwitch8000GNI 2 }


gni2OmniSwitch8000U8 OBJECT-IDENTITY
    STATUS current
    DESCRIPTION
        "OmniSwitch 8000 Series Universal 8-Port 1000BaseX Ethernet Network Interface Module.
        Model Name: OS8-GNI2-U8
        Assembly:   902070-10
        sysObjectID:  1.3.6.1.4.1.6486.800.1.1.2.1.2.4.2.2.3"
    ::= { niOmniSwitch8000GNI 3 }


gni2OmniSwitch8000C24 OBJECT-IDENTITY
    STATUS current
    DESCRIPTION
        "OmniSwitch 8000 Series Copper 24-Port 10/100BaseTX/1000BaseCX Ethernet Network Interface Module.
        Model Name: OS8-GNI2-C24
        Assembly:   902072-10
        sysObjectID:  1.3.6.1.4.1.6486.800.1.1.2.1.2.4.2.2.4"
    ::= { niOmniSwitch8000GNI 4 }


gni2OmniSwitch8000U24 OBJECT-IDENTITY
    STATUS current
    DESCRIPTION
        "OmniSwitch 8000 Series Universal 24-Port 1000BaseX Ethernet Network Interface Module.
        Model Name: OS8-GNI2-U24
        Assembly:   902073-10
        sysObjectID:  1.3.6.1.4.1.6486.800.1.1.2.1.2.4.2.2.5"
    ::= { niOmniSwitch8000GNI 5 }




niOmniSwitch8000G10NI OBJECT-IDENTITY
    STATUS current
    DESCRIPTION
        "OmniSwitch 8000 Series 10-Gigabit Ethernet Network Interface (G10NI) Modules."
    ::= { modulesOmniSwitch8000NI 3 }



g10niOmniSwitch8000U1 OBJECT-IDENTITY
    STATUS current
    DESCRIPTION
        "OmniSwitch 8000 Series Universal 1-Port 10-Gigabit Ethernet Network Interface Module.
        Model Name: OS8-10GNI-U1
        Assembly:   902056-10
        sysObjectID:  1.3.6.1.4.1.6486.800.1.1.2.1.2.4.2.3.1"
    ::= { niOmniSwitch8000G10NI 1 }




niOmniSwitch8000IC OBJECT-IDENTITY
    STATUS current
    DESCRIPTION
        "OmniSwitch 8000 Series Network Interface Module Interface Cards (IC)."
    ::= { modulesOmniSwitch8000NI 4 }



icOmniSwitch8000GIC OBJECT-IDENTITY
    STATUS current
    DESCRIPTION
        "OmniSwitch 8000 Series 1000BaseX Interface Cards (IC)."
    ::= { niOmniSwitch8000IC 1 }


mgicOmniSwitch8000SX OBJECT-IDENTITY
    STATUS current
    DESCRIPTION
        "OmniSwitch 8000 Series Multi Mode Fiber 1000BaseSX Interface Card.
        Model Name: MiniGBIC-SX
        Assembly:   902053-10
        sysObjectID:  1.3.6.1.4.1.6486.800.1.1.2.1.2.4.2.4.1.1"
    ::= { icOmniSwitch8000GIC 1 }


mgicOmniSwitch8000LX OBJECT-IDENTITY
    STATUS current
    DESCRIPTION
        "OmniSwitch 8000 Series Single Mode Fiber 1000BaseLX Interface Card.
        Model Name: MiniGBIC-LX
        Assembly:   902052-10
        sysObjectID:  1.3.6.1.4.1.6486.800.1.1.2.1.2.4.2.4.1.2"
    ::= { icOmniSwitch8000GIC 2 }


mgicOmniSwitch8000LH70 OBJECT-IDENTITY
    STATUS current
    DESCRIPTION
        "OmniSwitch 8000 Series Long Haul 70km Fiber 1000BaseX Interface Card.
        Model Name: MiniGBIC-LH-70
        Assembly:   902051-10
        sysObjectID:  1.3.6.1.4.1.6486.800.1.1.2.1.2.4.2.4.1.3"
    ::= { icOmniSwitch8000GIC 3 }




modulesOmniSwitch8000SF OBJECT-IDENTITY
    STATUS current
    DESCRIPTION
        "Branch For OmniSwitch 8000 Series Switch Fabric (SF) Modules."
    ::= { modulesOmniSwitch8000 3 }


sfOmniSwitch8800SFM OBJECT-IDENTITY
    STATUS current
    DESCRIPTION
        "OmniSwitch 8800 Series Switch Fabric Module.
        Model Name: OS8800-SFM
        Assembly:   901979-10
        sysObjectID:  1.3.6.1.4.1.6486.800.1.1.2.1.2.4.3.1"
    ::= { modulesOmniSwitch8000SF 1 }


familyOmniSwitch6600 OBJECT-IDENTITY
    STATUS current
    DESCRIPTION
        "OmniSwitch 8000 Series Product Family."
    ::= { alcatelIND1DevicesMIB 3 }
    

    
chassisOmniSwitch6600 OBJECT-IDENTITY
    STATUS current
    DESCRIPTION
        "Branch For OmniSwitch 6600 Series Chassis."
    ::= { familyOmniSwitch6600 1 }

deviceOmniSwitch6624 OBJECT-IDENTITY
    STATUS current
    DESCRIPTION
        "OmniSwitch 6624 Stackable Chassis.
        Model Number: 	OSW-6624
        Assembly:   	902083-10
        sysObjectID:  	1.3.6.1.4.1.6486.800.1.1.2.1.3.1.1"
    ::= { chassisOmniSwitch6600 1 }
    
deviceOmniSwitch6648 OBJECT-IDENTITY
    STATUS current
    DESCRIPTION
        "OmniSwitch 6648 Stackable Chassis.
        Model Number: 	OSW-6648
        Assembly:   	902098-10
        sysObjectID:  	1.3.6.1.4.1.6486.800.1.1.2.1.3.1.2"
    ::= { chassisOmniSwitch6600 2 }
    
    
fansOmniSwitch6600 OBJECT-IDENTITY
    STATUS current
    DESCRIPTION
        "Branch For OmniSwitch 6600 Series Fan Trays."
    ::= { familyOmniSwitch6600 2 }
    
powersOmniSwitch6600 OBJECT-IDENTITY
    STATUS current
    DESCRIPTION
        "Branch For OmniSwitch 6600 Series Power Supplies."
    ::= { familyOmniSwitch6600 3 }

powersOmniSwitch6600BSP OBJECT-IDENTITY
    STATUS current
    DESCRIPTION
        "OmniSwitch 6600 Hawk Back Up Power Supply
        Model Number: 	OSW-6600-BPS
        Assembly:   	902087-10
        sysObjectID:  	1.3.6.1.4.1.6486.800.1.1.2.1.3.3.1"
    ::= { powersOmniSwitch6600 1 } 
       
modulesOmniSwitch6600 OBJECT-IDENTITY
    STATUS current
    DESCRIPTION
        "Branch For OmniSwitch 6600 Series Modules."
    ::= { familyOmniSwitch6600 4 }
    
expOmniSwitch6600 OBJECT-IDENTITY
    STATUS current
    DESCRIPTION
        "Branch For OmniSwitch 6600 Expantion Modules."
    ::= { modulesOmniSwitch6600 1 }
    
mgicOmniSwitch6600-2 OBJECT-IDENTITY
    STATUS current
    DESCRIPTION
        "OmniSwitch 6600 - MiniGBIC - Fiber Module
        Model Number: 	OSW-66MiniGBIC2
        Assembly:   	902084-10
        sysObjectID:  	1.3.6.1.4.1.6486.800.1.1.2.1.3.4.1.1"
    ::= { expOmniSwitch6600 1 }
    
gsmOmniSwitch6600-T-2 OBJECT-IDENTITY
    STATUS current
    DESCRIPTION
        "OmniSwitch 6600 -T-2 - Copper Module.
        Model Number: 	OSW-66-GSM-T-2
        Assembly:   	902085-10
        sysObjectID:  	1.3.6.1.4.1.6486.800.1.1.2.1.3.4.1.2"
    ::= { expOmniSwitch6600 2 }

stkOmniSwitch6600-Kit OBJECT-IDENTITY
    STATUS current
    DESCRIPTION
       "OmniSwitch 6600 STK Kit.
        Model Number: 	OSW-66-STK-Kit
        Assembly:   	902086-10
        sysObjectID:  	1.3.6.1.4.1.6486.800.1.1.2.1.3.4.1.3"
    ::= { expOmniSwitch6600 3 }




familyOmniAccess200 OBJECT-IDENTITY
    STATUS current
    DESCRIPTION
        "OmniSwitch 8000 Series Product Family."
    ::= { alcatelIND1DevicesMIB 4 }
    
chassisOmniAccess200 OBJECT-IDENTITY
    STATUS current
    DESCRIPTION
        "Branch For OmniAccess 200 Series Chassis."
    ::= { familyOmniAccess200 1 }

deviceOmniAccess210 OBJECT-IDENTITY
    STATUS current
    DESCRIPTION
        "OmniAccess 210 VPN product Chassis.
        Model Number: 	
        Assembly:   	
        sysObjectID:  	1.3.6.1.4.1.6486.800.1.1.2.1.4.1.1"
    ::= { chassisOmniAccess200 1 }
    
deviceOmniAccess250 OBJECT-IDENTITY
    STATUS current
    DESCRIPTION
        "OmniAccess 250 VPN product Chassis.
        Model Number: 	
        Assembly:   	
        sysObjectID:  	1.3.6.1.4.1.6486.800.1.1.2.1.4.1.2"
    ::= { chassisOmniAccess200 2 }
    
    
fansOmniSwitch200 OBJECT-IDENTITY
    STATUS current
    DESCRIPTION
        "Branch For OmniAccess 200 Series Fan Trays."
    ::= { familyOmniAccess200 2 }
    
powersOmniAccess200 OBJECT-IDENTITY
    STATUS current
    DESCRIPTION
        "Branch For OmniAccess 200 Series Power Supplies."
    ::= { familyOmniAccess200 3 }

modulesOmniAccess200 OBJECT-IDENTITY
    STATUS current
    DESCRIPTION
        "Branch For OmniAccess 200 Series Modules."
    ::= { familyOmniAccess200 4 }

END
