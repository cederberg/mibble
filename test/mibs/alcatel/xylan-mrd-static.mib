--  Copyright (C) 2001 Alcatel Internetworking, Inc., all rights reserved.
--
--           Xylan MRouteD MIB ASN.1 Specification
--
-- File:        xylan-mrd-static.mib
--
-- Purpose:     Specifies Xylan's MIB definitions used only
--		to LOAD/ENABLE the MRouteD Software.
--		(Once MRouteD is loaded/enabled, a fully-fledged
--		"dynamic" mib takes over.)
--
-- Conformance: Created proprietary MIB to address specific needs of Xylan.
--              This MIB does not attempt to conform to any existing Mrouted
--              MIBS.
--
-- Background:  The MIB is proprietary and bears no resemblance no other Mrouted
--              MIBS.
--
--              History
--              =======
--		7/18/01    cpc  Hacked from xylan-mrd.mib
--
--

MRD-MIB DEFINITIONS ::= BEGIN
 
IMPORTS
    OBJECT-TYPE 				FROM RFC-1212
    xylanMrouted				FROM XYLAN-BASE-MIB;

    mrdStaticMIB OBJECT IDENTIFIER ::= { xylanMrouted 1 }

    mrdStaticMIBObjects OBJECT IDENTIFIER ::= { mrdStaticMIB 1 }


--  The General Group ********************************************************

mrdStaticGeneralGroup OBJECT IDENTIFIER ::= { mrdStaticMIBObjects 1 }

mrdStaticEnableDisable  OBJECT-TYPE                           
        SYNTAX        INTEGER { 
		      doEnable(1),
		      doDisable(2) 
		      }
        ACCESS        read-write
        STATUS        mandatory
        DESCRIPTION
            "This flag indicates whether or not mrouted will be enabled or
             disabled."
        ::= { mrdStaticGeneralGroup 5 }

END
