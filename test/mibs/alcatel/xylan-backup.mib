XYLAN-BACKUP-MIB DEFINITIONS ::= BEGIN

     --  RCSID information

     --  $RCSfile: xylan-backup.mib,v $
     --  $Revision: 1.2 $		$State: Exp $
     --  $Date: 1997/09/01 23:47:30 $
     --  $Author: fr $


     --  xylan-backup.mib
     --  Author:  Alan K. Bartky

     --  Revision Hisory:

     --  Revision: 0.01
     --  alan 07/17/97, Initial version 

     --  Alcatel Internetworking, Inc.
     --  26801 W. Agoura Road
     --  Calabasas, CA 91301
     --  (818) 880-3500
     --  support@ind.alcatel.com

     --  This module provides authoritative definitions for Alcatel Internetworking, Inc.
     --  enterprise-specific fr MIB.

     --  This module will be extended, as needed.


     --  Alcatel Internetworking, Inc. reserves the right to make changes in 
     --  specification and other information contained in this document 
     --  without prior notice.  The reader should consult Alcatel Internetworking,
     --  Inc. to determine whether any such changes have been made.

     --  In no event shall Alcatel Internetworking, Inc. be liable for any incidental, 
     --  indirect, special, or consequential damages whatsoever (including 
     --  but not limited to lost profits) arising out of or related to this
     --  document or the information contained in it, even if Alcatel Internetworking,
     --  Inc. has been advised of, known, or should have known, the 
     --  possibility of such damages.
     --  Alcatel Internetworking, Inc. grants vendors, end-users, and other interested
     --  parties a non-exclusive license to use this Specification in connection
     --  with the management of Alcatel Internetworking, Inc. products.

     --  Copyright (C) 1997, Alcatel Internetworking, Inc. All Rights Reserved.
     --  Rev 0.1
     	IMPORTS
		OBJECT-TYPE
			FROM RFC-1212
		DisplayString 
			FROM RFC1213-MIB
                xylanBackupArch
                        FROM XYLAN-BASE-MIB
			;

     -- Textual Conventions


     --
     --                    The MIB groups
     --
     backupxConfigGroup     OBJECT IDENTIFIER ::= { xylanBackupArch 1 }


     --		The Backup Service Configuration Group


         backupxConfigTable   OBJECT-TYPE
	    SYNTAX   SEQUENCE OF BackupxConfigEntry 
            ACCESS   not-accessible
            STATUS   mandatory
            DESCRIPTION
            	"A table of Backup Services configuration information." 
            ::= { backupxConfigGroup 1 }

         backupxConfigEntry   OBJECT-TYPE
            SYNTAX   BackupxConfigEntry
            ACCESS   not-accessible
            STATUS   mandatory
            DESCRIPTION
            	"An entry in the Backup Service Entity Configuration table, 
                 containing information about a backup service." 
            INDEX   { backupxConfigID }
            ::= { backupxConfigTable 1 }

         BackupxConfigEntry ::=
             SEQUENCE {
                 backupxConfigID
                     INTEGER,
                 backupxConfigDescription
                     DisplayString,
	         backupxConfigAdminStatus
                     INTEGER,
	         backupxConfigPrimaryType
                     INTEGER,
                 backupxConfigPrimaryIndex1
                     INTEGER,
                 backupxConfigPrimaryIndex2
                     INTEGER,
                 backupxConfigPrimaryIndex3
                     INTEGER,
	         backupxConfigBackupType
                     INTEGER,
                 backupxConfigBackupIndex1
                     INTEGER,
                 backupxConfigBackupIndex2
                     INTEGER,
                 backupxConfigBackupIndex3
                     INTEGER,
 	         backupxConfigStartupTimeout
                     INTEGER,
 	         backupxConfigActivateTimeout
                     INTEGER,
 	         backupxConfigRestoreTimeout
                     INTEGER
         }

         backupxConfigID OBJECT-TYPE
             SYNTAX   INTEGER
             ACCESS   read-only
             STATUS   mandatory
             DESCRIPTION
                "The Backup Service ID.  This is used as a unique
                 ID to identify a backup service entity."
             ::= { backupxConfigEntry 1 }

         backupxConfigDescription OBJECT-TYPE
             SYNTAX   DisplayString (SIZE (0..31))
             ACCESS   read-write
             STATUS   mandatory
             DESCRIPTION
                "A description for this Backup Service."
             ::= { backupxConfigEntry 2 }

	 backupxConfigAdminStatus OBJECT-TYPE
             SYNTAX   INTEGER {
                      enabled(1),
                      disabled(2),
                      delete(3)
                      }
             ACCESS   read-write
             STATUS   mandatory
             DESCRIPTION
                "This object controls the Administrative Status
                 of this Backup Service.  Enabled will allow the
                 Backup Service to operate.  Disabled will 
                 disable the service without deleting it.
                 Delete will disable the backup and delete
                 the backup service configuration record."
             ::= { backupxConfigEntry 3 }

	 backupxConfigPrimaryType OBJECT-TYPE
             SYNTAX   INTEGER {
                      physicalPort(1),
                      frameRelayPvcDlci(2)
                      }
             ACCESS   read-write
             STATUS   mandatory
             DESCRIPTION
                "This object controls the type of entity to
                 be backed up in case of failure."
             ::= { backupxConfigEntry 4 }

 	 backupxConfigPrimaryIndex1 OBJECT-TYPE
             SYNTAX   INTEGER 
             ACCESS   read-write
             STATUS   mandatory
             DESCRIPTION
                "This object controls the first Index object
                 to use to identify the Primary entity to backup
                 based on type:

                 Physical Port:    slot
                 Frame Relay PVC:  slot"

             ::= { backupxConfigEntry 5 }

 	 backupxConfigPrimaryIndex2 OBJECT-TYPE
             SYNTAX   INTEGER 
             ACCESS   read-write
             STATUS   mandatory
             DESCRIPTION
                "This object controls the first Index object
                 to use to identify the Primary entity to backup
                 based on type:

                 Physical Port:    port
                 Frame Relay PVC:  port"

             ::= { backupxConfigEntry 6 }

 	 backupxConfigPrimaryIndex3 OBJECT-TYPE
             SYNTAX   INTEGER 
             ACCESS   read-write
             STATUS   mandatory
             DESCRIPTION
                "This object controls the first Index object
                 to use to identify the Primary entity to backup 
                 based on type:

                 Physical Port:    0
                 Frame Relay PVC:  DLCI number"

             ::= { backupxConfigEntry 7 }

	 backupxConfigBackupType OBJECT-TYPE
             SYNTAX   INTEGER {
                      pppPeer(1)
                      }
             ACCESS   read-write
             STATUS   mandatory
             DESCRIPTION
                "This object controls the type of entity to
                 use to back up the primary entity in case of failure."
             ::= { backupxConfigEntry 8 }

 	 backupxConfigBackupIndex1 OBJECT-TYPE
             SYNTAX   INTEGER 
             ACCESS   read-write
             STATUS   mandatory
             DESCRIPTION
                "This object controls the first Index object
                 to use to identify the backup entity based on type:

                 PPP Peer:         Peer ID"  
             ::= { backupxConfigEntry 9 }

 	 backupxConfigBackupIndex2 OBJECT-TYPE
             SYNTAX   INTEGER 
             ACCESS   read-write
             STATUS   mandatory
             DESCRIPTION
                "This object controls the second Index object
                 to use to identify the backup entity:

                 This object is currently reserved for possible
                 future use."
             ::= { backupxConfigEntry 10 }

 	 backupxConfigBackupIndex3 OBJECT-TYPE
             SYNTAX   INTEGER 
             ACCESS   read-write
             STATUS   mandatory
             DESCRIPTION
                "This object controls the third Index object
                 to use to identify the backup entity:

                 This object is currently reserved for possible
                 future use."
             ::= { backupxConfigEntry 11 }

 	 backupxConfigStartupTimeout OBJECT-TYPE
             SYNTAX   INTEGER(0..65535) 
             ACCESS   read-write
             STATUS   mandatory
             DESCRIPTION
                "This object controls the time in seconds
                 after system startup to wait for the Primary
                 entity to come up before activating the
                 backup entity."
             ::= { backupxConfigEntry 12 }

 	 backupxConfigActivateTimeout OBJECT-TYPE
             SYNTAX   INTEGER(0..65535) 
             ACCESS   read-write
             STATUS   mandatory
             DESCRIPTION
                "This object controls the time in seconds
                 after the Primary entity enters and stays
                 in a Failed state before activating the
                 backup entity."
             ::= { backupxConfigEntry 13 }

 	 backupxConfigRestoreTimeout OBJECT-TYPE
             SYNTAX   INTEGER(0..65535) 
             ACCESS   read-write
             STATUS   mandatory
             DESCRIPTION
                "This object controls the time in seconds
                 after the Primary entity enters and stays
                 in a Operational state before deactivating the
                 backup entity."
             ::= { backupxConfigEntry 14 }

END
