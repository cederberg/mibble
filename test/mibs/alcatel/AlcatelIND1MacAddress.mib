ALCATEL-IND1-MAC-ADDRESS-MIB DEFINITIONS ::= BEGIN

IMPORTS
	OBJECT-TYPE,
	OBJECT-IDENTITY,
    	NOTIFICATION-TYPE,
	MODULE-IDENTITY  		FROM SNMPv2-SMI	
    	ifIndex                 	FROM IF-MIB
    	MacAddress,
    	RowStatus               	FROM SNMPv2-TC
    	dot1qVlanIndex          	FROM Q-BRIDGE-MIB
	MODULE-COMPLIANCE, 
	OBJECT-GROUP,
	NOTIFICATION-GROUP     	        FROM SNMPv2-CONF
    	softentIND1MacAddress,
    	sourceLearningTraps     	FROM ALCATEL-IND1-BASE;


alcatelIND1MacAddressMIB MODULE-IDENTITY
    LAST-UPDATED "200101301100Z"
    ORGANIZATION "Alcatel Internetworking, Incorporated"
    CONTACT-INFO 
     "Please consult with Customer Service to insure the most appropriate
      version of this document is used with the products in question:
    
                 Alcatel Internetworking, Incorporated
                (Division 1, Formerly XYLAN Corporation)
                        26801 West Agoura Road
                     Agoura Hills, CA  91301-5122
                       United States Of America
    
     Telephone:               North America  +1 800 995 2696
                              Latin America  +1 877 919 9526
                              Europe         +31 23 556 0100
                              Asia           +65 394 7933
                              All Other      +1 818 878 4507
    
     Electronic Mail:         support@ind.alcatel.com
     World Wide Web:          http://www.ind.alcatel.com
     File Transfer Protocol:  ftp://ftp.ind.alcatel.com/pub/products/mibs"
    DESCRIPTION
	"This module describes an authoritative enterprise-specific Simple
        etwork Management Protocol (SNMP) Management Information Base (MIB):
        
        For the Birds Of Prey Product Line, this is the MIB module for 
	address learning mac addresses entity.

        The right to make changes in specification and other information
        contained in this document without prior notice is reserved.

        No liability shall be assumed for any incidental, indirect, special, or
        consequential damages whatsoever arising from or related to this
        document or the information contained herein.
        
        Vendors, end-users, and other interested parties are granted
        non-exclusive license to use this specification in connection with
        management of the products for which it is intended to be used.
        
         Copyright (C) 1995-2002 Alcatel Internetworking, Incorporated
                       ALL RIGHTS RESERVED WORLDWIDE"

    REVISION      "200101301100Z"

    DESCRIPTION
        "The MIB module for Source Learning Mac Address entity."
    ::= { softentIND1MacAddress 1}


-- xxxxxxxxxxxxxxxxxxxxxxxxxxxxxxxxxxxxxxxxxxxxxxxxxxxxxxxxxx
-- Hook into the Alcatel Tree
-- xxxxxxxxxxxxxxxxxxxxxxxxxxxxxxxxxxxxxxxxxxxxxxxxxxxxxxxxxx
    
    alcatelIND1MacAddressMIBObjects OBJECT-IDENTITY
	STATUS  current
	DESCRIPTION
	    "Branch For Source Learning Module MIB Subsystem Managed Objects."
	::= { alcatelIND1MacAddressMIB 1 }

    alcatelIND1MacAddressMIBConformance OBJECT-IDENTITY
	STATUS  current
	DESCRIPTION
	    "Branch for Source Learning Module MIB Subsystem Conformance Information."
	::= { alcatelIND1MacAddressMIB 2 }

    alcatelIND1MacAddressMIBGroups OBJECT-IDENTITY
	STATUS  current
	DESCRIPTION
	    "Branch for Source Learning Module MIB Subsystem Units of Conformance."
	::= { alcatelIND1MacAddressMIBConformance 1 }

    alcatelIND1MacAddressMIBCompliances OBJECT-IDENTITY
	STATUS  current
	DESCRIPTION
	    "Branch for Source Learning Module MIB Subsystem Compliance Statements."
	::= { alcatelIND1MacAddressMIBConformance 2 }


--
-- Source Learning Common Definitions
--



-- Source Learning MAC Address Table
--  The Static Unicast Database for Transparent VLAN Bridges.
--  Similar to the dot1qStaticUnicastTable of 802.1Q,
--  It mainly allows the user to configure static Unicast
--  MAC address.

slMacAddressTable OBJECT-TYPE
    SYNTAX   	SEQUENCE OF SlMacAddressEntry
    MAX-ACCESS  not-accessible
    STATUS  	current
    DESCRIPTION
        "A table contains source addresses which can be configured as 
        permanent (not aged out), delete on reset, delete on timeout
	in the MAC address table, and those dynamic learned addresses 
	which can be viewed and deleted."
    ::= { alcatelIND1MacAddressMIBObjects 1 }

slMacAddressEntry OBJECT-TYPE
    SYNTAX  	SlMacAddressEntry
    MAX-ACCESS  not-accessible
    STATUS  	current
    DESCRIPTION
        "Defninition of the Mac Addresses entries for which the switch
	has information.

	For creation of a Mac Address, the following 6 fields in 
	slMacAddressEntry are required:
		ifIndex
		dot1qVlanIndex
		slMacAddress
		slMacAddressManagement
		slMacAddressDisposition	
		slMacAddressStatus: must be set last
	Dynamic mac addresses can not be created manually.

	For deletion of a Mac Address, the following 4 fields in
	slMacAddressEntry are required:
		ifIndex
		dot1qVlanIndex
		slMacAddress
		slMacAddressStatus: must be set last"
    INDEX   { ifIndex, dot1qVlanIndex, slMacAddress }
    ::= { slMacAddressTable 1 }

SlMacAddressEntry ::=
    SEQUENCE {
	slMacAddress
            MacAddress,
	slMacAddressManagement
	    INTEGER,
	slMacAddressDisposition
	    INTEGER,
        slMacAddressRowStatus
            RowStatus
        }

slMacAddress OBJECT-TYPE
    SYNTAX  	MacAddress
    MAX-ACCESS  read-write
    STATUS  	current
    DESCRIPTION
        "The MAC address for this entry."
    ::= { slMacAddressEntry 1 }


slMacAddressManagement OBJECT-TYPE
    SYNTAX  INTEGER {
		    permanent(1),
		    deleteOnReset(2),
	 	    deleteOnTimeout(3),
		    learned(4)
		    }
    MAX-ACCESS  read-write
    STATUS  current
    DESCRIPTION
	"This object indicates the management of this entry.
		permanent(1) - this entry is currently in use
		    and will remain so after the user removing
		    this entry.
		deleteOnReset(2) - this entry is currently in
		    use and will remain so until the next 
		    reset of the bridge.
		deleteOnTimeout(3) - this entry is currently 
		    in use and will remain so until it is aged
		    out.
		learned(4) - this entry is currently in use 
		    and will remain so until it is aged out."
    DEFVAL     	{ permanent }
    ::= { slMacAddressEntry 2 }    


slMacAddressDisposition OBJECT-TYPE
    SYNTAX  INTEGER {
		    bridging(1),
		    filtering(2)
		    }
    MAX-ACCESS  read-write
    STATUS  current
    DESCRIPTION
	"This object indicates the disposition of the entry.
		bridging(1) - this entry is currently in use
		    for bridging.
		filtering(2) - this entry is currently in use
		    for filtering."
    DEFVAL      { bridging }
    ::= { slMacAddressEntry 3 }


slMacAddressRowStatus OBJECT-TYPE
    SYNTAX  RowStatus
    MAX-ACCESS  read-write
    STATUS  current
    DESCRIPTION
	"Row Status for creating/deleting the mac address."
    ::= { slMacAddressEntry 4 }
	

-- Layer 2 Mac Address Aging Mib Table


slMacAddressAgingTable OBJECT-TYPE
    SYNTAX  SEQUENCE OF SlMacAddressAgingEntry
    MAX-ACCESS  not-accessible
    STATUS  current
    DESCRIPTION
        "Definition of the timeout for those learned mac addresses and 
	configured as deleted_on_timeout addresses."
    ::= { alcatelIND1MacAddressMIBObjects 2 }

slMacAddressAgingEntry OBJECT-TYPE
    SYNTAX  SlMacAddressAgingEntry
    MAX-ACCESS  not-accessible
    STATUS  current
    DESCRIPTION
	"Information about the aging time for some specific vlan.

	For creation of the aging time, If the vlan Id is specified, then
	the aging time value will be applied to those mac addresses in
	that vlan. Otherwise, the aging time will be applied to all of
	the mac addresses throughout the vlans."
    INDEX    { dot1qVlanIndex }
    ::= { slMacAddressAgingTable 1 }

SlMacAddressAgingEntry ::=
    SEQUENCE {
	slMacAgingValue
	     INTEGER,
	slMacAgingRowStatus
	     RowStatus
	     
	}

slMacAgingValue OBJECT-TYPE
    SYNTAX  INTEGER (10..1000000)
    MAX-ACCESS  read-write
    STATUS  current
    DESCRIPTION
	"This object indicates the value of mac address aging time."
    DEFVAL  	{ 300 }
    ::= { slMacAddressAgingEntry 1 }

slMacAgingRowStatus OBJECT-TYPE
    SYNTAX  RowStatus
    MAX-ACCESS  read-write
    STATUS  current
    DESCRIPTION
	"Row Status for creating/deleting the aging time."
    ::= { slMacAddressAgingEntry 2 }


-- layer 2 PesudoCAM Trap elements ***********************

slPCamTrapObj OBJECT IDENTIFIER ::= { alcatelIND1MacAddressMIBObjects 3 }

slPCAMSlotNumber OBJECT-TYPE  
    SYNTAX 	INTEGER (1..16) 
    MAX-ACCESS	accessible-for-notify
    STATUS	current
    DESCRIPTION
    "The slot number of this Coronado."
    ::= { slPCamTrapObj 1 }

slPCAMSliceNumber OBJECT-TYPE
    SYNTAX     	INTEGER (1..4)
    MAX-ACCESS	accessible-for-notify
    STATUS	current
    DESCRIPTION
    "The Slice Number of this Coronado."
    ::= { slPCamTrapObj 2 }

slPCAMStatus OBJECT-TYPE
   SYNTAX	INTEGER {
			lowWaterMark(1),
			highWaterMark(2),
			floodWaterMark(3),
			full(4)
		}
   MAX-ACCESS	accessible-for-notify
   STATUS       current
   DESCRIPTION
   "The layer 2 pesudoCAM status of this Coronado."
   ::= { slPCamTrapObj 3 }


-- Added by S F For multicast VLAN feature *************

	slMacToPortMacTable	OBJECT-TYPE
		SYNTAX	SEQUENCE OF MacToPortMacEntry
		MAX-ACCESS  not-accessible
		STATUS  current
		DESCRIPTION
			"A list of Mac To Port Binding Mac address."
		::= { alcatelIND1MacAddressMIBObjects 4 }

	slMacToPortMacEntry	OBJECT-TYPE
		SYNTAX	MacToPortMacEntry
		MAX-ACCESS  not-accessible
		STATUS  current
		DESCRIPTION
			"Mac To Port Binding Mac address entry."
		INDEX { slMacToPortMacVlanId, slMacToPortMacAddress}
		::= { slMacToPortMacTable 1 }


	MacToPortMacEntry ::= SEQUENCE {
		slMacToPortMacVlanId					INTEGER,
		slMacToPortMacAddress		  MacAddress,
		slMacToPortMacRowStatus	 RowStatus
		}

	slMacToPortMacVlanId		OBJECT-TYPE
		SYNTAX	INTEGER
		MAX-ACCESS  read-write
		STATUS  current
		DESCRIPTION
		"The vlan Id in which the packet with this mac address is flooded"
		::= { slMacToPortMacEntry 1 }


	slMacToPortMacAddress	OBJECT-TYPE
		SYNTAX	MacAddress
		MAX-ACCESS  read-write
		STATUS  current
		DESCRIPTION
		"A Mac address that is associated with the Mac To Port Binding."
		::= { slMacToPortMacEntry 2 }

	slMacToPortMacRowStatus	OBJECT-TYPE
		SYNTAX	RowStatus
		MAX-ACCESS  read-write
		STATUS  current
		DESCRIPTION
		"This indicate whether to add or delete the mac address"
		::= { slMacToPortMacEntry 3 }


-- End section added by SF



-- Layer 2 PesudoCAM Status Trap ***********************

slPCAMStatusTrap NOTIFICATION-TYPE
    OBJECTS	{
		slPCAMSlotNumber,
		slPCAMSliceNumber,
		slPCAMStatus
		}
   STATUS	current
   DESCRIPTION
	"Trap Status of Layer 2 pesudoCAM on this Coronado."
   ::= { sourceLearningTraps 0 1 }


-- xxxxxxxxxxxxxxxxxxxxxxxxxxxxxxxxxxxxxxxxxxxxxxxxxxxxxxxxxx
-- COMPLIANCE
-- xxxxxxxxxxxxxxxxxxxxxxxxxxxxxxxxxxxxxxxxxxxxxxxx

alcatelIND1MacAddressMIBCompliance MODULE-COMPLIANCE
   STATUS    current
   DESCRIPTION
	"Compliance statement for source learning."
   MODULE
	MANDATORY-GROUPS
	{
		slMacAddressGroup,
		slMacAgingGroup,
		slPCamNotificationGroup
	}
   ::= { alcatelIND1MacAddressMIBCompliances 1 }


-- xxxxxxxxxxxxxxxxxxxxxxxxxxxxxxxxxxxxxxxxxxxxxxxxxxxxxxxxxx
-- UNITS OF CONFORMANCE
-- xxxxxxxxxxxxxxxxxxxxxxxxxxxxxxxxxxxxxxxxxxxxxxxxxxxxxxxxxx

slMacAddressGroup OBJECT-GROUP
   OBJECTS
   {
	slMacAddress,
	slMacAddressManagement,
	slMacAddressDisposition,
	slMacAddressRowStatus
   }
   STATUS  current
   DESCRIPTION
	"Collection of objects for management of source learning Mac addresses."
   ::= { alcatelIND1MacAddressMIBGroups 1 }


slMacAgingGroup OBJECT-GROUP
   OBJECTS
   {
	slMacAgingValue,
	slMacAgingRowStatus
   }			
   STATUS  current
   DESCRIPTION
	"Collection of objects for management of source learning Mac addresses aging-time."
   ::= { alcatelIND1MacAddressMIBGroups 2 }

slPCamNotificationGroup NOTIFICATION-GROUP
   NOTIFICATIONS
   {
	slPCAMStatusTrap
   }			
   STATUS  current
   DESCRIPTION
	"Collection of notification of signaling Pesudo CAM event."
   ::= { alcatelIND1MacAddressMIBGroups 3 }

--  END ***********************


END
