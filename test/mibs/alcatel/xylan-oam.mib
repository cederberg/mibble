XYLAN-OAM-MIB DEFINITIONS ::= BEGIN

          IMPORTS
              OBJECT-TYPE
                    FROM RFC-1212
              TRAP-TYPE
                    FROM RFC-1215
              xylanOamArch
                    FROM XYLAN-BASE-MIB;


     xylanOam  OBJECT IDENTIFIER ::=  { xylanOamArch 1 }


          -- This is the Xylan Corporation proprietary MIB module for
          -- configuring OAM F4/F5 processing module.


          -- OAM F4 related Tables.

       
          -- OAM F4 VP configuration table.

          xylanOamF4VPTable OBJECT-TYPE
              SYNTAX  SEQUENCE OF XylanOamF4VPEntry
              ACCESS  not-accessible
              STATUS  mandatory
              DESCRIPTION
                 "OAM F4 VP configuration table."
              ::= { xylanOam 1 }

          xylanOamF4VPEntry OBJECT-TYPE
              SYNTAX  XylanOamF4VPEntry
              ACCESS  not-accessible
              STATUS  mandatory
              DESCRIPTION
                 "An entry in the OAM F4 VP configuration table."
              INDEX   { xylanOamF4VPSlotIndex,
                        xylanOamF4VPPortIndex,
                        xylanOamF4VPVpiIndex }
               ::= { xylanOamF4VPTable 1 }

          XylanOamF4VPEntry ::=
              SEQUENCE {
                   xylanOamF4VPSlotIndex                    INTEGER,
                   xylanOamF4VPPortIndex                    INTEGER,
                   xylanOamF4VPVpiIndex                     INTEGER,
                   xylanOamF4VPAdminEnable                  INTEGER,
                   xylanOamF4VPAisEnable                    INTEGER,
                   xylanOamF4VPRdiEnable                    INTEGER,
                   xylanOamF4VPContCheckEnable              INTEGER,
                   xylanOamF4VPTrapOnAlarmEnable            INTEGER,
                   xylanOamF4VPLoopbackEnable               INTEGER,
                   xylanOamF4VPLoopbackType                 INTEGER,
                   xylanOamF4VPLoopbackStatus               INTEGER,
                   xylanOamF4VPContCheckStatus              INTEGER,
                   xylanOamF4VPAisRxCount                   INTEGER,
                   xylanOamF4VPAisTxCount                   INTEGER,
                   xylanOamF4VPRdiRxCount                   INTEGER,
                   xylanOamF4VPRdiTxCount                   INTEGER,
                   xylanOamF4VPLoopbackRxCount              INTEGER,
                   xylanOamF4VPLoopbackTxCount              INTEGER,
                   xylanOamF4VPContCheckRxCount             INTEGER,
                   xylanOamF4VPContCheckTxCount             INTEGER,
                   xylanOamF4VPLOCCount                     INTEGER,
                   xylanOamF4VPLoopbackSuccessCount         INTEGER,
                   xylanOamF4VPLoopbackFailureCount         INTEGER,
                   xylanOamF4VPSegmentAction                INTEGER,
                   xylanOamF4VPEndtoendAction               INTEGER
               }
              
          xylanOamF4VPSlotIndex OBJECT-TYPE
              SYNTAX  INTEGER (1..9)
              ACCESS  read-only
              STATUS  mandatory
              DESCRIPTION
                 "A unique value which identifies CSM board slot."
              ::= { xylanOamF4VPEntry 1 }

          xylanOamF4VPPortIndex OBJECT-TYPE
              SYNTAX  INTEGER (1..2)
              ACCESS  read-only
              STATUS  mandatory
              DESCRIPTION
                 "A unique value which identifies CSM module port."
              ::= { xylanOamF4VPEntry 2 }

          xylanOamF4VPVpiIndex OBJECT-TYPE
              SYNTAX  INTEGER 
              ACCESS  read-only
              STATUS  mandatory
              DESCRIPTION
                 "A unique value which identifies this VP connection."
              ::= { xylanOamF4VPEntry 3 }

          xylanOamF4VPAdminEnable OBJECT-TYPE
              SYNTAX  INTEGER  {
                         enable(1),
                         disable(2)
                      }
              ACCESS  read-write
              STATUS  mandatory
              DESCRIPTION
                 "A value to indicate whether this VP connection is enabled." 
              ::= { xylanOamF4VPEntry 4 }

          xylanOamF4VPAisEnable OBJECT-TYPE
              SYNTAX  INTEGER  {
                         enable(1),
                         disable(2)
                      }
              ACCESS  read-write
              STATUS  mandatory
              DESCRIPTION
                 "A value to indicate whether AIS transmission is enabled
                 or disabled for this VP connection."
              ::= { xylanOamF4VPEntry 5 }

          xylanOamF4VPRdiEnable OBJECT-TYPE
              SYNTAX  INTEGER  {
                         enable(1),
                         disable(2)
                      }
              ACCESS  read-write
              STATUS  mandatory
              DESCRIPTION
                 "A value to indicate whether RDI transmission is enabled
                 or disabled for this VP connection."
              ::= { xylanOamF4VPEntry 6 }

          xylanOamF4VPContCheckEnable OBJECT-TYPE
              SYNTAX  INTEGER  {
                         enable(1),
                         disable(2)
                      }
              ACCESS  read-write
              STATUS  mandatory
              DESCRIPTION
                 "A value to indicate whether VP Continuity Check is 
                 enabled or disabled for this VP connection."
              ::= { xylanOamF4VPEntry 7 }

          xylanOamF4VPTrapOnAlarmEnable OBJECT-TYPE
              SYNTAX  INTEGER  {
                         enable(1),
                         disable(2)
                      }
              ACCESS  read-write
              STATUS  mandatory
              DESCRIPTION
                 "A value to indicate whether ATM Layer Trap generation 
                 on alarms is enabled or disabled for this VP connection."
              ::= { xylanOamF4VPEntry 8 }

          xylanOamF4VPLoopbackEnable OBJECT-TYPE
              SYNTAX  INTEGER  {
                         enable(1),
                         disable(2)
                      }
              ACCESS  read-write
              STATUS  mandatory
              DESCRIPTION
                 "A value to indicate whether Loopback is enabled
                 or disabled for this VP connection."
              ::= { xylanOamF4VPEntry 9 }

          xylanOamF4VPLoopbackType OBJECT-TYPE
              SYNTAX  INTEGER  {
                         end-to-end(1),
                         access-line(2),
                         inter-domain(3),
                         network-to-endpoint(4),
                         intra-domain(5)
                      }
              ACCESS  read-write
              STATUS  mandatory
              DESCRIPTION
                 "A unique value indicates Loopback Type."
              ::= { xylanOamF4VPEntry 10 }

          xylanOamF4VPLoopbackStatus OBJECT-TYPE
              SYNTAX  INTEGER  {
                         disabled(1),
                         successful(2),
                         unsuccessful(3),
                         responsewaiting(4)
                      }
              ACCESS  read-only
              STATUS  mandatory
              DESCRIPTION
                 "A unique value indicates Loopback Status."
              ::= { xylanOamF4VPEntry 11 }

          xylanOamF4VPContCheckStatus OBJECT-TYPE
              SYNTAX  INTEGER  {
                         ready(1),
                         waitingActivate(2),
                         waitingDeactivate(3),
                         active(4),
                         disabled(5)         
                      }
              ACCESS  read-only
              STATUS  mandatory
              DESCRIPTION
                 "A unique value indicates VP Continuity Check Status."
              ::= { xylanOamF4VPEntry 12 }

          xylanOamF4VPAisRxCount OBJECT-TYPE
              SYNTAX  INTEGER 
              ACCESS  read-only
              STATUS  mandatory
              DESCRIPTION
                 "A unique value indicates number of received AIS cells
                 on this VP connection."
              ::= { xylanOamF4VPEntry 13 }

          xylanOamF4VPAisTxCount OBJECT-TYPE
              SYNTAX  INTEGER 
              ACCESS  read-only
              STATUS  mandatory
              DESCRIPTION
                 "A unique value indicates number of transmitted AIS cells
                 on this VP connection."
              ::= { xylanOamF4VPEntry 14 }

          xylanOamF4VPRdiRxCount OBJECT-TYPE
              SYNTAX  INTEGER 
              ACCESS  read-only
              STATUS  mandatory
              DESCRIPTION
                 "A unique value indicates number of received RDI cells
                 on this VP connection."
              ::= { xylanOamF4VPEntry 15 }

          xylanOamF4VPRdiTxCount OBJECT-TYPE
              SYNTAX  INTEGER 
              ACCESS  read-only
              STATUS  mandatory
              DESCRIPTION
                 "A unique value indicates number of transmitted RDI cells
                 on this VP connection."
              ::= { xylanOamF4VPEntry 16 }

          xylanOamF4VPLoopbackRxCount OBJECT-TYPE
              SYNTAX  INTEGER 
              ACCESS  read-only
              STATUS  mandatory
              DESCRIPTION
                 "A unique value indicates number of received Loopback cells
                 on this VP connection."
              ::= { xylanOamF4VPEntry 17 }

          xylanOamF4VPLoopbackTxCount OBJECT-TYPE
              SYNTAX  INTEGER 
              ACCESS  read-only
              STATUS  mandatory
              DESCRIPTION
                 "A unique value indicates number of transmitted Loopback 
                 cells on this VP connection."
              ::= { xylanOamF4VPEntry 18 }

          xylanOamF4VPContCheckRxCount OBJECT-TYPE
              SYNTAX  INTEGER 
              ACCESS  read-only
              STATUS  mandatory
              DESCRIPTION
                 "A unique value indicates number of received 
                 Continuity Check cells on this VP connection."
              ::= { xylanOamF4VPEntry 19 }

          xylanOamF4VPContCheckTxCount OBJECT-TYPE
              SYNTAX  INTEGER 
              ACCESS  read-only
              STATUS  mandatory
              DESCRIPTION
                 "A unique value indicates number of received 
                 Continuity Check cells on this VP connection."
              ::= { xylanOamF4VPEntry 20 }

          xylanOamF4VPLOCCount OBJECT-TYPE
              SYNTAX  INTEGER 
              ACCESS  read-only
              STATUS  mandatory
              DESCRIPTION
                 "A unique value indicates number of Loss of Continuity 
                 on this VP connection."
              ::= { xylanOamF4VPEntry 21 }

          xylanOamF4VPLoopbackSuccessCount OBJECT-TYPE
              SYNTAX  INTEGER 
              ACCESS  read-only
              STATUS  mandatory
              DESCRIPTION
                 "A unique value indicates number of successful Loopbacks 
                 on this VP connection."
              ::= { xylanOamF4VPEntry 22 }

          xylanOamF4VPLoopbackFailureCount OBJECT-TYPE
              SYNTAX  INTEGER 
              ACCESS  read-only
              STATUS  mandatory
              DESCRIPTION
                 "A unique value indicates number of unsuccessful Loopbacks 
                 on this VP connection."
              ::= { xylanOamF4VPEntry 23 }

          xylanOamF4VPSegmentAction OBJECT-TYPE
              SYNTAX  INTEGER  {
                         none(1),
                         copy(2),
                         extract(3)
                      }
              ACCESS  read-write
              STATUS  mandatory
              DESCRIPTION
                 "A unique value indicates the configuration on this
                 VP connection."
              ::= { xylanOamF4VPEntry 24 }

          xylanOamF4VPEndtoendAction OBJECT-TYPE
              SYNTAX  INTEGER  {
                         none(1),
                         copy(2),
                         extract(3)
                      }
              ACCESS  read-write
              STATUS  mandatory
              DESCRIPTION
                 "A unique value indicates the configuration on this
                 VP connection."
              ::= { xylanOamF4VPEntry 25 }

          

          -- OAM F5 related Tables.


          -- OAM F5 VC connection  configuration table.

          xylanOamF5VCTable OBJECT-TYPE
              SYNTAX  SEQUENCE OF XylanOamF5VCEntry
              ACCESS  not-accessible
              STATUS  mandatory
              DESCRIPTION
                 "OAM F4 VC connection configuration table."
              ::= { xylanOam 2 }

          xylanOamTraps      OBJECT IDENTIFIER ::= { xylanOam 3 }

          xylanOamF5VCEntry OBJECT-TYPE
              SYNTAX  XylanOamF5VCEntry
              ACCESS  not-accessible
              STATUS  mandatory
              DESCRIPTION
                 "An entry in the OAM F5 VC connection  configuration
                 table."
              INDEX   { xylanOamF5VCSlotIndex,
                        xylanOamF5VCPortIndex,
                        xylanOamF5VCVpiIndex,
                        xylanOamF5VCVciIndex }
               ::= { xylanOamF5VCTable 1 }

          XylanOamF5VCEntry ::=
              SEQUENCE {
                   xylanOamF5VCSlotIndex                    INTEGER,
                   xylanOamF5VCPortIndex                    INTEGER,
                   xylanOamF5VCVpiIndex                     INTEGER,
                   xylanOamF5VCVciIndex                     INTEGER,
                   xylanOamF5VCAdminEnable                  INTEGER,
                   xylanOamF5VCAisEnable                    INTEGER,
                   xylanOamF5VCRdiEnable                    INTEGER,
                   xylanOamF5VCContCheckEnable              INTEGER,
                   xylanOamF5VCTrapOnAlarmEnable            INTEGER,
                   xylanOamF5VCLoopbackEnable               INTEGER,
                   xylanOamF5VCLoopbackType                 INTEGER,
                   xylanOamF5VCLoopbackStatus               INTEGER,
                   xylanOamF5VCContCheckStatus              INTEGER,
                   xylanOamF5VCAisRxCount                   INTEGER,
                   xylanOamF5VCAisTxCount                   INTEGER,
                   xylanOamF5VCRdiRxCount                   INTEGER,
                   xylanOamF5VCRdiTxCount                   INTEGER,
                   xylanOamF5VCLoopbackRxCount              INTEGER,
                   xylanOamF5VCLoopbackTxCount              INTEGER,
                   xylanOamF5VCContCheckRxCount             INTEGER,
                   xylanOamF5VCContCheckTxCount             INTEGER,
                   xylanOamF5VCLOCCount                     INTEGER,
                   xylanOamF5VCLoopbackSuccessCount         INTEGER,
                   xylanOamF5VCLoopbackFailureCount         INTEGER,
                   xylanOamF5VCSegmentAction                INTEGER,
                   xylanOamF5VCEndtoendAction               INTEGER
               }
              
          xylanOamF5VCSlotIndex OBJECT-TYPE
              SYNTAX  INTEGER (1..9)
              ACCESS  read-only
              STATUS  mandatory
              DESCRIPTION
                 "A unique value which identifies CSM board slot."
              ::= { xylanOamF5VCEntry 1 }

          xylanOamF5VCPortIndex OBJECT-TYPE
              SYNTAX  INTEGER (1..2)
              ACCESS  read-only
              STATUS  mandatory
              DESCRIPTION
                 "A unique value which identifies CSM module port."
              ::= { xylanOamF5VCEntry 2 }

           xylanOamF5VCVpiIndex OBJECT-TYPE
              SYNTAX  INTEGER 
              ACCESS  read-only
              STATUS  mandatory
              DESCRIPTION
                 "A unique value which identifies this VC connection."
              ::= { xylanOamF5VCEntry 3 }

          xylanOamF5VCVciIndex OBJECT-TYPE
              SYNTAX  INTEGER 
              ACCESS  read-only
              STATUS  mandatory
              DESCRIPTION
                 "A unique value which identifies this VC connection."
              ::= { xylanOamF5VCEntry 4 }

          xylanOamF5VCAdminEnable OBJECT-TYPE
              SYNTAX  INTEGER  {
                         enable(1),
                         disable(2)
                      }
              ACCESS  read-write
              STATUS  mandatory
              DESCRIPTION
                 "A value to indicate whether this VC connection is enabled."
              ::= { xylanOamF5VCEntry 5 }

          xylanOamF5VCAisEnable OBJECT-TYPE
              SYNTAX  INTEGER  {
                         enable(1),
                         disable(2)
                      }
              ACCESS  read-write
              STATUS  mandatory
              DESCRIPTION
                 "A value to indicate whether AIS tranmission is enabled
                 or disabled for this VC connection."
              ::= { xylanOamF5VCEntry 6 }

          xylanOamF5VCRdiEnable OBJECT-TYPE
              SYNTAX  INTEGER  {
                         enable(1),
                         disable(2)
                      }
              ACCESS  read-write
              STATUS  mandatory
              DESCRIPTION
                 "A value to indicate whether RDI transmission is enabled
                 or disabled for this VC connection."
              ::= { xylanOamF5VCEntry 7 }

          xylanOamF5VCContCheckEnable OBJECT-TYPE
              SYNTAX  INTEGER  {
                         enable(1),
                         disable(2)
                      }
              ACCESS  read-write
              STATUS  mandatory
              DESCRIPTION
                 "A value to indicate whether VCC Continuity Check is enabled
                 or disabled for this VC connection."
              ::= { xylanOamF5VCEntry 8 }

          xylanOamF5VCTrapOnAlarmEnable OBJECT-TYPE
              SYNTAX  INTEGER  {
                         enable(1),
                         disable(2)
                      }
              ACCESS  read-write
              STATUS  mandatory
              DESCRIPTION
                 "A value to indicate whether ATM Layer trap generation 
                 on alarms is enabled or disabled for this VC connection."
              ::= { xylanOamF5VCEntry 9 }

          xylanOamF5VCLoopbackEnable OBJECT-TYPE
              SYNTAX  INTEGER  {
                         enable(1),
                         disable(2)
                      }
              ACCESS  read-write
              STATUS  mandatory
              DESCRIPTION
                 "A value to indicate whether Loopback is enabled
                 or disabled for this VC connection."
              ::= { xylanOamF5VCEntry 10 }

          xylanOamF5VCLoopbackType OBJECT-TYPE
              SYNTAX  INTEGER  {
                         end-to-end(1),
                         access-line(2),
                         inter-domain(3),
                         network-to-endpoint(4),
                         intra-domain(5)
                      }
              ACCESS  read-write
              STATUS  mandatory
              DESCRIPTION
                 "A unique value indicates Loopback Type." 
              ::= { xylanOamF5VCEntry 11 }

          xylanOamF5VCLoopbackStatus OBJECT-TYPE
              SYNTAX  INTEGER  {
                         disabled(1),
                         successful(2),
                         unsuccessful(3),
                         responsewaiting(4)
                      }
              ACCESS  read-only
              STATUS  mandatory
              DESCRIPTION
                 "A unique value indicates Loopback Status." 
              ::= { xylanOamF5VCEntry 12 }

          xylanOamF5VCContCheckStatus OBJECT-TYPE
              SYNTAX  INTEGER  {
                         ready(1),
                         waitingActivate(2),
                         waitingDeactivate(3),
                         active(4),
                         disabled(5)         
                      }
              ACCESS  read-only
              STATUS  mandatory
              DESCRIPTION
                 "A unique value indicates VCC Continuity Check Status."
              ::= { xylanOamF5VCEntry 13 }

          xylanOamF5VCAisRxCount OBJECT-TYPE
              SYNTAX  INTEGER 
              ACCESS  read-only
              STATUS  mandatory
              DESCRIPTION
                 "A unique value indicates number of received AIS cells
                 on this VC connection."
              ::= { xylanOamF5VCEntry 14 }

          xylanOamF5VCAisTxCount OBJECT-TYPE
              SYNTAX  INTEGER 
              ACCESS  read-only
              STATUS  mandatory
              DESCRIPTION
                 "A unique value indicates number of transmitted AIS cells
                 on this VC connection."
              ::= { xylanOamF5VCEntry 15 }

          xylanOamF5VCRdiRxCount OBJECT-TYPE
              SYNTAX  INTEGER 
              ACCESS  read-only
              STATUS  mandatory
              DESCRIPTION
                 "A unique value indicates number of received RDI cells
                 on this VC connection."
              ::= { xylanOamF5VCEntry 16 }

          xylanOamF5VCRdiTxCount OBJECT-TYPE
              SYNTAX  INTEGER 
              ACCESS  read-only
              STATUS  mandatory
              DESCRIPTION
                 "A unique value indicates number of transmitted RDI cells
                 on this VC connection."
              ::= { xylanOamF5VCEntry 17 }

          xylanOamF5VCLoopbackRxCount OBJECT-TYPE
              SYNTAX  INTEGER 
              ACCESS  read-only
              STATUS  mandatory
              DESCRIPTION
                 "A unique value indicates number of received Loopback
                 cells on this VC connection."
              ::= { xylanOamF5VCEntry 18 }

          xylanOamF5VCLoopbackTxCount OBJECT-TYPE
              SYNTAX  INTEGER 
              ACCESS  read-only
              STATUS  mandatory
              DESCRIPTION
                 "A unique value indicates number of transmitted Loopback
                 cells on this VC connection."
              ::= { xylanOamF5VCEntry 19 }

          xylanOamF5VCContCheckRxCount OBJECT-TYPE
              SYNTAX  INTEGER 
              ACCESS  read-only
              STATUS  mandatory
              DESCRIPTION
                 "A unique value indicates number of received VCC 
                 Continuity Check cells on this VC connection."
              ::= { xylanOamF5VCEntry 20 }

          xylanOamF5VCContCheckTxCount OBJECT-TYPE
              SYNTAX  INTEGER 
              ACCESS  read-only
              STATUS  mandatory
              DESCRIPTION
                 "A unique value indicates number of transmitted VCC 
                 Continuity Check cells on this VC connection."
              ::= { xylanOamF5VCEntry 21 }

          xylanOamF5VCLOCCount OBJECT-TYPE
              SYNTAX  INTEGER
              ACCESS  read-only
              STATUS  mandatory
              DESCRIPTION
                 "A unique value indicates number of Loss of Continuity 
                 on this VC connection."
              ::= { xylanOamF5VCEntry 22 }

          xylanOamF5VCLoopbackSuccessCount OBJECT-TYPE
              SYNTAX  INTEGER 
              ACCESS  read-only
              STATUS  mandatory
              DESCRIPTION
                 "A unique value indicates number of successful loopbacks
                 on this VC connection."
              ::= { xylanOamF5VCEntry 23 }

          xylanOamF5VCLoopbackFailureCount OBJECT-TYPE
              SYNTAX  INTEGER 
              ACCESS  read-only
              STATUS  mandatory
              DESCRIPTION
                 "A unique value indicates number of unsuccessful loopbacks
                 on this VC connection."
              ::= { xylanOamF5VCEntry 24 }

          xylanOamF5VCSegmentAction OBJECT-TYPE
              SYNTAX  INTEGER  {
                         none(1),
                         copy(2),
                         extract(3)
                      }
              ACCESS  read-write
              STATUS  mandatory
              DESCRIPTION
                 "A unique value indicates the F5 segment configuration on
                 this VC connection."
              ::= { xylanOamF5VCEntry 25 }
              

          xylanOamF5VCEndtoendAction OBJECT-TYPE
              SYNTAX  INTEGER  {
                         none(1),
                         copy(2),
                         extract(3)
                      }
              ACCESS  read-write
              STATUS  mandatory
              DESCRIPTION
                 "A unique value indicates the F5 Endpoint configuration on
                 this VC connection."
              ::= { xylanOamF5VCEntry 26 }


          -- Traps
          --   The section describes the traps defined for F4/F5 OAM

          xylanOamTrapVCAIS  TRAP-TYPE
          ENTERPRISE    xylanOamTraps
          VARIABLES     {
                             xylanOamF5VCSlotIndex,
                             xylanOamF5VCPortIndex,
                             xylanOamF5VCVpiIndex,
                             xylanOamF5VCVciIndex
                        }
          DESCRIPTION 
              "This trap signifies that the specified connection is in VC-AIS 
               state."
          ::= 1

          xylanOamTrapVCRDI  TRAP-TYPE
          ENTERPRISE    xylanOamTraps
          VARIABLES     {
                             xylanOamF5VCSlotIndex,
                             xylanOamF5VCPortIndex,
                             xylanOamF5VCVpiIndex,
                             xylanOamF5VCVciIndex
                        }
          DESCRIPTION 
              "This trap signifies that the specified connection is in VC-RDI 
               state."
          ::= 2

          xylanOamTrapVCLOC  TRAP-TYPE
          ENTERPRISE    xylanOamTraps
          VARIABLES     {
                             xylanOamF5VCSlotIndex,
                             xylanOamF5VCPortIndex,
                             xylanOamF5VCVpiIndex,
                             xylanOamF5VCVciIndex
                        }
          DESCRIPTION 
              "This trap signifies that the specified connection is in VC-LOC 
               state."
          ::= 3

          xylanOamTrapVCUnsuccessLoop  TRAP-TYPE
          ENTERPRISE    xylanOamTraps
          VARIABLES     {
                             xylanOamF5VCSlotIndex,
                             xylanOamF5VCPortIndex,
                             xylanOamF5VCVpiIndex,
                             xylanOamF5VCVciIndex
                        }
          DESCRIPTION
              "This trap signifies that the specified connection is unsuccessful 
               Loopback state."
          ::= 4

          xylanOamTrapVPAIS  TRAP-TYPE
          ENTERPRISE    xylanOamTraps
          VARIABLES     {
                             xylanOamF4VPSlotIndex,
                             xylanOamF4VPPortIndex,
                             xylanOamF4VPVpiIndex
                        }
          DESCRIPTION  
              "This trap signifies that the specified VP connection is in VP-AIS 
               state."
          ::= 5

          xylanOamTrapVPRDI  TRAP-TYPE
          ENTERPRISE    xylanOamTraps
          VARIABLES     {
                             xylanOamF4VPSlotIndex,
                             xylanOamF4VPPortIndex,
                             xylanOamF4VPVpiIndex
                        }
          DESCRIPTION 
              "This trap signifies that the specified VP connection is in VP-RDI 
               state."
          ::= 6

          xylanOamTrapVPLOC  TRAP-TYPE
          ENTERPRISE    xylanOamTraps
          VARIABLES     {
                             xylanOamF4VPSlotIndex,
                             xylanOamF4VPPortIndex,
                             xylanOamF4VPVpiIndex
                        }
          DESCRIPTION 
              "This trap signifies that the specified VP connection is in VP-LOC 
               state."
          ::= 7

          xylanOamTrapVPUnsuccessLoop  TRAP-TYPE
          ENTERPRISE    xylanOamTraps
          VARIABLES     {
                             xylanOamF4VPSlotIndex,
                             xylanOamF4VPPortIndex,
                             xylanOamF4VPVpiIndex
                        }
          DESCRIPTION 
              "This trap signifies that the specified VP connection is in  
               Unsuccessful loopback state."
          ::= 8

          END
