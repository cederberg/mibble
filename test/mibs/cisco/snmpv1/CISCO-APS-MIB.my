-- MIB file created 19-Jun-2001 15:12:02, by
--   SMICng version 2.2.11-beta(PRO)(Solaris), January 20, 2001. Enterprise key cisco.com

CISCO-APS-MIB DEFINITIONS ::= BEGIN

-- From file: "CISCO-APS-MIB.my"
-- Compile options "4 7 F H N W 03 06 0B 0G 0N 0T"

IMPORTS
    RowStatus, TimeStamp
            FROM SNMPv2-TC-v1
    SnmpAdminString
            FROM SNMP-FRAMEWORK-MIB
    InterfaceIndex
            FROM IF-MIB
    ciscoExperiment
            FROM CISCO-SMI
    Counter, Gauge
            FROM RFC1155-SMI
    OBJECT-TYPE
            FROM RFC-1212
    TRAP-TYPE
            FROM RFC-1215;

cApsMIB OBJECT IDENTIFIER ::= { ciscoExperiment 71 }
-- MODULE-IDENTITY
--  LastUpdated
--    200104290000Z
--  OrgName
--    Cisco Systems, Inc.
--  ContactInfo
--    Cisco Systems, Inc.
--     Customer Service
--     Postal: 170 W. Tasman Drive
--             San Jose, CA  95134-1706
--             USA
--     Tel: +1 800 553-NETS
--     Email: optmgmt-dev@cisco.com
--  Descr
--    This management information module supports the configuration 
--     and management of SONET linear APS groups. The definitions and 
--     descriptions used in this mib have been derived from 
--     Synchronous Optical Network (SONET) Transport Systems: Common 
--     Generic Criteria, GR-253-CORE Revision 2, January 1999, 
--     section 5.3. The MIB is also consistent with the Multiplex 
--     Section Protection (MSP) protocol as specified in ITU-T 
--     Recommendation G.783, Characteristics of synchronous digital 
--     hierarchy (SDH) equipment function blocks, Annex A and B.
--    
--     This MIB was extracted from internet draft
--     draft-ietf-atommib-sonetaps-mib-04.txt for SONET Linear APS 
--     architectures, by J. Johnson, M. Thatcher, and J. Kuhfeld.
--     The objects modified in this MIB implementation from that in
--     the draft are cApsConfigCreationTime and 
--     cApsChanStatusLastSwitchover. They are defined as TimeTicks in
--     the draft and have been changed to TimeStamp in this MIB.
--  RevDate
--    200104290000Z
--  RevDescr
--    A draft version of the APS MIB.

cApsMIBObjects  OBJECT IDENTIFIER ::= { cApsMIB 1 }
cApsMIBNotifications OBJECT IDENTIFIER ::= { cApsMIB 2 }
cApsMIBConformance OBJECT IDENTIFIER ::= { cApsMIB 3 }
cApsConfig      OBJECT IDENTIFIER ::= { cApsMIBObjects 1 }
cApsMap         OBJECT IDENTIFIER ::= { cApsMIBObjects 3 }
cApsNotificationsPrefix OBJECT IDENTIFIER ::= { cApsMIBNotifications 0 }
cApsGroups      OBJECT IDENTIFIER ::= { cApsMIBConformance 1 }
cApsCompliances OBJECT IDENTIFIER ::= { cApsMIBConformance 2 }

CApsK1K2 ::= OCTET STRING(SIZE(2))
-- TEXTUAL-CONVENTION
--  Status
--    mandatory
--  Descr
--    This Textual Convention describes an object that stores
--     a SONET K1 and K2 byte APS protocol field.
--    
--     K1 is located in the first octet, K2 is located in
--     the second octet. Bits are numbered from left to right.
--    
--     Bits 1-4 of the K1 byte indicate a request.
--    
--     1111  Lockout of Protection
--     1110  Forced Switch
--     1101  SF - High Priority
--     1100  SF - Low Priority
--     1011  SD - High Priority
--     1010  SD - Low Priority
--     1001  not used
--     1000  Manual Switch
--     0111  not used
--     0110  Wait-to-Restore
--     0101  not used
--     0100  Exercise
--     0011  not used
--     0010  Reverse Request
--     0001  Do Not Revert
--     0000  No Request
--    
--     Bits 5-8 of the K1 byte indicate the channel associated with the
--     request defined in bits 1-4.
--    
--     0000 is the Null channel.
--    
--     1-14 are working channels.
--     15   is the extra traffic channel
--    
--     Bits 1-4 of the K2 byte indicate a channel. The channel is
--     defined with the same syntax as K1 Bits 5-8.
--    
--    
--     Bit 5 of the K2 byte indicates the
--     architecture.
--    
--     0 if the architecture is 1+1
--     1 if the architecture is 1:n
--    
--     Bits 6-8 of the K2 byte indicates the
--     mode.
--    
--     000 - 011 are reserved for future use
--    
--     100  indicates the mode is unidirectional
--     101  indicates the mode is bidirectional
--    
--     110  RDI-L
--    
--     111  AIS-L
--  Refer
--    Bellcore (Telcordia Technologies) GR-253-CORE, Issue 2,
--     Revision 2 (January 1999), 5.3.5.

CApsSwitchCommand ::= INTEGER {
        noCmd(1),
        clear(2),
        lockoutOfProtection(3),
        forcedSwitchWorkToProtect(4),
        forcedSwitchProtectToWork(5),
        manualSwitchWorkToProtect(6),
        manualSwitchProtectToWork(7),
        exercise(8)
        }
-- TEXTUAL-CONVENTION
--  Status
--    mandatory
--  Descr
--    An APS switch command allows a user to perform protection
--     switch actions.
--    
--     The Switch command values are:
--    
--     noCmd
--    
--     This value should be returned by a read request when no switch
--     command has been written to the object in question since
--     initialization. This value may not be used in a write operation.
--    
--     clear
--    
--     Clears all of the switch commands listed below for the specified
--     channel.
--    
--     lockoutOfProtection
--    
--     Prevents any of the working channels from switching to the 
--     protection line. The specified channel should be the 
--     protection channel.
--    
--     forcedSwitchWorkToProtect
--    
--     Switches the specified working channel to the protection line.
--    
--     forcedSwitchProtectToWork
--    
--     Switches the working channel back from the protection
--     line to the working line. The specified channel should be
--     the protection channel.
--    
--     manualSwitchWorkToProtect
--    
--     Switches the specified working channel to the protection line.
--    
--     manualSwitchProtectToWork
--    
--     Switches the working channel back from the protection
--     line to the working line. The specified channel should be
--     the protection channel.
--    
--     exercise
--    
--     Exercises the protocol for a protection switch of the specified
--     channel by issuing an Exercise request for that channel and
--     checking the response on the APS channel.

CApsControlCommand ::= INTEGER {
        noCmd(1),
        lockoutWorkingChannel(2),
        clearLockoutWorkingChannel(3)
        }
-- TEXTUAL-CONVENTION
--  Status
--    mandatory
--  Descr
--    An APS control command applies only to LTE that support the
--     1:n architecture and performs the following actions.
--    
--    
--     The Control command values are:
--    
--     noCmd
--    
--     This value should be returned by a read request when no control
--     command has been written to the object in question since
--     initialization. This value may not be used in a write operation.
--    
--     lockoutWorkingChannel
--    
--     Prevents the specified working channel from switching to the 
--     protection line.
--    
--     clearLockoutWorkingChannel
--    
--     Clears the lockout a working channel command for the channel 
--     specified.

cApsConfigGroups OBJECT-TYPE
    SYNTAX Gauge
    ACCESS read-only
    STATUS mandatory
    DESCRIPTION
        "The count of APS groups. This count includes all rows in
         cApsConfigTable."
    ::= { cApsConfig 1 }

cApsConfigTable OBJECT-TYPE
    SYNTAX SEQUENCE OF CApsConfigEntry
    ACCESS not-accessible
    STATUS mandatory
    DESCRIPTION
        "This table lists the APS groups that have been configured
         on the system."
    ::= { cApsConfig 2 }

cApsConfigEntry OBJECT-TYPE
    SYNTAX CApsConfigEntry
    ACCESS not-accessible
    STATUS mandatory
    DESCRIPTION
        "A conceptual row in the cApsConfigTable."
    INDEX { --?? IMPLIED may cause problems
            IMPLIED cApsConfigName }
    ::= { cApsConfigTable 1 }

CApsConfigEntry ::= SEQUENCE {
    cApsConfigName SnmpAdminString,
    cApsConfigRowStatus RowStatus,
    cApsConfigMode INTEGER,
    cApsConfigRevert INTEGER,
    cApsConfigDirection INTEGER,
    cApsConfigExtraTraffic INTEGER,
    cApsConfigSdBerThreshold INTEGER,
    cApsConfigSfBerThreshold INTEGER,
    cApsConfigWaitToRestore INTEGER,
    cApsConfigCreationTime TimeStamp
    }

cApsConfigName OBJECT-TYPE
    SYNTAX SnmpAdminString(SIZE(1..32))
--    Rsyntax OCTET STRING(SIZE(1..32))
    ACCESS not-accessible
    STATUS mandatory
    DESCRIPTION
        "A textual name for the APS group."
    ::= { cApsConfigEntry 1 }

cApsConfigRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this APS group entry.
        
         An entry may not exist in the active state unless all
         objects in the entry have an appropriate value. Also,
         all associated cApsChanConfigEntry rows must represent
         a set of consecutive channel numbers beginning with
         0 or 1, depending on the selected architecture.
        
         When set to notInService changes may be made to 
         cApsConfigMode, cApsConfigRevert, cApsConfigDirection, 
         cApsConfigExtraTraffic, cApsConfigSdBerThreshold, 
         cApsConfigSfBerThreshold, and cApsConfigWaitToRestore. 
         Also, associated cApsChanConfigTable objects may be added, 
         deleted and modified."
    ::= { cApsConfigEntry 2 }

cApsConfigMode OBJECT-TYPE
    SYNTAX INTEGER {
        onePlusOne(1),
        oneToN(2),
        onePlusOneCompatible(3),
        onePlusOneOptimized(4)
        }
    ACCESS read-write
    STATUS mandatory
    DESCRIPTION
        "The architecture of the APS group.
        
         onePlusOne
        
         The 1+1 architecture permanently bridges the working
         line to the protection line.
        
         oneToN
        
         The 1:n architecture allows one protection channel to
         protect up to n working channels. When a fault is detected
         on one of the n working channels that channel is bridged
         over the protection channel.
        
         onePlusOneCompatible
        
         This refers to 1 + 1 bidirectional switching compatible with
         1:n bidirectional switching as specified in ITU-T
         Recommendation G.783 (04/97) section A.3.4.1. Since this
         mode necessitates bidirectional switching, 
         cApsConfigDirection must be set to bidirectional whenever 
         onePlusOneCompatible is set.
        
         onePlusOneOptimized
        
         This refers to 1 + 1 bidirectional switching optimized
         for a network using predominantly 1 + 1 bidirectional
         switching as specified in ITU-T Recommendation G.783 (04/97)
         section B.1. Since this mode necessitates bidirectional
         switching, cApsConfigDirection must be set to bidirectional
         whenever onePlusOneOptimized is set.
        
         This object may not be modified if the associated
         cApsConfigRowStatus object is equal to active(1)."
    DEFVAL { onePlusOne }
    ::= { cApsConfigEntry 3 }

cApsConfigRevert OBJECT-TYPE
    SYNTAX INTEGER {
        nonrevertive(1),
        revertive(2)
        }
    ACCESS read-write
    STATUS mandatory
    DESCRIPTION
        "The revertive mode of the APS group.
        
         nonrevertive
        
         Traffic remains on the protection line until another switch
         request is received.
        
         revertive
        
         When the condition that caused a switch to the protection
         line has been cleared the signal is switched back to the
         working line. Since switching is revertive with the 1:n
         architecture, cApsConfigRevert must be set to revertive if
         cApsConfigMode is set to oneToN.
        
         Switching may optionally be revertive with the 1+1 
         architecture.
        
         This object may not be modified if the associated
         cApsConfigRowStatus object is equal to active(1)."
    DEFVAL { nonrevertive }
    ::= { cApsConfigEntry 4 }

cApsConfigDirection OBJECT-TYPE
    SYNTAX INTEGER {
        unidirectional(1),
        bidirectional(2)
        }
    ACCESS read-write
    STATUS mandatory
    DESCRIPTION
        "The directional mode of the APS group.
        
         unidirectional
        
         The unidirectional mode provides protection in one direction.
        
         bidirectional
        
         The bidirectional mode provides protection in both
         directions.
        
         This object may not be modified if the associated
         cApsConfigRowStatus object is equal to active(1)."
    DEFVAL { unidirectional }
    ::= { cApsConfigEntry 5 }

cApsConfigExtraTraffic OBJECT-TYPE
    SYNTAX INTEGER {
        enabled(1),
        disabled(2)
        }
    ACCESS read-write
    STATUS mandatory
    DESCRIPTION
        "This object enables or disables the transfer of extra traffic
         on the protection channel in a 1:n architecture. This object
         must be set to disabled if the architecture is 1+1. It may be
         necessary to disable this in order to interwork with other 
         SONET network elements that don't support extra traffic.
        
         This object may not be modified if the associated
         cApsConfigRowStatus object is equal to active(1)."
    DEFVAL { disabled }
    ::= { cApsConfigEntry 6 }

cApsConfigSdBerThreshold OBJECT-TYPE
    SYNTAX INTEGER(5..9)
    ACCESS read-write
    STATUS mandatory
    DESCRIPTION
        "The Signal Degrade Bit Error Rate.
        
         The negated value of this number is used as the exponent of
         10 for computing the threshold value for the Bit Error Rate
         (BER). For example, a value of 5 indicates a BER threshold 
         of 10^-5.
        
         This object may be modified if the associated
         cApsConfigRowStatus object is equal to active(1)."
    DEFVAL { 5 }
    ::= { cApsConfigEntry 7 }

cApsConfigSfBerThreshold OBJECT-TYPE
    SYNTAX INTEGER(3..5)
    ACCESS read-write
    STATUS mandatory
    DESCRIPTION
        "The Signal Failure Bit Error Rate.
        
         The negated value of this number is used as the exponent of
         10 for computing the threshold value for the Bit Error Rate
         (BER). For example, a value of 5 indicates a BER threshold 
         of 10^-5.
        
         This object may be modified if the associated
         cApsConfigRowStatus object is equal to active(1)."
    DEFVAL { 3 }
    ::= { cApsConfigEntry 8 }

cApsConfigWaitToRestore OBJECT-TYPE
    SYNTAX INTEGER(0..720)
--  Units
--    seconds
    ACCESS read-write
    STATUS mandatory
    DESCRIPTION
        "The Wait To Restore period in seconds.
        
         After clearing of a condition that necessitated an
         automatic switch, the wait to restore period must elapse
         before reverting. This is intended to avoid rapid switch
         oscillations.
        
         GR-253-CORE specifies a Wait To Restore range of 5 to 12
         minutes. G.783 defines a 5 to 12 minute Wait To Restore
         range in section 5.4.1.1.3, but also allows for a shorter
         WTR period in  Table 2-1,
         WaitToRestore value (MI_WTRtime: 0..(5)..12 minutes).
        
         This object may not be modified if the associated
         cApsConfigRowStatus object is equal to active(1)."
    DEFVAL { 300 }
    ::= { cApsConfigEntry 9 }

cApsConfigCreationTime OBJECT-TYPE
    SYNTAX TimeStamp
--    Rsyntax TimeTicks
    ACCESS read-only
    STATUS mandatory
    DESCRIPTION
        "The value of sysUpTime at the time the row was created."
    ::= { cApsConfigEntry 10 }

cApsStatusTable OBJECT-TYPE
    SYNTAX SEQUENCE OF CApsStatusEntry
    ACCESS not-accessible
    STATUS mandatory
    DESCRIPTION
        "This table provides status information about APS groups 
         that have been configured on the system."
    ::= { cApsMIBObjects 2 }

cApsStatusEntry OBJECT-TYPE
    SYNTAX CApsStatusEntry
    ACCESS not-accessible
    STATUS mandatory
    DESCRIPTION
        "A conceptual row in the cApsStatusTable. Entries in this table 
         are created as a side effect of row addition in cApsConfigTable."
    INDEX { --?? IMPLIED may cause problems
            IMPLIED cApsConfigName }
    ::= { cApsStatusTable 1 }

CApsStatusEntry ::= SEQUENCE {
    cApsStatusK1K2Rcv CApsK1K2,
    cApsStatusK1K2Trans CApsK1K2,
    cApsStatusCurrent OCTET STRING,
    cApsStatusModeMismatches Counter,
    cApsStatusChannelMismatches Counter,
    cApsStatusPSBFs Counter,
    cApsStatusFEPLFs Counter,
    cApsStatusSwitchedChannel INTEGER
    }

cApsStatusK1K2Rcv OBJECT-TYPE
    SYNTAX CApsK1K2
--    Rsyntax OCTET STRING(SIZE(2))
    ACCESS read-only
    STATUS mandatory
    DESCRIPTION
        "The current value of the K1 and K2 bytes received on the
         protection channel."
    ::= { cApsStatusEntry 1 }

cApsStatusK1K2Trans OBJECT-TYPE
    SYNTAX CApsK1K2
--    Rsyntax OCTET STRING(SIZE(2))
    ACCESS read-only
    STATUS mandatory
    DESCRIPTION
        "The current value of the K1 and K2 bytes transmitted on the
         protection channel."
    ::= { cApsStatusEntry 2 }

cApsStatusCurrent OBJECT-TYPE
    SYNTAX OCTET STRING(SIZE(1..2))
        -- BITS are:
        --   modeMismatch(0)
        --   channelMismatch(1)
        --   psbf(2)
        --   feplf(3)
        --   extraTraffic(4)
    ACCESS read-only
    STATUS mandatory
    DESCRIPTION
        "The current status of the APS group.
        
         modeMismatch
        
         Modes other than 1+1 unidirectional monitor protection line
         K2 bit 5, which indicates the architecture and K2 bits
         6-8, which indicate if the mode is unidirectional or
         bidirectional. A conflict between the current local mode
         and the received K2 mode information constitutes a
         mode mismatch.
        
         channelMismatch
        
         This bit indicates a  mismatch between the transmitted K1 
         channel and the received K2 channel has been detected.
        
         psbf
        
         This bit indicates a Protection Switch Byte Failure (PSBF) is
         in effect. This condition occurs when either an inconsistent
         APS byte or an invalid code is detected. An inconsistent APS
         byte occurs when no three consecutive K1 bytes of the last 12
         successive frames are identical, starting with the last frame
         containing a previously consistent byte. An invalid code occurs
         when the incoming K1 byte contains an unused code or a code
         irrelevant for the specific switching operation (e.g., Reverse
         Request while no switching request is outstanding) in three
         consecutive frames. An invalid code also occurs when the 
         incoming K1 byte contains an invalid channel number in three 
         consecutive frames.
        
         feplf
        
         Modes other than 1+1 unidirectional monitor the K1 byte
         for Far-End Protection-Line failures. A Far-End
         Protection-Line defect is declared based on receiving
         SF on the protection line.
        
         extraTraffic
        
         This bit indicates whether extra traffic is currently being
         accepted on the protection line."
    ::= { cApsStatusEntry 3 }

cApsStatusModeMismatches OBJECT-TYPE
    SYNTAX Counter
    ACCESS read-only
    STATUS mandatory
    DESCRIPTION
        "A count of Mode Mismatch conditions."
    ::= { cApsStatusEntry 4 }

cApsStatusChannelMismatches OBJECT-TYPE
    SYNTAX Counter
    ACCESS read-only
    STATUS mandatory
    DESCRIPTION
        "A count of Channel Mismatch conditions."
    ::= { cApsStatusEntry 5 }

cApsStatusPSBFs OBJECT-TYPE
    SYNTAX Counter
    ACCESS read-only
    STATUS mandatory
    DESCRIPTION
        "A count of Protection Switch Byte Failure conditions.
         This condition occurs when either an inconsistent APS
         byte or an invalid code is detected. An inconsistent APS
         byte occurs when no three consecutive K1 bytes of the last
         12 successive frames are identical, starting with the last
         frame containing a previously consistent byte. An invalid
         code occurs when the incoming K1 byte contains an unused
         code or a code irrelevant for the specific switching 
         operation (e.g., Reverse Request while no switching 
         request is outstanding) in three consecutive frames. 
         An invalid code also occurs when the incoming K1 byte 
         contains an invalid channel number in three consecutive 
         frames."
    ::= { cApsStatusEntry 6 }

cApsStatusFEPLFs OBJECT-TYPE
    SYNTAX Counter
    ACCESS read-only
    STATUS mandatory
    DESCRIPTION
        "A count of Far-End Protection-Line Failure conditions.
         This condition is declared based on receiving SF on
         the protection line in the K1 byte."
    ::= { cApsStatusEntry 7 }

cApsStatusSwitchedChannel OBJECT-TYPE
    SYNTAX INTEGER
    ACCESS read-only
    STATUS mandatory
    DESCRIPTION
        "This field is set to the number of the channel that is 
         currently switched to protection. The value 0 indicates no 
         channel is switched to protection. The values 1-14 indicate
         that working channel is switched to protection."
    ::= { cApsStatusEntry 8 }

cApsChanLTEs OBJECT-TYPE
    SYNTAX Gauge
    ACCESS read-only
    STATUS mandatory
    DESCRIPTION
        "The count of SONET LTE interfaces on the system. Each 
         interface that is included has an ifType value of sonet(39)."
    ::= { cApsMap 1 }

cApsMapTable OBJECT-TYPE
    SYNTAX SEQUENCE OF CApsMapEntry
    ACCESS not-accessible
    STATUS mandatory
    DESCRIPTION
        "This table lists the SONET LTE interfaces on the system. Each 
         interface that is listed has an ifType value of sonet(39)."
    ::= { cApsMap 2 }

cApsMapEntry OBJECT-TYPE
    SYNTAX CApsMapEntry
    ACCESS not-accessible
    STATUS mandatory
    DESCRIPTION
        "A conceptual row in the cApsMapTable."
    INDEX { cApsMapIfIndex }
    ::= { cApsMapTable 1 }

CApsMapEntry ::= SEQUENCE {
    cApsMapIfIndex InterfaceIndex,
    cApsMapGroupName SnmpAdminString,
    cApsMapChanNumber INTEGER
    }

cApsMapIfIndex OBJECT-TYPE
    SYNTAX InterfaceIndex
--    Rsyntax INTEGER(1..2147483647)
    ACCESS not-accessible
    STATUS mandatory
    DESCRIPTION
        "The Interface Index assigned to a SONET LTE. This is an 
         interface with ifType sonet(39)."
    ::= { cApsMapEntry 1 }

cApsMapGroupName OBJECT-TYPE
    SYNTAX SnmpAdminString(SIZE(0..32))
--    Rsyntax OCTET STRING(SIZE(0..32))
    ACCESS read-only
    STATUS mandatory
    DESCRIPTION
        "A textual name for the APS group which this channel is
         included in. If the channel is not part of an APS group
         this value is set to a string of size 0.
        
         When an instance of cApsChanConfigIfIndex is set equal to an
         instance of cApsMapIfIndex, cApsMapGroupName is set equal
         to the corresponding value of cApsChanConfigGroupName.
        
         If the cApsMapIfIndex ceases to be equal to an instance of
         cApsChanConfigIfIndex, either because of a change in the 
         value of cApsChanConfigIfIndex, or because of row deletion 
         in the CApsChanConfigTable, cApsMapGroupName is set to a 
         string of size 0."
    ::= { cApsMapEntry 2 }

cApsMapChanNumber OBJECT-TYPE
    SYNTAX INTEGER(-1..14)
    ACCESS read-only
    STATUS mandatory
    DESCRIPTION
        "This field is set to a unique channel number within an APS 
         group. The value 0 indicates the null channel. The values 1-14 
         define a working channel. If the SONET LTE is not part of an 
         APS group this value is set to -1.
        
         When an instance of cApsChanConfigIfIndex is set equal to an 
         instance of cApsMapIfIndex, cApsMapChanNumber is set equal to 
         the corresponding value of cApsChanConfigNumber.
        
         If the cApsMapIfIndex ceases to be equal to an instance of
         cApsChanConfigIfIndex, either because of a change in the value 
         of cApsChanConfigIfIndex, or because of row deletion in the
         CApsChanConfigTable, cApsMapChanNumber is set to -1."
    ::= { cApsMapEntry 3 }

cApsChanConfigTable OBJECT-TYPE
    SYNTAX SEQUENCE OF CApsChanConfigEntry
    ACCESS not-accessible
    STATUS mandatory
    DESCRIPTION
        "This table lists the APS channels that have been configured
         in APS groups."
    ::= { cApsMIBObjects 4 }

cApsChanConfigEntry OBJECT-TYPE
    SYNTAX CApsChanConfigEntry
    ACCESS not-accessible
    STATUS mandatory
    DESCRIPTION
        "A conceptual row in the cApsChanConfigTable."
    INDEX { cApsChanConfigGroupName, cApsChanConfigNumber }
    ::= { cApsChanConfigTable 1 }

CApsChanConfigEntry ::= SEQUENCE {
    cApsChanConfigGroupName SnmpAdminString,
    cApsChanConfigNumber INTEGER,
    cApsChanConfigRowStatus RowStatus,
    cApsChanConfigIfIndex InterfaceIndex,
    cApsChanConfigPriority INTEGER
    }

cApsChanConfigGroupName OBJECT-TYPE
    SYNTAX SnmpAdminString(SIZE(1..32))
--    Rsyntax OCTET STRING(SIZE(1..32))
    ACCESS not-accessible
    STATUS mandatory
    DESCRIPTION
        "A textual name for the APS group which this channel is
         included in."
    ::= { cApsChanConfigEntry 1 }

cApsChanConfigNumber OBJECT-TYPE
    SYNTAX INTEGER(0..14)
    ACCESS not-accessible
    STATUS mandatory
    DESCRIPTION
        "This field is set to a unique channel number within an APS 
         group. The value 0 indicates the null channel. The values 1-14 
         define a working channel.
        
         This field must be assigned a unique number within the group."
    ::= { cApsChanConfigEntry 2 }

cApsChanConfigRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this APS channel entry.
        
         An entry may not exist in the active state unless all
         objects in the entry have an appropriate value.
        
         A row in the cApsChanConfigTable may not be created,
         deleted, set to notInService or otherwise modified
         if the cApsChanConfigGroupName value is equal to an
         cApsConfigName value and the associated cApsConfigRowStatus
         object is equal to active. However, if the 
         cApsConfigRowStatus object is equal to notInService, a row 
         may be created, deleted or modified. In other words, a 
         channel may not be added, deleted or modified if the group 
         is active.
        
         A row may be created with an cApsChanConfigGroupName value
         that is not equal to any existing instance of cApsConfigName.
         This action is the initial step in adding a SONET LTE to a
         new APS group.
        
         If this object is set to destroy, the associated instance
         of cApsMapGroupName will be set to a string of size 0 and
         the cApsMapChanNumber will be set to -1. The channel status
         entry will also be deleted by this action.
        
         cApsChanConfigNumber must be set to a unique channel number 
         within the APS group. The value 0 indicates the null channel.
         The values 1-14 define a working channel. When an attempt is
         made to set the  corresponding cApsConfigRowStatus field to
         active the cApsChanConfigNumber values of all entries with 
         equal cApsChanConfigGroupName fields must represent a set of
         consecutive integer values beginning with 0 or 1, depending 
         on the architecture of the group, and ending with n, where 
         n is  greater than or equal to 1 and less than or equal to 
         14. Otherwise, the error inconsistentValue is returned to 
         the cApsConfigRowStatus set attempt."
    ::= { cApsChanConfigEntry 3 }

cApsChanConfigIfIndex OBJECT-TYPE
    SYNTAX InterfaceIndex
--    Rsyntax INTEGER(1..2147483647)
    ACCESS read-write
    STATUS mandatory
    DESCRIPTION
        "The Interface Index assigned to a SONET LTE. This is an
         interface with ifType sonet(39). The value of this object
         must be unique among all instances of cApsChanConfigIfIndex.
         In other words, a particular SONET LTE can only be configured in
         one APS group.
        
         This object cannot be set if the cApsChanConfigGroupName 
         instance associated with this row is equal to an instance of 
         cApsConfigName and the corresponding cApsConfigRowStatus object
         is set to active. In other words this value cannot be changed 
         if the APS group is active. However, this value may be changed 
         if the cApsConfigRowStatus value is equal to notInService."
    ::= { cApsChanConfigEntry 4 }

cApsChanConfigPriority OBJECT-TYPE
    SYNTAX INTEGER {
        low(1),
        high(2)
        }
    ACCESS read-write
    STATUS mandatory
    DESCRIPTION
        "The priority of the channel.
        
         This field deterimines whether high or low priority
         SD and SF codes are used in K1 requests.
        
         This field is only applicable if the channel is to be 
         included in a group using the 1:n architecture. It is not 
         applicable if the channel is to be included in a group 
         using the 1+1 architecture, and is ignored in that case.
        
         This object cannot be set if the cApsChanConfigGroupName 
         instance associated with this row is equal to an instance 
         of cApsConfigName and the corresponding cApsConfigRowStatus
         object is set to active. In other words this value cannot 
         be changed if the APS group is active. However, This value 
         may be changed if the cApsConfigRowStatus value is equal to
         notInService."
    DEFVAL { low }
    ::= { cApsChanConfigEntry 5 }

cApsCommandTable OBJECT-TYPE
    SYNTAX SEQUENCE OF CApsCommandEntry
    ACCESS not-accessible
    STATUS mandatory
    DESCRIPTION
        "This table allows commands to be sent to configured APS 
         groups."
    ::= { cApsMIBObjects 5 }

cApsCommandEntry OBJECT-TYPE
    SYNTAX CApsCommandEntry
    ACCESS not-accessible
    STATUS mandatory
    DESCRIPTION
        "A conceptual row in the cApsCommandTable. This row exists 
         only if the associated cApsConfigEntry is active."
    INDEX { cApsChanConfigGroupName, cApsChanConfigNumber }
    ::= { cApsCommandTable 1 }

CApsCommandEntry ::= SEQUENCE {
    cApsCommandSwitch CApsSwitchCommand,
    cApsCommandControl CApsControlCommand
    }

cApsCommandSwitch OBJECT-TYPE
    SYNTAX CApsSwitchCommand
--    Rsyntax INTEGER {
--        noCmd(1),
--        clear(2),
--        lockoutOfProtection(3),
--        forcedSwitchWorkToProtect(4),
--        forcedSwitchProtectToWork(5),
--        manualSwitchWorkToProtect(6),
--        manualSwitchProtectToWork(7),
--        exercise(8)
--        }
    ACCESS read-write
    STATUS mandatory
    DESCRIPTION
        "Allows the initiation of an APS switch command on the
         APS group and channel specified by the index values.
        
         When read this object returns the last command written
         or noCmd if no command has been written to this
         channel since initialization. The return of the last command
         written does not imply that this command is currently in effect.
         This request may have been preempted by a higer priority
         local or remote request. In order to determine the
         current state of the APS group it is necessary to read
         the objects cApsStatusK1K2Rcv and cApsStatusK1K2Trans.
        
         The value lockoutOfProtection should only be applied
         to the protection line channel since that switch command
         prevents any of the working channels from switching to the 
         protection line. Following the same logic, 
         forcedSwitchProtectToWork and manualSwitchProtectToWork should 
         only be applied to the protection line channel.
        
         forcedSwitchWorkToProtect and manualSwitchWorkToProtect
         should only be applied to a working channel."
    ::= { cApsCommandEntry 1 }

cApsCommandControl OBJECT-TYPE
    SYNTAX CApsControlCommand
--    Rsyntax INTEGER {
--        noCmd(1),
--        lockoutWorkingChannel(2),
--        clearLockoutWorkingChannel(3)
--        }
    ACCESS read-write
    STATUS mandatory
    DESCRIPTION
        "Allows the initiation of an APS control command on the
         APS group and channel specified by the index values.
        
         When read this object returns the last command written
         or noCmd if no command has been
         written to this channel since initialization.
        
         This object does not apply to the protection line."
    ::= { cApsCommandEntry 2 }

cApsChanStatusTable OBJECT-TYPE
    SYNTAX SEQUENCE OF CApsChanStatusEntry
    ACCESS not-accessible
    STATUS mandatory
    DESCRIPTION
        "This table contains status information for all SONET LTE
         interfaces that are included in APS groups."
    ::= { cApsMIBObjects 6 }

cApsChanStatusEntry OBJECT-TYPE
    SYNTAX CApsChanStatusEntry
    ACCESS not-accessible
    STATUS mandatory
    DESCRIPTION
        "A conceptual row in the cApsChanStatusTable. A row in this
         table is created as a side effect of row addition in the
         cApsChanConfigTable. The cApsChanStatusTable row exists
         as long as the cApsChanConfigTable entry exists, regardless
         of whether the associated cApsChanConfigRowStatus is active."
    INDEX { cApsChanConfigGroupName, cApsChanConfigNumber }
    ::= { cApsChanStatusTable 1 }

CApsChanStatusEntry ::= SEQUENCE {
    cApsChanStatusCurrent OCTET STRING,
    cApsChanStatusSignalDegrades Counter,
    cApsChanStatusSignalFailures Counter,
    cApsChanStatusSwitchovers Counter,
    cApsChanStatusLastSwitchover TimeStamp
    }

cApsChanStatusCurrent OBJECT-TYPE
    SYNTAX OCTET STRING(SIZE(1..2))
        -- BITS are:
        --   lockedOut(0)
        --   sd(1)
        --   sf(2)
        --   switched(3)
    ACCESS read-only
    STATUS mandatory
    DESCRIPTION
        "Indicates the current state of the port.
        
         lockedOut
        
         This bit, when applied to a working channel, indicates that
         the channel is prevented from switching to the protection 
         line. When applied to the null channel, this bit indicates 
         that no working channel may switch to the protection line.
        
         sd
        
         A signal degrade condition is in effect.
        
         sf
        
         A signal failure condition is in effect.
        
         switched
        
         The switched bit is applied to a working channel if that
         channel is currently switched to the protection line."
    ::= { cApsChanStatusEntry 1 }

cApsChanStatusSignalDegrades OBJECT-TYPE
    SYNTAX Counter
    ACCESS read-only
    STATUS mandatory
    DESCRIPTION
        "A count of Signal Degrade conditions. This condition occurs 
         when the line Bit Error Rate exceeds the currently configured 
         threshold."
    ::= { cApsChanStatusEntry 2 }

cApsChanStatusSignalFailures OBJECT-TYPE
    SYNTAX Counter
    ACCESS read-only
    STATUS mandatory
    DESCRIPTION
        "A count of Signal Failure conditions that have been detected on
         the incoming signal. This condition occurs when a loss of 
         signal, loss of frame, AIS-L or a Line bit error rate exceeding
         10^-3 is detected on an incoming line."
    ::= { cApsChanStatusEntry 3 }

cApsChanStatusSwitchovers OBJECT-TYPE
    SYNTAX Counter
    ACCESS read-only
    STATUS mandatory
    DESCRIPTION
        "The number of times this channel has switched to the protection
         line. When queried with index value cApsChanConfigNumber set to
         0, which is the protection line, this object will return 0."
    ::= { cApsChanStatusEntry 4 }

cApsChanStatusLastSwitchover OBJECT-TYPE
    SYNTAX TimeStamp
--    Rsyntax TimeTicks
    ACCESS read-only
    STATUS mandatory
    DESCRIPTION
        "The value of sysUpTime when this channel last completed a 
         switch to the protection line. If this channel has never 
         switched to the protection line, or this channel is the 
         protection line, the value 0  will be returned."
    ::= { cApsChanStatusEntry 5 }

cApsEventSwitchover TRAP-TYPE
-- Reverse mappable trap
    ENTERPRISE cApsMIBNotifications
    VARIABLES {
        cApsChanStatusSwitchovers, cApsChanStatusCurrent }
--  Status
--    mandatory
    DESCRIPTION
        "A cApsEventSwitchover notification is sent when the
         value of an instance of cApsChanStatusSwitchovers increments."
    ::= 1

cApsEventModeMismatch TRAP-TYPE
-- Reverse mappable trap
    ENTERPRISE cApsMIBNotifications
    VARIABLES {
        cApsStatusModeMismatches, cApsStatusCurrent }
--  Status
--    mandatory
    DESCRIPTION
        "A cApsEventModeMismatch notification is sent when the value of 
         an instance of cApsStatusModeMismatches increments."
    ::= 2

cApsEventChannelMismatch TRAP-TYPE
-- Reverse mappable trap
    ENTERPRISE cApsMIBNotifications
    VARIABLES {
        cApsStatusChannelMismatches, cApsStatusCurrent }
--  Status
--    mandatory
    DESCRIPTION
        "A cApsEventChannelMismatch notification is sent when the value 
         of an instance of cApsStatusChannelMismatches increments."
    ::= 3

cApsEventPSBF TRAP-TYPE
-- Reverse mappable trap
    ENTERPRISE cApsMIBNotifications
    VARIABLES {
        cApsStatusPSBFs, cApsStatusCurrent }
--  Status
--    mandatory
    DESCRIPTION
        "An cApsEventPSBF notification is sent when the value of an 
         instance of cApsStatusPSBFs increments."
    ::= 4

cApsEventFEPLF TRAP-TYPE
-- Reverse mappable trap
    ENTERPRISE cApsMIBNotifications
    VARIABLES {
        cApsStatusFEPLFs, cApsStatusCurrent }
--  Status
--    mandatory
    DESCRIPTION
        "An cApsEventFEPLFs notification is sent when the value of an 
         instance of cApsStatusFEPLFs increments."
    ::= 5

cApsConfigGeneral OBJECT IDENTIFIER ::= { cApsGroups 1 }
-- OBJECT-GROUP
--  Status
--    mandatory
--  Descr
--    A collection of cApsConfigTable objects providing configuration
--     information applicable to all linear APS groups.
--  objects
--    cApsConfigMode, cApsConfigRevert, cApsConfigDirection, 
--    cApsConfigExtraTraffic, cApsConfigSdBerThreshold, 
--    cApsConfigSfBerThreshold, cApsConfigCreationTime, 
--    cApsConfigRowStatus

cApsConfigWtr OBJECT IDENTIFIER ::= { cApsGroups 2 }
-- OBJECT-GROUP
--  Status
--    mandatory
--  Descr
--    The cApsConfigTable object that provides information which is
--     applicable to groups supporting a configurable WTR period.
--  objects
--    cApsConfigWaitToRestore

cApsCommandOnePlusOne OBJECT IDENTIFIER ::= { cApsGroups 3 }
-- OBJECT-GROUP
--  Status
--    mandatory
--  Descr
--    The  cApsCommandTable object which is applicable to groups
--     implementing the linear APS 1+1 architecture. Also, set 
--     operations must be supported.
--  objects
--    cApsCommandSwitch

cApsCommandOneToN OBJECT IDENTIFIER ::= { cApsGroups 4 }
-- OBJECT-GROUP
--  Status
--    mandatory
--  Descr
--    A collection of cApsCommandTable objects which are applicable to
--     groups implementing the linear APS 1:n architecture. Also, set
--     operations must be supported.
--  objects
--    cApsCommandSwitch, cApsCommandControl

cApsStatusGeneral OBJECT IDENTIFIER ::= { cApsGroups 5 }
-- OBJECT-GROUP
--  Status
--    mandatory
--  Descr
--    A collection of cApsStatusTable objects providing status 
--     information applicable to all linear APS groups.
--  objects
--    cApsStatusK1K2Rcv, cApsStatusK1K2Trans, cApsStatusCurrent, 
--    cApsStatusModeMismatches, cApsStatusChannelMismatches, 
--    cApsStatusPSBFs, cApsStatusFEPLFs, cApsStatusSwitchedChannel

cApsChanGeneral OBJECT IDENTIFIER ::= { cApsGroups 6 }
-- OBJECT-GROUP
--  Status
--    mandatory
--  Descr
--    A collection of channel objects providing information 
--     applicable to all linear APS channels.
--  objects
--    cApsChanConfigIfIndex, cApsChanConfigRowStatus, 
--    cApsChanStatusCurrent, cApsChanStatusSignalDegrades, 
--    cApsChanStatusSignalFailures, cApsChanStatusSwitchovers, 
--    cApsChanStatusLastSwitchover

cApsChanOneToN OBJECT IDENTIFIER ::= { cApsGroups 7 }
-- OBJECT-GROUP
--  Status
--    mandatory
--  Descr
--    The cApsChanConfigTable object that provides information which 
--     is only applicable to groups implementing the linear APS 1:n 
--     architecture.
--  objects
--    cApsChanConfigPriority

cApsTotalsGroup OBJECT IDENTIFIER ::= { cApsGroups 8 }
-- OBJECT-GROUP
--  Status
--    mandatory
--  Descr
--    A collection of objects providing optional counts of configured
--     APS groups and SONET LTE interfaces.
--  objects
--    cApsConfigGroups, cApsChanLTEs

cApsMapGroup OBJECT IDENTIFIER ::= { cApsGroups 9 }
-- OBJECT-GROUP
--  Status
--    mandatory
--  Descr
--    A collection of cApsMapTable objects providing a mapping
--     from sonet(39) InterfaceIndex to group name and channel
--     number for assigned APS channels and a list of unassigned
--     sonet(39) interfaces.
--  objects
--    cApsMapGroupName, cApsMapChanNumber

cApsEventOptional OBJECT IDENTIFIER ::= { cApsGroups 10 }
-- NOTIFICATION-GROUP
--  Status
--    mandatory
--  Descr
--    A collection of SONET linear APS notifications that may 
--     optionally be implemented.
--  notifications
--    cApsEventSwitchover, cApsEventModeMismatch, 
--    cApsEventChannelMismatch, cApsEventPSBF, cApsEventFEPLF

cApsCompliance OBJECT IDENTIFIER ::= { cApsCompliances 1 }
-- MODULE-COMPLIANCE
--  Status
--    mandatory
--  Descr
--    The compliance statement for linear APS groups.
--  Module
--    >>current<<
--   MandGroup
--    cApsConfigGeneral
--   MandGroup
--    cApsStatusGeneral
--   MandGroup
--    cApsChanGeneral
--   ObjVar
--    cApsConfigMode
--   ObjVar
--    cApsConfigRevert
--   ObjVar
--    cApsConfigDirection
--   ObjVar
--    cApsConfigExtraTraffic
--   ObjVar
--    cApsConfigSdBerThreshold
--   ObjVar
--    cApsConfigSfBerThreshold
--   ObjVar
--    cApsConfigWaitToRestore
--   ObjVar
--    cApsConfigRowStatus
--   ObjVar
--    cApsChanConfigIfIndex
--   ObjVar
--    cApsChanConfigPriority
--   ObjVar
--    cApsChanConfigRowStatus
--   OptGroup
--    cApsConfigWtr
--   OptGroup
--    cApsCommandOnePlusOne
--   OptGroup
--    cApsCommandOneToN
--   OptGroup
--    cApsChanOneToN
--   OptGroup
--    cApsTotalsGroup
--   OptGroup
--    cApsMapGroup


END
