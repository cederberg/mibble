-- MIB file created 04-May-2006 16:24:16, by
--   SMICng version 2.2.11-beta(PRO)(Solaris), January 20, 2001. Enterprise key cisco.com

CISCO-IETF-DHCP-SERVER-MIB DEFINITIONS ::= BEGIN

-- From file: "CISCO-IETF-DHCP-SERVER-MIB.my"
-- Compile options "4 7 F H N O W 03 06 0B 0G 0N 0T"

IMPORTS
    SnmpAdminString
            FROM SNMP-FRAMEWORK-MIB
    ciscoExperiment
            FROM CISCO-SMI
    Counter
            FROM RFC1155-SMI
    OBJECT-TYPE
            FROM RFC-1212;

ciscoIetfDhcpSrvMIB OBJECT IDENTIFIER ::= { ciscoExperiment 102 }
-- MODULE-IDENTITY
--  LastUpdated
--    200403011200Z
--  OrgName
--    Cisco Systems, Inc.
--  ContactInfo
--           Cisco Systems
--            Customer Service
--    
--    Postal: 170 W Tasman Drive
--            San Jose, CA  95134
--            USA
--    
--       Tel: +1 800 553-NETS
--    
--    E-mail: cs-dhcp-mib@cisco.com
--  Descr
--    The MIB module for entities implementing the server side of 
--    the Bootstrap Protocol (BOOTP) and the Dynamic Host 
--    Configuration protocol (DHCP) for Internet Protocol version 
--    4(IPv4).  This MIB does not include support for Dynamic DNS 
--    (DDNS) updating nor for the DHCP Failover Protocol.
--  RevDate
--    200403011200Z
--  RevDescr
--    Initial version of this MIB module.

ciscoIetfDhcpv4SrvMIBNotifs OBJECT IDENTIFIER ::= { ciscoIetfDhcpSrvMIB 0 }
ciscoIetfDhcpv4SrvMIBObjects OBJECT IDENTIFIER ::= { ciscoIetfDhcpSrvMIB 1 }
ciscoIetfDhcpv4SrvMIBConform OBJECT IDENTIFIER ::= { ciscoIetfDhcpSrvMIB 2 }
cDhcpv4SrvCompliances OBJECT IDENTIFIER ::= { ciscoIetfDhcpv4SrvMIBConform 1 }
cDhcpv4SrvGroups OBJECT IDENTIFIER ::= { ciscoIetfDhcpv4SrvMIBConform 2 }

cDhcpv4SrvSystem OBJECT IDENTIFIER ::= { ciscoIetfDhcpv4SrvMIBObjects 1 }
-- OBJECT-IDENTITY
--  Status
--    mandatory
--  Descr
--    Group of objects that are related to the overall system.

cBootpCounters OBJECT IDENTIFIER ::= { ciscoIetfDhcpv4SrvMIBObjects 2 }
-- OBJECT-IDENTITY
--  Status
--    mandatory
--  Descr
--    Group of objects that count various BOOTP events.

cDhcpv4Counters OBJECT IDENTIFIER ::= { ciscoIetfDhcpv4SrvMIBObjects 3 }
-- OBJECT-IDENTITY
--  Status
--    mandatory
--  Descr
--    Group of objects that count various DHCPv4 events.

cDhcpv4SrvConfiguration OBJECT IDENTIFIER ::= { ciscoIetfDhcpv4SrvMIBObjects 4 }
-- OBJECT-IDENTITY
--  Status
--    mandatory
--  Descr
--    Objects that contain pre-configured and dynamic configuration 
--    information.

cDhcpv4SrvSystemDescr OBJECT-TYPE
    SYNTAX SnmpAdminString(SIZE(0..255))
--    Rsyntax OCTET STRING(SIZE(0..255))
    ACCESS read-only
    STATUS mandatory
    DESCRIPTION
        "A textual description of the server.  This value should 
        include the full name and version identification of the 
        server."
    ::= { cDhcpv4SrvSystem 1 }

cDhcpv4SrvSystemObjectID OBJECT-TYPE
    SYNTAX OBJECT IDENTIFIER
    ACCESS read-only
    STATUS mandatory
    DESCRIPTION
        "The vendor's authoritative identification of the network 
        management subsystem contained in this entity.  This value is 
        allocated within the SMI enterprise subtree (1.3.6.1.4.1) and 
        provides an easy and unambiguous means for determining what
        kind of server is being managed.  For example, if vendor Ohso
        Soft, Inc. is assigned the subtree 1.3.6.1.4.1.4242, it may
        assign the identifier 1.3.6.1.4.1.4242.1.1 to its Ursa DHCP
        Server."
    ::= { cDhcpv4SrvSystem 2 }

cBootpCountRequests OBJECT-TYPE
    SYNTAX Counter
    ACCESS read-only
    STATUS mandatory
    DESCRIPTION
        "The number of packets received that contain a Message Type of 
        1 (BOOTREQUEST) in the first octet and do not contain option 
        number 53 (DHCP Message Type) in the options."
    REFERENCE
        "RFC-2131."
    ::= { cBootpCounters 1 }

cBootpCountInvalids OBJECT-TYPE
    SYNTAX Counter
    ACCESS read-only
    STATUS mandatory
    DESCRIPTION
        "The number of packets received that do not contain a Message 
        Type of 1 (BOOTREQUEST) in the first octet or are not valid 
        BOOTP packets (e.g., too short, invalid field in packet 
        header)."
    ::= { cBootpCounters 2 }

cBootpCountReplies OBJECT-TYPE
    SYNTAX Counter
    ACCESS read-only
    STATUS mandatory
    DESCRIPTION
        "The number of packets sent that contain a Message Type of 2 
        (BOOTREPLY) in the first octet and do not contain option number 
        53 (DHCP Message Type) in the options."
    REFERENCE
        "RFC-2131."
    ::= { cBootpCounters 3 }

cBootpCountDropUnknownClients OBJECT-TYPE
    SYNTAX Counter
    ACCESS read-only
    STATUS mandatory
    DESCRIPTION
        "The number of BOOTP packets dropped due to the server not 
        recognizing or not providing service to the hardware address 
        received in the incoming packet."
    ::= { cBootpCounters 4 }

cBootpCountDropNotServingSubnet OBJECT-TYPE
    SYNTAX Counter
    ACCESS read-only
    STATUS mandatory
    DESCRIPTION
        "The number of BOOTP packets dropped due to the server not 
        being configured or not otherwise able to serve addresses on 
        the subnet from which this message was received."
    ::= { cBootpCounters 5 }

cDhcpv4CountDiscovers OBJECT-TYPE
    SYNTAX Counter
    ACCESS read-only
    STATUS mandatory
    DESCRIPTION
        "The number of DHCPDISCOVER (option 53 with value 1) packets 
        received."
    REFERENCE
        "RFC2131; RFC2132, section 9.6."
    ::= { cDhcpv4Counters 1 }

cDhcpv4CountOffers OBJECT-TYPE
    SYNTAX Counter
    ACCESS read-only
    STATUS mandatory
    DESCRIPTION
        "The number of DHCPOFFER (option 53 with value 2) packets 
        sent."
    REFERENCE
        "RFC2131; RFC2132, section 9.6."
    ::= { cDhcpv4Counters 2 }

cDhcpv4CountRequests OBJECT-TYPE
    SYNTAX Counter
    ACCESS read-only
    STATUS mandatory
    DESCRIPTION
        "The number of DHCPREQUEST (option 53 with value 3) packets 
        received."
    REFERENCE
        "RFC2131; RFC2132, section 9.6."
    ::= { cDhcpv4Counters 3 }

cDhcpv4CountDeclines OBJECT-TYPE
    SYNTAX Counter
    ACCESS read-only
    STATUS mandatory
    DESCRIPTION
        "The number of DHCPDECLINE (option 53 with value 4) packets 
        received."
    REFERENCE
        "RFC2131; RFC2132, section 9.6."
    ::= { cDhcpv4Counters 4 }

cDhcpv4CountAcks OBJECT-TYPE
    SYNTAX Counter
    ACCESS read-only
    STATUS mandatory
    DESCRIPTION
        "The number of DHCPACK (option 53 with value 5) packets sent."
    REFERENCE
        "RFC2131; RFC2132, section 9.6."
    ::= { cDhcpv4Counters 5 }

cDhcpv4CountNaks OBJECT-TYPE
    SYNTAX Counter
    ACCESS read-only
    STATUS mandatory
    DESCRIPTION
        "The number of DHCPNACK (option 53 with value 6) packets sent."
    REFERENCE
        "RFC2131; RFC2132, section 9.6."
    ::= { cDhcpv4Counters 6 }

cDhcpv4CountReleases OBJECT-TYPE
    SYNTAX Counter
    ACCESS read-only
    STATUS mandatory
    DESCRIPTION
        "The number of DHCPRELEASE (option 53 with value 7) packets 
        received."
    REFERENCE
        "RFC2131; RFC2132, section 9.6."
    ::= { cDhcpv4Counters 7 }

cDhcpv4CountInforms OBJECT-TYPE
    SYNTAX Counter
    ACCESS read-only
    STATUS mandatory
    DESCRIPTION
        "The number of DHCPINFORM (option 53 with value 8) packets 
        received."
    REFERENCE
        "RFC2131; RFC2132, section 9.6."
    ::= { cDhcpv4Counters 8 }

cDhcpv4CountInvalids OBJECT-TYPE
    SYNTAX Counter
    ACCESS read-only
    STATUS mandatory
    DESCRIPTION
        "The number of DHCP packets received whose DHCP message type 
        (i.e., option number 53) is not understood or handled by the 
        server."
    ::= { cDhcpv4Counters 10 }

cDhcpv4CountDropUnknownClient OBJECT-TYPE
    SYNTAX Counter
    ACCESS read-only
    STATUS mandatory
    DESCRIPTION
        "The number of DHCP packets dropped due to the server not 
        recognizing or not providing service to the client-id and/or 
        hardware address received in the incoming packet."
    ::= { cDhcpv4Counters 11 }

cDhcpv4CountDropNotServingSubnet OBJECT-TYPE
    SYNTAX Counter
    ACCESS read-only
    STATUS mandatory
    DESCRIPTION
        "The number of DHCP packets dropped due to the server not being 
        configured or not otherwise able to serve addresses on the 
        subnet from which this message was received."
    ::= { cDhcpv4Counters 12 }

cDhcpv4SrvSystemObjects OBJECT IDENTIFIER ::= { cDhcpv4SrvGroups 1 }
-- OBJECT-GROUP
--  Status
--    mandatory
--  Descr
--    Objects belonging to the cDhcpv4SrvSystemObjects group.
--  objects
--    cDhcpv4SrvSystemDescr, cDhcpv4SrvSystemObjectID

cBootpCountersGroup OBJECT IDENTIFIER ::= { cDhcpv4SrvGroups 2 }
-- OBJECT-GROUP
--  Status
--    mandatory
--  Descr
--    Objects belonging to the cBootpBountersGroup.
--  objects
--    cBootpCountRequests, cBootpCountInvalids, cBootpCountReplies, 
--    cBootpCountDropUnknownClients, 
--    cBootpCountDropNotServingSubnet

cDhcpv4CounterObjects OBJECT IDENTIFIER ::= { cDhcpv4SrvGroups 3 }
-- OBJECT-GROUP
--  Status
--    mandatory
--  Descr
--    Objects belonging to the cDhcpv4CounterObjects group.
--  objects
--    cDhcpv4CountDiscovers, cDhcpv4CountOffers, 
--    cDhcpv4CountRequests, cDhcpv4CountDeclines, cDhcpv4CountAcks, 
--    cDhcpv4CountNaks, cDhcpv4CountReleases, cDhcpv4CountInforms, 
--    cDhcpv4CountInvalids, cDhcpv4CountDropUnknownClient, 
--    cDhcpv4CountDropNotServingSubnet

cDhcpv4SrvCompliance OBJECT IDENTIFIER ::= { cDhcpv4SrvCompliances 1 }
-- MODULE-COMPLIANCE
--  Status
--    mandatory
--  Descr
--    This group describes the requirements for conformance to the
--    DHCP Server MIB.  A DHCPv4 server implementation is only
--    required to support IPv4 addresses.
--  Module
--    >>current<<
--   MandGroup
--    cDhcpv4SrvSystemObjects
--   MandGroup
--    cBootpCountersGroup
--   MandGroup
--    cDhcpv4CounterObjects


END
