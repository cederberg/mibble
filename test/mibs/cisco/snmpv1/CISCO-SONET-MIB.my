-- MIB file created 10-Sep-2001 11:32:44, by
--   SMICng version 2.2.11-beta(PRO)(Solaris), January 20, 2001. Enterprise key cisco.com

CISCO-SONET-MIB DEFINITIONS ::= BEGIN

-- From file: "CISCO-SONET-MIB.my"
-- Compile options "4 7 F H N W 03 06 0B 0G 0N 0T"

IMPORTS
    TruthValue
            FROM SNMPv2-TC-v1
--    Unsigned32
--            FROM CISCO-TC
    InterfaceIndex, ifIndex
            FROM IF-MIB
    ciscoMgmt
            FROM CISCO-SMI
    Counter, Gauge
            FROM RFC1155-SMI
    OBJECT-TYPE
            FROM RFC-1212;

ciscoSonetMIB OBJECT IDENTIFIER ::= { ciscoMgmt 126 }
-- MODULE-IDENTITY
--  LastUpdated
--    200007120000Z
--  OrgName
--    Cisco Systems, Inc.
--  ContactInfo
--           Cisco Systems
--            Customer Service
--    
--    Postal: 170 W Tasman Drive
--            San Jose, CA  95134
--            USA
--    
--            Tel: +1 800 553-NETS
--    
--    E-mail: cs-wanatm@cisco.com
--  Descr
--    The MIB module to describe SONET/SDH interfaces
--     objects. This is an extension to the standard SONET 
--     MIB(RFC 2558).
--  RevDate
--    200007120000Z
--  RevDescr
--    Made following changes
--    
--     (1) Added enumeration csApsNone(3) to 
--         csApsActiveLine object and updated the 
--         description.
--     (2) Added enumerations sonetSts192c(7) and 
--         sonetStm64(8) to csConfigType object and 
--         updated the descripton.
--     (3) Fixed description of csConfigType object.
--  RevDate
--    9903080000Z
--  RevDescr
--    Initial version of the MIB.

ciscoSonetMIBObjects OBJECT IDENTIFIER ::= { ciscoSonetMIB 1 }
csConfig        OBJECT IDENTIFIER ::= { ciscoSonetMIBObjects 1 }
csApsConfig     OBJECT IDENTIFIER ::= { ciscoSonetMIBObjects 2 }
csSection       OBJECT IDENTIFIER ::= { ciscoSonetMIBObjects 3 }
csLine          OBJECT IDENTIFIER ::= { ciscoSonetMIBObjects 4 }
csPath          OBJECT IDENTIFIER ::= { ciscoSonetMIBObjects 5 }
csStats         OBJECT IDENTIFIER ::= { ciscoSonetMIBObjects 6 }
ciscoSonetMIBConformance OBJECT IDENTIFIER ::= { ciscoSonetMIB 3 }
ciscoSonetMIBCompliances OBJECT IDENTIFIER ::= { ciscoSonetMIBConformance 1 }
ciscoSonetMIBGroups OBJECT IDENTIFIER ::= { ciscoSonetMIBConformance 2 }

csConfigTable OBJECT-TYPE
    SYNTAX SEQUENCE OF CsConfigEntry
    ACCESS not-accessible
    STATUS mandatory
    DESCRIPTION
        "The SONET/SDH configuration table. This table has objects 
         for configuring sonet lines."
    ::= { csConfig 1 }

csConfigEntry OBJECT-TYPE
    SYNTAX CsConfigEntry
    ACCESS not-accessible
    STATUS mandatory
    DESCRIPTION
        "An entry in the table. There is an entry for each SONET line 
         in the table. Entries are automatically created for an 
         ifType value of sonet(39). 'ifAdminStatus' from the ifTable 
         must be used to enable or disable a line. By default, the 
         line state is down."
    INDEX { ifIndex }
    ::= { csConfigTable 1 }

CsConfigEntry ::= SEQUENCE {
    csConfigLoopbackType INTEGER,
    csConfigXmtClockSource INTEGER,
    csConfigFrameScramble INTEGER,
    csConfigType INTEGER
    }

csConfigLoopbackType OBJECT-TYPE
    SYNTAX INTEGER {
        noLoopback(1),
        lineLocal(2),
        lineRemote(3)
        }
    ACCESS read-write
    STATUS mandatory
    DESCRIPTION
        "This object represents the desired loopback 
         configuration of the  SONET line.
         The Values mean:
        
         noLoopback :  
                 Not in the loopback state.  
         lineLocal : 
                 The sent signal at this line is looped back
                 through the device.
         lineRemote :
                 The sent signal does not go through the 
                 device but is looped back out."
    DEFVAL { noLoopback }
    ::= { csConfigEntry 1 }

csConfigXmtClockSource OBJECT-TYPE
    SYNTAX INTEGER {
        loopTiming(1),
        localTiming(2)
        }
    ACCESS read-write
    STATUS mandatory
    DESCRIPTION
        "The source of the transmit clock.
         
         loopTiming: indicates that the recovered receive 
                     clock is used as the transmit clock.
        
         localTiming: indicates that a local clock source is
                      used or that an external clock is 
                      attached to the box containing the 
                      interface. "
    DEFVAL { localTiming }
    ::= { csConfigEntry 2 }

csConfigFrameScramble OBJECT-TYPE
    SYNTAX INTEGER {
        disabled(1),
        enabled(2)
        }
    ACCESS read-write
    STATUS mandatory
    DESCRIPTION
        "This object is used to disable or enable the Scrambling
         option in SONET line. Please refer to GR-253-CORE for 
         frame scrambling."
    REFERENCE
        "GR-253-CORE"
    DEFVAL { enabled }
    ::= { csConfigEntry 3 }

csConfigType OBJECT-TYPE
    SYNTAX INTEGER {
        sonetSts3c(1),
        sonetStm1(2),
        sonetSts12c(3),
        sonetStm4(4),
        sonetSts48c(5),
        sonetStm16(6),
        sonetSts192c(7),
        sonetStm64(8)
        }
    ACCESS read-only
    STATUS mandatory
    DESCRIPTION
        "This object represents the configured line type.
         Sts is SONET format. Stm is SDH format. 
             sonetSts3c   : For OC3
             sonetStm1    : For European standard OC3
             sonetSts12c  : For OC12
             sonetStm4    : European standard OC12
             sonetSts48c  : OC48
             sonetStm16   : European standard OC48 
             sonetSts192c : OC-192
             sonetStm64   : European standard OC-192"
    ::= { csConfigEntry 4 }

csApsConfigTable OBJECT-TYPE
    SYNTAX SEQUENCE OF CsApsConfigEntry
    ACCESS not-accessible
    STATUS mandatory
    DESCRIPTION
        "This table contains objects to configure APS 
         (Automatic Protection Switching) feature in a SONET 
         Line. APS is the ability to configure a pair of SONET 
         lines for redundancy so that the hardware will 
         automatically switch the active line from working line
         to the protection line or vice versa, within 60ms, 
         when the active line fails."
    ::= { csApsConfig 1 }

csApsConfigEntry OBJECT-TYPE
    SYNTAX CsApsConfigEntry
    ACCESS not-accessible
    STATUS mandatory
    DESCRIPTION
        "An entry is created when an APS pair is configured.
         To create an entry, the following objects must be 
         specified:
         csApsWorkingIndex, csApsProtectionIndex, csApsEnable,  
         csApsArchMode. The protection line must not be active,
         i.e, ifAdminStatus must be 'down',  while configuring 
         APS. An entry is created by setting the value of 
         'csApsEnable' to csApsEnabled (2) and deleted by 
         setting it to csApsDisabled (1). Once a line is 
         configured as working line or protection line, it 
         remains in that role until APS is disabled on that 
         sonet line pair. It remains in the  working/protection 
         role even after the card is reset."
    INDEX { csApsWorkingIndex }
    ::= { csApsConfigTable 1 }

CsApsConfigEntry ::= SEQUENCE {
    csApsWorkingIndex InterfaceIndex,
    csApsProtectionIndex InterfaceIndex,
    csApsEnable INTEGER,
    csApsArchMode INTEGER,
    csApsActiveLine INTEGER,
    csApsSigFaultBER Gauge,
    csApsSigDegradeBER Gauge,
    csApsWaitToRestore Gauge,
    csApsDirection INTEGER,
    csApsRevertive INTEGER,
    csApsDirectionOperational INTEGER,
    csApsArchModeOperational INTEGER,
    csApsChannelProtocol INTEGER
    }

csApsWorkingIndex OBJECT-TYPE
    SYNTAX InterfaceIndex
--    Rsyntax INTEGER(1..2147483647)
    ACCESS not-accessible
    STATUS mandatory
    DESCRIPTION
        "When a pair of APS lines is configured, one line has
         to be the working line, which is the primary line,
         and the other has to be the protection line, which
         is the backup line. This object refers to the working line
         in the APS pair."
    ::= { csApsConfigEntry 1 }

csApsProtectionIndex OBJECT-TYPE
    SYNTAX InterfaceIndex
--    Rsyntax INTEGER(1..2147483647)
    ACCESS read-write
    STATUS mandatory
    DESCRIPTION
        "The protection line indicates that it will become
         the active line when an APS switch occurs (APS switch
         could occur because of a failure on the working line)."
    ::= { csApsConfigEntry 2 }

csApsEnable OBJECT-TYPE
    SYNTAX INTEGER {
        csApsDisabled(1),
        csApsEnabled(2)
        }
    ACCESS read-write
    STATUS mandatory
    DESCRIPTION
        "This object is used to enable or disable the APS feature
         on the working/protection line pairs. When enabled,
         the hardware will automatically switch the active line 
         from the working line to the protection line within 60ms,
         or vice versa."
    ::= { csApsConfigEntry 3 }

csApsArchMode OBJECT-TYPE
    SYNTAX INTEGER {
        onePlusOne(1),
        oneToOne(2),
        anexBOnePlusOne(3),
        ycableOnePlusOneNok1k2(4),
        straightOnePlusOneNok1k2(5)
        }
    ACCESS read-write
    STATUS mandatory
    DESCRIPTION
        "This object is used to configure APS architecture mode
         on the working/protection line pairs.
        
          All of the following are supported on single slot.
          oneToOne(2) is not  supported across 2 slots,i.e. the 
          working and protection slot numbers must be the same in 
          oneToOne(2).
        
          onePlusOne : This can be supported on the same card
          and across 2 cards.
          This mode means that the transmit and receive signals
          go only over the active line(which could be working or 
          protection line). (straight cable implied)
        
          oneToOne : This is supported only on the same card
          This mode means that the transmit and receive signals
          go over the working and protection lines.
          (straight cable implied)
        
          anexBOnePlusOne : This can be supported on the same card
          and across 2 cards.
          This mode is like the onePlusOne mode, except that the
          'csApsDirection' can only be bi-directional.
          (straight cable implied)
        
          ycableOnePlusOneNok1k2: With Y-cable ignore K1K2 bytes.
          This mode is the Y-cable redundancy mode.
        
          straightOnePlusOneNok1k2 : With straight cable, ignore 
                                     K1K2 bytes. This mode is like
                                     onePlusOne, but with K1, K2 
                                     bytes ignored."
    ::= { csApsConfigEntry 4 }

csApsActiveLine OBJECT-TYPE
    SYNTAX INTEGER {
        csApsWorkingLine(1),
        csApsProtectionLine(2),
        csApsNone(3)
        }
    ACCESS read-only
    STATUS mandatory
    DESCRIPTION
        "This object indicates which line is currently active. 
         It could be the working line, the protection line or 
         none if neither working nor protection line is active. 
         This object reflects the status of receive direction."
    ::= { csApsConfigEntry 5 }

csApsSigFaultBER OBJECT-TYPE
    SYNTAX Gauge(3..5)
    ACCESS read-write
    STATUS mandatory
    DESCRIPTION
        "This object contains the Bit Error Rate threshold for
         Signal Fault detection on the working line. Once this
         threshold is exceeded, an APS switch will occur.
         This value is 10 to the -n, where n is between 3 and 5."
    DEFVAL { 3 }
    ::= { csApsConfigEntry 6 }

csApsSigDegradeBER OBJECT-TYPE
    SYNTAX Gauge(5..9)
    ACCESS read-write
    STATUS mandatory
    DESCRIPTION
        "This object contains the Bit Error Rate threshold for
         Signal Degrade detection on the working line. Once this
         threshold is exceeded, an APS switch will occur.
         This value is 10 to -n where n is between 5 and 9."
    DEFVAL { 5 }
    ::= { csApsConfigEntry 7 }

csApsWaitToRestore OBJECT-TYPE
    SYNTAX Gauge(1..12)
--  Units
--    minutes
    ACCESS read-write
    STATUS mandatory
    DESCRIPTION
        "This object contains interval in minutes to wait 
         before attempting to switch back to working line. 
         Not applicable if the line is configured in 
         non-revertive mode, i.e. protection line will 
         continue to be active, even if failures on the 
         working line are cleared. The framer clears the 
         signal-fault and signal-degrade when APS switch 
         occurs. Please refer to 'csApsRevertive' for 
         description of non-revertive."
    ::= { csApsConfigEntry 8 }

csApsDirection OBJECT-TYPE
    SYNTAX INTEGER {
        uniDirectional(1),
        biDirectional(2)
        }
    ACCESS read-write
    STATUS mandatory
    DESCRIPTION
        "This object is used to configure the switching 
         direction which this APS line supports. 
        
         Unidirectional : APS switch only in one direction.
         Bidirectional  : APS switch in both ends of the line."
    ::= { csApsConfigEntry 9 }

csApsRevertive OBJECT-TYPE
    SYNTAX INTEGER {
        nonrevertive(1),
        revertive(2)
        }
    ACCESS read-write
    STATUS mandatory
    DESCRIPTION
        "This object is used to configure the APS revertive or
         nonrevertive option. 
        
         revertive : 
           Will switch the working line back to active state after
           the Wait-To-restore interval has expired and the 
           working line Signal-Fault/Signal-Degrade has been 
           cleared. Please refer to 'csApsWaitToRestore' for 
           description of Wait-To-Restore interval.
         nonrevertive : 
           The  protection line continues to be the active line,
           The active line does not switch to the working line."
    ::= { csApsConfigEntry 10 }

csApsDirectionOperational OBJECT-TYPE
    SYNTAX INTEGER {
        uniDirectional(1),
        biDirectional(2)
        }
    ACCESS read-only
    STATUS mandatory
    DESCRIPTION
        "This object shows the actual APS direction that is 
         implemented on the Near End terminal. APS direction 
         configured through csApsDirection is negotiated with
         the Far End and APS direction setting acceptable to 
         both ends is operational at the Near End."
    ::= { csApsConfigEntry 11 }

csApsArchModeOperational OBJECT-TYPE
    SYNTAX INTEGER {
        onePlusOne(1),
        oneToOne(2),
        anexBOnePlusOne(3),
        ycableOnePlusOneNok1k2(4),
        straightOnePlusOneNok1k2(5)
        }
    ACCESS read-only
    STATUS mandatory
    DESCRIPTION
        "This object shows the actual APS architecture mode that
         is implemented on the Near End terminal. APS architecture
         mode configured through csApsArchMode object is 
         negotiated with the Far End through APS channel. 
         Architecture mode acceptable to both the Near End and 
         the Far End terminals is then operational at the Near 
         End. This value can be different than the APS 
         Architecture mode configured."
    ::= { csApsConfigEntry 12 }

csApsChannelProtocol OBJECT-TYPE
    SYNTAX INTEGER {
        bellcore(1),
        itu(2)
        }
    ACCESS read-write
    STATUS mandatory
    DESCRIPTION
        "This object allows to configure APS channel protocol to 
         be implemented at Near End terminal.
        
         K1 and K2 overhead bytes in a SONET signal are used as
         an APS channel.
         This channel is used to carry APS protocol.
        
         Possible values:
         bellcore(1) : Implements APS channel protocol as defined
                       in bellcore document GR-253-CORE.
         itu(2) : Implements APS channel protocol as defined in 
                  ITU document G.783, Annex A."
    REFERENCE
        "GR-253-CORE, G.783"
    ::= { csApsConfigEntry 13 }

csApsLineFailureCode OBJECT-TYPE
    SYNTAX INTEGER {
        csApsChannelMismatch(1),
        csApsProtectionByteFail(2),
        csApsFEProtectionFailure(3)
        }
    ACCESS read-only
    STATUS mandatory
    DESCRIPTION
        "The Sonet APS line failure code - this is the failure 
         encountered by the APS line. 
        
         csApsChannelMismatch: trasmitted K1 byte and
                               received K2 byte do not match.
         csApsProtectionByteFail: It could mean either K1 byte 
                                  with invalid type of switch 
                                  request bits was received, or,  
                                  priority of received K1 byte 
                                  is lower than the transmitted 
                                  K1 byte.
         csApsFEProtectionFailure: Remote end error detected."
    REFERENCE
        "GR-253-CORE"
    ::= { csApsConfig 2 }

csApsLineSwitchReason OBJECT-TYPE
    SYNTAX INTEGER {
        csApsOther(1),
        csApsRevertive(2),
        csApsManual(3),
        csApsSignalDefectLow(4),
        csApsSignalDefectHigh(5),
        csApsSignalFailureLow(6),
        csApsSignalFailureHigh(7),
        csApsForceSwitch(8),
        csApsLockOut(9)
        }
    ACCESS read-only
    STATUS mandatory
    DESCRIPTION
        "The reason why APS switch happened. When the working
         line on one end fails, its other end is told to do
         an  APS switch. The following options in the increasing
         order of priority indicate what type of switch request 
         it is. 
        
        csApsRevertive : Switch back to working line after the 
          Wait-to-Restore interval is over, and failures are 
          cleared. It is the lowest priority.
        csApsManual : Manual switch causes APS switch unless a 
          request of equal or higher priority is in effect.
        csApsSignalDefectLow : Switch happened because threshold 
          for 'csApsSigFaultBER' was exceeded. 
        csApsSignalDefectHigh : Same as above, but higher priority.
        csApsSignalFailureLow : Switch happened because threshold 
          for 'csApsSigDegradeBER' was exceeded. 
        csApsSignalFailureHigh : Same as above, but higher 
          priority.
        csApsForceSwitch : Forced switch forces hardware to switch
          the active line even if the other line (could be 
          working line or protection line) is in alarm.
        csApsLockOut : This is the highest priority switch. This
          will override all other requests. "
    ::= { csApsConfig 3 }

cssTotalTable OBJECT-TYPE
    SYNTAX SEQUENCE OF CssTotalEntry
    ACCESS not-accessible
    STATUS mandatory
    DESCRIPTION
        "The SONET/SDH Section Total table. It contains the 
         cumulative sum of the various statistics for the 24 hour
         period preceding the current interval. The object 
         'sonetMediumValidIntervals' from RFC2558 contains the
         number of 15 minute intervals that have elapsed since
         the line is enabled. "
    ::= { csSection 1 }

cssTotalEntry OBJECT-TYPE
    SYNTAX CssTotalEntry
    ACCESS not-accessible
    STATUS mandatory
    DESCRIPTION
        "An entry in the SONET/SDH Section Total table. Entries
         are created automatically for sonet lines."
    INDEX { ifIndex }
    ::= { cssTotalTable 1 }

CssTotalEntry ::= SEQUENCE {
    cssTotalESs Gauge,
    cssTotalSESs Gauge,
    cssTotalSEFSs Gauge,
    cssTotalCVs Gauge
    }

cssTotalESs OBJECT-TYPE
    SYNTAX Gauge
--  Units
--    errored seconds
    ACCESS read-only
    STATUS mandatory
    DESCRIPTION
        "The number of Errored Seconds encountered by a SONET/SDH
         Section in the last 24 hours."
    REFERENCE
        " RFC2558 "
    ::= { cssTotalEntry 1 }

cssTotalSESs OBJECT-TYPE
    SYNTAX Gauge
--  Units
--    severely errored seconds
    ACCESS read-only
    STATUS mandatory
    DESCRIPTION
        "The number of Severely Errored Seconds encountered by a 
         SONET/SDH Section in the last 24 hours."
    REFERENCE
        " RFC2558 "
    ::= { cssTotalEntry 2 }

cssTotalSEFSs OBJECT-TYPE
    SYNTAX Gauge
--  Units
--    severely errored framing seconds
    ACCESS read-only
    STATUS mandatory
    DESCRIPTION
        "The number of Severely Errored Framing Seconds 
         encountered by a SONET/SDH Section in the last 24 hours."
    REFERENCE
        " RFC2558 "
    ::= { cssTotalEntry 3 }

cssTotalCVs OBJECT-TYPE
    SYNTAX Gauge
--  Units
--    coding violations
    ACCESS read-only
    STATUS mandatory
    DESCRIPTION
        "The number of Coding Violations encountered by a 
         SONET/SDH Section in the last 24 hours."
    REFERENCE
        " RFC2558 "
    ::= { cssTotalEntry 4 }

cssTraceTable OBJECT-TYPE
    SYNTAX SEQUENCE OF CssTraceEntry
    ACCESS not-accessible
    STATUS mandatory
    DESCRIPTION
        "The SONET/SDH Section Trace table. This table contains 
         objects for tracing the sonet section."
    ::= { csSection 2 }

cssTraceEntry OBJECT-TYPE
    SYNTAX CssTraceEntry
    ACCESS not-accessible
    STATUS mandatory
    DESCRIPTION
        "An entry in the trace table. Entries exist for active sonet
         lines. The objects in this table are used to verify 
         continued connection between the two ends of the line."
    INDEX { ifIndex }
    ::= { cssTraceTable 1 }

CssTraceEntry ::= SEQUENCE {
    cssTraceToTransmit OCTET STRING,
    cssTraceToExpect OCTET STRING,
    cssTraceFailure TruthValue,
    cssTraceReceived OCTET STRING
    }

cssTraceToTransmit OBJECT-TYPE
    SYNTAX OCTET STRING(SIZE(0|16|64))
    ACCESS read-write
    STATUS mandatory
    DESCRIPTION
        "Sonet Section Trace To Transmit. This is string that
         is transmitted to perform Sonet section trace 
         diagnostics. The trace string is  repetitively 
         transmited so that a trace receiving terminal can 
         verify its continued connection to the intended 
         transmitter. The default value is a zero-length string.
         Unless this object is set to a non-zero length string, 
         tracing will not be performed."
    REFERENCE
        "GR-253-CORE"
    ::= { cssTraceEntry 1 }

cssTraceToExpect OBJECT-TYPE
    SYNTAX OCTET STRING(SIZE(0|16|64))
    ACCESS read-write
    STATUS mandatory
    DESCRIPTION
        "Sonet Section Trace To Expect. The receiving terminal 
         verifies if the incoming string matches this string. 
         The value of 'cssTraceFailure' indicates whether a 
         trace mismatch occurred. The default value is a 
         zero-length string."
    REFERENCE
        "GR-253-CORE"
    ::= { cssTraceEntry 2 }

cssTraceFailure OBJECT-TYPE
    SYNTAX TruthValue
--    Rsyntax INTEGER {
--        true(1),
--        false(2)
--        }
    ACCESS read-only
    STATUS mandatory
    DESCRIPTION
        "The value of this object is set to 'true' when Sonet 
         Section received trace does not match the 
         'cssTraceToExpect'."
    REFERENCE
        "GR-253-CORE"
    ::= { cssTraceEntry 3 }

cssTraceReceived OBJECT-TYPE
    SYNTAX OCTET STRING(SIZE(0|16|64))
    ACCESS read-only
    STATUS mandatory
    DESCRIPTION
        "This object is used to view the Sonet Section Trace that 
         is received by the receiving terminal."
    REFERENCE
        "GR-253-CORE"
    ::= { cssTraceEntry 4 }

cslTotalTable OBJECT-TYPE
    SYNTAX SEQUENCE OF CslTotalEntry
    ACCESS not-accessible
    STATUS mandatory
    DESCRIPTION
        "The SONET/SDH Line Total table. It contains the 
         cumulative sum of the various statistics for the 24 
         hour period preceding the current interval. The object 
         'sonetMediumValidIntervals' from RFC2558 contains the 
         number of 15 minute intervals that have elapsed since
         the line is enabled."
    ::= { csLine 1 }

cslTotalEntry OBJECT-TYPE
    SYNTAX CslTotalEntry
    ACCESS not-accessible
    STATUS mandatory
    DESCRIPTION
        "An entry in the SONET/SDH Line Total table. Entries
         are created automatically for sonet lines."
    INDEX { ifIndex }
    ::= { cslTotalTable 1 }

CslTotalEntry ::= SEQUENCE {
    cslTotalESs Gauge,
    cslTotalSESs Gauge,
    cslTotalCVs Gauge,
    cslTotalUASs Gauge
    }

cslTotalESs OBJECT-TYPE
    SYNTAX Gauge
--  Units
--    errored seconds
    ACCESS read-only
    STATUS mandatory
    DESCRIPTION
        "The number of Errored Seconds encountered by a SONET/SDH
         Line in the last 24 hours."
    ::= { cslTotalEntry 1 }

cslTotalSESs OBJECT-TYPE
    SYNTAX Gauge
--  Units
--    severely errored seconds
    ACCESS read-only
    STATUS mandatory
    DESCRIPTION
        "The number of Severely Errored Seconds encountered by a 
         SONET/SDH Line in the last 24 hours."
    REFERENCE
        " RFC2558 "
    ::= { cslTotalEntry 2 }

cslTotalCVs OBJECT-TYPE
    SYNTAX Gauge
--  Units
--    coding violations
    ACCESS read-only
    STATUS mandatory
    DESCRIPTION
        "The number of Coding Violations encountered by a 
         SONET/SDH Line in the last 24 hours."
    REFERENCE
        " RFC2558 "
    ::= { cslTotalEntry 3 }

cslTotalUASs OBJECT-TYPE
    SYNTAX Gauge
--  Units
--    unavailable seconds
    ACCESS read-only
    STATUS mandatory
    DESCRIPTION
        "The number of Unavailable Seconds encountered by a 
         SONET/SDH Line in the last 24 hours."
    REFERENCE
        " RFC2558 "
    ::= { cslTotalEntry 4 }

cslFarEndTotalTable OBJECT-TYPE
    SYNTAX SEQUENCE OF CslFarEndTotalEntry
    ACCESS not-accessible
    STATUS mandatory
    DESCRIPTION
        "The SONET/SDH Far End Line Total table. It contains the 
         cumulative sum of the various statistics for the 24 hour 
         period preceding the current interval. The object 
         'sonetMediumValidIntervals' from RFC2558 contains the 
         number of 15 minute intervals that have elapsed since the 
         line is enabled."
    ::= { csLine 2 }

cslFarEndTotalEntry OBJECT-TYPE
    SYNTAX CslFarEndTotalEntry
    ACCESS not-accessible
    STATUS mandatory
    DESCRIPTION
        "An entry in the SONET/SDH Far End Line Total table. Entries
         are created automatically for sonet lines."
    INDEX { ifIndex }
    ::= { cslFarEndTotalTable 1 }

CslFarEndTotalEntry ::= SEQUENCE {
    cslFarEndTotalESs Gauge,
    cslFarEndTotalSESs Gauge,
    cslFarEndTotalCVs Gauge,
    cslFarEndTotalUASs Gauge
    }

cslFarEndTotalESs OBJECT-TYPE
    SYNTAX Gauge
--  Units
--    errored seconds
    ACCESS read-only
    STATUS mandatory
    DESCRIPTION
        "The number of Errored Seconds encountered by a SONET/SDH Far
         End Line in the last 24 hours."
    REFERENCE
        " RFC2558 "
    ::= { cslFarEndTotalEntry 1 }

cslFarEndTotalSESs OBJECT-TYPE
    SYNTAX Gauge
--  Units
--    severely errored seconds
    ACCESS read-only
    STATUS mandatory
    DESCRIPTION
        "The number of Severely Errored Seconds encountered by a 
         SONET/SDH Far End Line in the last 24 hours."
    REFERENCE
        " RFC2558 "
    ::= { cslFarEndTotalEntry 2 }

cslFarEndTotalCVs OBJECT-TYPE
    SYNTAX Gauge
--  Units
--    coding violations
    ACCESS read-only
    STATUS mandatory
    DESCRIPTION
        "The number of Coding Violations encountered by a SONET/SDH 
         Far End Line in the last 24 hours."
    REFERENCE
        " RFC2558 "
    ::= { cslFarEndTotalEntry 3 }

cslFarEndTotalUASs OBJECT-TYPE
    SYNTAX Gauge
--  Units
--    unavailable seconds
    ACCESS read-only
    STATUS mandatory
    DESCRIPTION
        "The number of Unavailable Seconds encountered by a 
         SONET/SDH Far End Line in the last 24 hours."
    REFERENCE
        " RFC2558 "
    ::= { cslFarEndTotalEntry 4 }

cspTotalTable OBJECT-TYPE
    SYNTAX SEQUENCE OF CspTotalEntry
    ACCESS not-accessible
    STATUS mandatory
    DESCRIPTION
        "The SONET/SDH Path Total table. It contains the cumulative 
         sum of the various statistics for the 24 hour period 
         preceding the current interval.The object 
         'sonetMediumValidIntervals' from RFC2558 contains the number
         of 15 minute intervals that have elapsed since the line is 
         enabled."
    ::= { csPath 1 }

cspTotalEntry OBJECT-TYPE
    SYNTAX CspTotalEntry
    ACCESS not-accessible
    STATUS mandatory
    DESCRIPTION
        "An entry in the SONET/SDH Path Total table. Entries
         are created automatically for sonet lines."
    INDEX { ifIndex }
    ::= { cspTotalTable 1 }

CspTotalEntry ::= SEQUENCE {
    cspTotalESs Gauge,
    cspTotalSESs Gauge,
    cspTotalCVs Gauge,
    cspTotalUASs Gauge
    }

cspTotalESs OBJECT-TYPE
    SYNTAX Gauge
--  Units
--    errored seconds
    ACCESS read-only
    STATUS mandatory
    DESCRIPTION
        "The number of Errored Seconds encountered by a SONET/SDH
         Path in the last 24 hours."
    REFERENCE
        " RFC2558 "
    ::= { cspTotalEntry 1 }

cspTotalSESs OBJECT-TYPE
    SYNTAX Gauge
--  Units
--    severely errored seconds
    ACCESS read-only
    STATUS mandatory
    DESCRIPTION
        "The number of Severely Errored Seconds encountered by a 
         SONET/SDH Path in the last 24 hours."
    REFERENCE
        " RFC2558 "
    ::= { cspTotalEntry 2 }

cspTotalCVs OBJECT-TYPE
    SYNTAX Gauge
--  Units
--    coding violations
    ACCESS read-only
    STATUS mandatory
    DESCRIPTION
        "The number of Coding Violations encountered by a 
         SONET/SDH Path in the last 24 hours."
    REFERENCE
        " RFC2558 "
    ::= { cspTotalEntry 3 }

cspTotalUASs OBJECT-TYPE
    SYNTAX Gauge
--  Units
--    unavailable seconds
    ACCESS read-only
    STATUS mandatory
    DESCRIPTION
        "The number of Unavailable Seconds encountered by a 
         SONET/SDH Path in the last 24 hours."
    REFERENCE
        " RFC2558 "
    ::= { cspTotalEntry 4 }

cspFarEndTotalTable OBJECT-TYPE
    SYNTAX SEQUENCE OF CspFarEndTotalEntry
    ACCESS not-accessible
    STATUS mandatory
    DESCRIPTION
        "The SONET/SDH Far End Path Total table. Far End is the 
         remote end of the line. The table contains the cumulative
         sum of the various statistics for the 24 hour period 
         preceding the current interval. The object 
         'sonetMediumValidIntervals' from RFC2558 contains the
         number of 15 minute intervals that have elapsed since
         the line is enabled. "
    ::= { csPath 2 }

cspFarEndTotalEntry OBJECT-TYPE
    SYNTAX CspFarEndTotalEntry
    ACCESS not-accessible
    STATUS mandatory
    DESCRIPTION
        "An entry in the SONET/SDH Far End Path Total table. 
         Entries are created automatically for sonet lines."
    INDEX { ifIndex }
    ::= { cspFarEndTotalTable 1 }

CspFarEndTotalEntry ::= SEQUENCE {
    cspFarEndTotalESs Gauge,
    cspFarEndTotalSESs Gauge,
    cspFarEndTotalCVs Gauge,
    cspFarEndTotalUASs Gauge
    }

cspFarEndTotalESs OBJECT-TYPE
    SYNTAX Gauge
--  Units
--    errored seconds
    ACCESS read-only
    STATUS mandatory
    DESCRIPTION
        "The number of Errored Seconds encountered by a SONET/SDH
         far end path in the last 24 hours."
    REFERENCE
        " RFC2558 "
    ::= { cspFarEndTotalEntry 1 }

cspFarEndTotalSESs OBJECT-TYPE
    SYNTAX Gauge
--  Units
--    severely errored seconds
    ACCESS read-only
    STATUS mandatory
    DESCRIPTION
        "The number of Severely Errored Seconds encountered by a 
         SONET/SDH far end path in the last 24 hours."
    REFERENCE
        " RFC2558 "
    ::= { cspFarEndTotalEntry 2 }

cspFarEndTotalCVs OBJECT-TYPE
    SYNTAX Gauge
--  Units
--    coding violations
    ACCESS read-only
    STATUS mandatory
    DESCRIPTION
        "The number of Coding Violations encountered by a 
         SONET/SDH far end path in the last 24 hours."
    REFERENCE
        " RFC2558 "
    ::= { cspFarEndTotalEntry 3 }

cspFarEndTotalUASs OBJECT-TYPE
    SYNTAX Gauge
--  Units
--    unavailable seconds
    ACCESS read-only
    STATUS mandatory
    DESCRIPTION
        "The number of Unavailable Seconds encountered by a 
         SONET/SDH far end path in the last 24 hours."
    REFERENCE
        " RFC2558 "
    ::= { cspFarEndTotalEntry 4 }

cspTraceTable OBJECT-TYPE
    SYNTAX SEQUENCE OF CspTraceEntry
    ACCESS not-accessible
    STATUS mandatory
    DESCRIPTION
        "The SONET/SDH Path Trace table. This table contains objects 
         for tracing the sonet path."
    ::= { csPath 3 }

cspTraceEntry OBJECT-TYPE
    SYNTAX CspTraceEntry
    ACCESS not-accessible
    STATUS mandatory
    DESCRIPTION
        "An entry in the SONET/SDH Path Trace table. The entries 
         exist for active sonet lines. The objects in this table are 
         used to verify continued connection between the two ends of
         the line."
    INDEX { ifIndex }
    ::= { cspTraceTable 1 }

CspTraceEntry ::= SEQUENCE {
    cspTraceToTransmit OCTET STRING,
    cspTraceToExpect OCTET STRING,
    cspTraceFailure TruthValue,
    cspTraceReceived OCTET STRING
    }

cspTraceToTransmit OBJECT-TYPE
    SYNTAX OCTET STRING(SIZE(0|16|64))
    ACCESS read-write
    STATUS mandatory
    DESCRIPTION
        "Sonet Path Trace To Transmit. The trace string is 
         repetitively transmited so that a trace receiving terminal 
         can verify its continued receiving terminal can verify its 
         continued connection to the intended transmitter. The 
         default value is a zero-length string. Unless this object 
         is set to a non-zero length string, tracing will not be 
         performed."
    REFERENCE
        "GR-253-CORE"
    ::= { cspTraceEntry 1 }

cspTraceToExpect OBJECT-TYPE
    SYNTAX OCTET STRING(SIZE(0|16|64))
    ACCESS read-write
    STATUS mandatory
    DESCRIPTION
        "Sonet Path Trace To Expect.  The receiving terminal verifies
         if the incoming string matches this string. The value of 
         'cspTraceFailure' indicates whether a trace mismatch 
         occured. The default value is a zero-length string."
    REFERENCE
        "GR-253-CORE"
    ::= { cspTraceEntry 2 }

cspTraceFailure OBJECT-TYPE
    SYNTAX TruthValue
--    Rsyntax INTEGER {
--        true(1),
--        false(2)
--        }
    ACCESS read-only
    STATUS mandatory
    DESCRIPTION
        "The value of this object is set to 'true' when Sonet Path 
         received trace does not match the 'cspTraceToExpect'."
    REFERENCE
        "GR-253-CORE"
    ::= { cspTraceEntry 3 }

cspTraceReceived OBJECT-TYPE
    SYNTAX OCTET STRING(SIZE(0|16|64))
    ACCESS read-only
    STATUS mandatory
    DESCRIPTION
        "This object is used to view the Sonet Path Trace that is
         received by the receiving terminal."
    REFERENCE
        "GR-253-CORE"
    ::= { cspTraceEntry 4 }

csStatsTable OBJECT-TYPE
    SYNTAX SEQUENCE OF CsStatsEntry
    ACCESS not-accessible
    STATUS mandatory
    DESCRIPTION
        "The SONET/SDH Section statistics table. This table 
         maintains the number of times the line encountered Loss of
         Signal(LOS), Loss of frame(LOF), Alarm Indication 
         signals(AISs), Remote failure indications(RFIs)."
    ::= { csStats 1 }

csStatsEntry OBJECT-TYPE
    SYNTAX CsStatsEntry
    ACCESS not-accessible
    STATUS mandatory
    DESCRIPTION
        "An entry in the SONET/SDH statistics table. These are 
         realtime statistics for the Sonet section, line and path
         layers. The statistics are gathered for each sonet line. 
         An entry is created automatically and is indexed by 
         ifIndex."
    INDEX { ifIndex }
    ::= { csStatsTable 1 }

CsStatsEntry ::= SEQUENCE {
    cssLOSs Counter,
    cssLOFs Counter,
    cslAISs Counter,
    cslRFIs Counter,
    cspAISs Counter,
    cspRFIs Counter
    }

cssLOSs OBJECT-TYPE
    SYNTAX Counter
--  Units
--    loss of signals
    ACCESS read-only
    STATUS mandatory
    DESCRIPTION
        "The number of Loss of signals(LOS) encountered by a 
         SONET/SDH Section. A high value for this object may 
         indicate a problem with the Sonet Section layer."
    REFERENCE
        " RFC2558 "
    ::= { csStatsEntry 1 }

cssLOFs OBJECT-TYPE
    SYNTAX Counter
--  Units
--    loss of frames
    ACCESS read-only
    STATUS mandatory
    DESCRIPTION
        "The number of Loss of Frames (LOF) encountered by a 
         SONET/SDH Section. A high value for this object may 
         indicate a problem with the Sonet Section layer."
    REFERENCE
        " RFC2558 "
    ::= { csStatsEntry 2 }

cslAISs OBJECT-TYPE
    SYNTAX Counter
--  Units
--    alarm indication signals
    ACCESS read-only
    STATUS mandatory
    DESCRIPTION
        "The number of alarm indication signals(AIS)  encountered by 
         a SONET/SDH Line. A high value for this object may indicate a
         problem with the Sonet Line layer."
    REFERENCE
        " RFC2558 "
    ::= { csStatsEntry 3 }

cslRFIs OBJECT-TYPE
    SYNTAX Counter
--  Units
--    remote failure indications
    ACCESS read-only
    STATUS mandatory
    DESCRIPTION
        "The number of remote failure indications (RFI) encountered 
         by a SONET/SDH Line. A high value for this object may 
         indicate a problem with the Sonet Line layer."
    REFERENCE
        " RFC2558 "
    ::= { csStatsEntry 4 }

cspAISs OBJECT-TYPE
    SYNTAX Counter
--  Units
--    alarm indication signals
    ACCESS read-only
    STATUS mandatory
    DESCRIPTION
        "The  number of alarm indication signals (AIS) encountered
         by a SONET/SDH Path. A high value for this object may 
         indicate a problem with the Sonet Path layer."
    REFERENCE
        " RFC2558 "
    ::= { csStatsEntry 5 }

cspRFIs OBJECT-TYPE
    SYNTAX Counter
--  Units
--    remote failure indications
    ACCESS read-only
    STATUS mandatory
    DESCRIPTION
        "The number of  remote failure indications (RFI) 
         encountered by a SONET/SDH Path. A high value for this 
         object may indicate a problem with the Sonet Path layer."
    REFERENCE
        " RFC2558 "
    ::= { csStatsEntry 6 }

ciscoSonetConfMIBGroup OBJECT IDENTIFIER ::= { ciscoSonetMIBGroups 1 }
-- OBJECT-GROUP
--  Status
--    mandatory
--  Descr
--    Objects used for configuring Sonet lines.
--  objects
--    csConfigLoopbackType, csConfigXmtClockSource, 
--    csConfigFrameScramble, csConfigType

ciscoSonetStatsMIBGroup OBJECT IDENTIFIER ::= { ciscoSonetMIBGroups 2 }
-- OBJECT-GROUP
--  Status
--    mandatory
--  Descr
--    These are objects related to Sonet line statistics.
--  objects
--    cssTotalESs, cssTotalSESs, cssTotalSEFSs, cssTotalCVs, 
--    cssLOSs, cssLOFs, cslAISs, cslRFIs, cspAISs, cspRFIs, 
--    cslTotalESs, cslTotalSESs, cslTotalCVs, cslTotalUASs, 
--    cslFarEndTotalESs, cslFarEndTotalSESs, cslFarEndTotalCVs, 
--    cslFarEndTotalUASs, cspTotalESs, cspTotalSESs, cspTotalCVs, 
--    cspTotalUASs, cspFarEndTotalESs, cspFarEndTotalSESs, 
--    cspFarEndTotalCVs, cspFarEndTotalUASs

ciscoSonetTraceMIBGroup OBJECT IDENTIFIER ::= { ciscoSonetMIBGroups 3 }
-- OBJECT-GROUP
--  Status
--    mandatory
--  Descr
--    Objects related to Sonet line connectivity.
--  objects
--    cssTraceToTransmit, cssTraceToExpect, cssTraceFailure, 
--    cssTraceReceived, cspTraceToTransmit, cspTraceToExpect, 
--    cspTraceFailure, cspTraceReceived

ciscoSonetApsMIBGroup OBJECT IDENTIFIER ::= { ciscoSonetMIBGroups 4 }
-- OBJECT-GROUP
--  Status
--    mandatory
--  Descr
--    Objects used for configuring APS over Sonet lines.
--  objects
--    csApsProtectionIndex, csApsEnable, csApsArchMode, 
--    csApsActiveLine, csApsSigFaultBER, csApsSigDegradeBER, 
--    csApsWaitToRestore, csApsDirection, csApsRevertive, 
--    csApsLineFailureCode, csApsLineSwitchReason, 
--    csApsDirectionOperational, csApsArchModeOperational, 
--    csApsChannelProtocol

ciscoSonetMIBCompliance OBJECT IDENTIFIER ::= { ciscoSonetMIBCompliances 1 }
-- MODULE-COMPLIANCE
--  Status
--    mandatory
--  Descr
--    The Compliance statement for ciscoSonet management group.
--  Module
--    >>current<<
--   MandGroup
--    ciscoSonetConfMIBGroup
--   MandGroup
--    ciscoSonetStatsMIBGroup
--   MandGroup
--    ciscoSonetTraceMIBGroup
--   OptGroup
--    ciscoSonetApsMIBGroup
--   ObjVar
--    cssTraceReceived
--   ObjVar
--    cspTraceReceived


END
