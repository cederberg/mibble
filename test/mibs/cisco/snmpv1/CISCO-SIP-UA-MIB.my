-- MIB file created 27-Feb-2002 15:12:34, by
--   SMICng version 2.2.11-beta(PRO)(Solaris), January 20, 2001. Enterprise key cisco.com

CISCO-SIP-UA-MIB DEFINITIONS ::= BEGIN

-- From file: "CISCO-SIP-UA-MIB.my"
-- Compile options "4 7 F H N W 03 06 0B 0G 0N 0T"

IMPORTS
    SnmpAdminString
            FROM SNMP-FRAMEWORK-MIB
    ciscoMgmt
            FROM CISCO-SMI
    Counter
            FROM RFC1155-SMI
    OBJECT-TYPE
            FROM RFC-1212;

ciscoSipUaMIB OBJECT IDENTIFIER ::= { ciscoMgmt 152 }
-- MODULE-IDENTITY
--  LastUpdated
--    200103020000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-sip@cisco.com
--  Descr
--    Cisco User Agent Session Initiation Protocol (SIP) 
--     MIB module.  SIP is an application-layer signalling
--     protocol for creating, modifying and terminating
--     multimedia sessions with one or more participants.
--     These sessions include Internet multimedia conferences
--     and Internet telephone calls.  SIP is defined in 
--     RFC 2543 (March 1999).  
--    
--     This MIB is defined for the management of SIP User 
--     Agents (UAs).  A User Agent is an application which 
--     contains both a User Agent Client (UAC) and a User 
--     Agent Server (UAS).   A UAC is an application that 
--     initiates a SIP request.  A UAS is an application that 
--     contacts the user when a SIP request is received and 
--     that returns a response on behalf of the user.  The 
--     response accepts, rejects, or redirects the request.
--    
--     A SIP transaction occurs between a client and a server 
--     and comprises all messages from the first request sent
--     from the client to the server up to a final (non-1xx) 
--     response sent from the server to the client.
--  RevDate
--    200103020000Z
--  RevDescr
--    Addition of the following objects:
--       cSipCfgMaxForwards
--       cSipCfgTimerPrack
--       cSipCfgTimerComet
--       cSipCfgTimerReliableRsp
--       cSipCfgRetryPrack
--       cSipCfgRetryComet
--       cSipCfgRetryReliableRsp
--       cSipCfgOutSessionTransport
--       cSipCfgReliable1xxRspStr
--       cSipCfgReliable1xxRspHdr
--       cSipCfgUrlType
--       cSipCfgPeerTable
--           cSipCfgPeerIndex
--           cSipCfgPeerOutSessionTransport
--           cSipCfgPeerReliable1xxRspStr
--           cSipCfgPeerReliable1xxRspHdr
--           cSipCfgPeerUrlType
--       cSipStatsClientReqTermIns
--       cSipStatsClientReqTermOuts
--       cSipStatsClientNoAcceptHereIns
--       cSipStatsClientNoAcceptHereOuts
--       cSipStatsServerPrecondFailureIns
--       cSipStatsServerPrecondFailureOuts
--       cSipStatsTrafficCometIns
--       cSipStatsTrafficCometOuts
--       cSipStatsTrafficPrackIns
--       cSipStatsTrafficPrackOuts
--       cSipStatsRetryPrack
--       cSipStatsRetryComets
--       cSipStatsRetryReliable1xxRsps

ciscoSipUaMIBObjects OBJECT IDENTIFIER ::= { ciscoSipUaMIB 1 }
cSipCfg         OBJECT IDENTIFIER ::= { ciscoSipUaMIBObjects 1 }
cSipCfgBase     OBJECT IDENTIFIER ::= { cSipCfg 1 }
cSipCfgTimer    OBJECT IDENTIFIER ::= { cSipCfg 2 }
cSipCfgRetry    OBJECT IDENTIFIER ::= { cSipCfg 3 }
cSipCfgPeer     OBJECT IDENTIFIER ::= { cSipCfg 4 }
cSipStats       OBJECT IDENTIFIER ::= { ciscoSipUaMIBObjects 2 }
cSipStatsInfo   OBJECT IDENTIFIER ::= { cSipStats 1 }
cSipStatsSuccess OBJECT IDENTIFIER ::= { cSipStats 2 }
cSipStatsRedirect OBJECT IDENTIFIER ::= { cSipStats 3 }
cSipStatsErrClient OBJECT IDENTIFIER ::= { cSipStats 4 }
cSipStatsErrServer OBJECT IDENTIFIER ::= { cSipStats 5 }
cSipStatsGlobalFail OBJECT IDENTIFIER ::= { cSipStats 6 }
cSipStatsTraffic OBJECT IDENTIFIER ::= { cSipStats 7 }
cSipStatsRetry  OBJECT IDENTIFIER ::= { cSipStats 8 }
ciscoSipUaMIBConformance OBJECT IDENTIFIER ::= { ciscoSipUaMIB 3 }
ciscoSipUaMIBCompliances OBJECT IDENTIFIER ::= { ciscoSipUaMIBConformance 1 }
ciscoSipUaMIBGroups OBJECT IDENTIFIER ::= { ciscoSipUaMIBConformance 2 }

cSipCfgVersion OBJECT-TYPE
    SYNTAX SnmpAdminString
--    Rsyntax OCTET STRING(SIZE(0..255))
    ACCESS read-only
    STATUS mandatory
    DESCRIPTION
        "This object will reflect the version of SIP supported by this 
         user agent.  It will follow the same format as SIP version 
         information contained in the SIP messages generated by this
         user agent.  For example, user agents supporting SIP version 2
         will return 'SIP/2.0' as dictated by RFC 2543."
    ::= { cSipCfgBase 1 }

cSipCfgTransport OBJECT-TYPE
    SYNTAX INTEGER {
        udp(1),
        tcp(2),
        udpAndTcp(3),
        disabled(4)
        }
    ACCESS read-write
    STATUS mandatory
    DESCRIPTION
        "This object will specify the transport protocol the SIP user 
         agent will use to receive SIP messages.  A value of 'disabled'
         indicates that the UA will not receive any SIP messages."
    ::= { cSipCfgBase 2 }

cSipCfgUserLocationServerAddr OBJECT-TYPE
    SYNTAX SnmpAdminString
--    Rsyntax OCTET STRING(SIZE(0..255))
    ACCESS read-write
    STATUS mandatory
    DESCRIPTION
        "This object will specify address of the User Location 
         Server (ULS) being used to resolve the location of end 
         points.  This could be a Domain Name Server (DNS) or a 
         SIP proxy/redirect server.
        
         The format of the address follows the IETF service location 
         protocol. The syntax is as follows:
        
            mapping-type:type-specific-syntax
        
         the mapping-type specifies a scheme for mapping the matching 
         dial string to a target server. The type-specific-syntax is 
         exactly that, something that the particular mapping scheme can
         understand.  For example,
            Session target           Meaning
            ipv4:171.68.13.55:1006   The session target is the IP 
                                     version 4 address of 171.68.13.55 
                                     and port 1006.
            dns:pots.cisco.com       The session target is the IP host 
                                     with dns name pots.cisco.com.
        
         The valid Mapping type definitions for the peer follow:
            ipv4  - Syntax: ipv4:w.x.y.z:port or  ipv4:w.x.y.z 
            dns   - Syntax: dns:host.domain."
    ::= { cSipCfgBase 3 }

cSipCfgMaxForwards OBJECT-TYPE
    SYNTAX INTEGER(1..15)
    ACCESS read-write
    STATUS mandatory
    DESCRIPTION
        "This object may be used with any SIP method to limit the 
         number of proxies that can forward the request to the next 
         downstream server."
    ::= { cSipCfgBase 4 }

cSipCfgTimerTrying OBJECT-TYPE
    SYNTAX INTEGER(100..1000)
--  Units
--    milliseconds
    ACCESS read-write
    STATUS mandatory
    DESCRIPTION
        "This object specifies the time a user agent will wait to 
         receive a provisional response to a INVITE before resending 
         the INVITE."
    ::= { cSipCfgTimer 1 }

cSipCfgTimerExpires OBJECT-TYPE
    SYNTAX INTEGER(60000..300000)
--  Units
--    milliseconds
    ACCESS read-write
    STATUS mandatory
    DESCRIPTION
        "This object specifies the time a user agent will wait to 
         receive a final response to a INVITE before cancelling the 
         transaction."
    ::= { cSipCfgTimer 2 }

cSipCfgTimerConnect OBJECT-TYPE
    SYNTAX INTEGER(100..1000)
--  Units
--    milliseconds
    ACCESS read-write
    STATUS mandatory
    DESCRIPTION
        "This object specifies the time a user agent will wait to 
         receive an ACK confirmation a session is established."
    ::= { cSipCfgTimer 3 }

cSipCfgTimerDisconnect OBJECT-TYPE
    SYNTAX INTEGER(100..1000)
--  Units
--    milliseconds
    ACCESS read-write
    STATUS mandatory
    DESCRIPTION
        "This object specifies the time a user agent will wait to 
         receive an BYE confirmation a session is disconnected."
    ::= { cSipCfgTimer 4 }

cSipCfgTimerPrack OBJECT-TYPE
    SYNTAX INTEGER(100..1000)
--  Units
--    milliseconds
    ACCESS read-write
    STATUS mandatory
    DESCRIPTION
        "This object specifies the time a user agent will wait for 
         a final response before retransmitting the PRACK (PRovisional
         ACKnowledgment)."
    ::= { cSipCfgTimer 5 }

cSipCfgTimerComet OBJECT-TYPE
    SYNTAX INTEGER(100..1000)
--  Units
--    milliseconds
    ACCESS read-write
    STATUS mandatory
    DESCRIPTION
        "This object specifies the time a user agent will wait 
         for a final response before retransmitting the COMET 
         (COndition MET)."
    ::= { cSipCfgTimer 6 }

cSipCfgTimerReliableRsp OBJECT-TYPE
    SYNTAX INTEGER(100..1000)
--  Units
--    milliseconds
    ACCESS read-write
    STATUS mandatory
    DESCRIPTION
        "This object specifies the amount of time to wait for a
         PRACK before retransmitting the reliable 1xx response."
    ::= { cSipCfgTimer 7 }

cSipCfgRetryInvite OBJECT-TYPE
    SYNTAX INTEGER(1..10)
    ACCESS read-write
    STATUS mandatory
    DESCRIPTION
        "This object will specify the number of times a user agent 
         will retry sending a INVITE request."
    ::= { cSipCfgRetry 1 }

cSipCfgRetryBye OBJECT-TYPE
    SYNTAX INTEGER(1..10)
    ACCESS read-write
    STATUS mandatory
    DESCRIPTION
        "This object will specify the number of times a user agent 
         will retry sending a BYE request."
    ::= { cSipCfgRetry 2 }

cSipCfgRetryCancel OBJECT-TYPE
    SYNTAX INTEGER(1..10)
    ACCESS read-write
    STATUS mandatory
    DESCRIPTION
        "This object will specify the number of times a user agent 
         will retry sending a CANCEL request."
    ::= { cSipCfgRetry 3 }

cSipCfgRetryRegister OBJECT-TYPE
    SYNTAX INTEGER(1..10)
    ACCESS read-write
    STATUS mandatory
    DESCRIPTION
        "This object will specify the number of times a user agent 
         will retry sending a REGISTER request."
    ::= { cSipCfgRetry 4 }

cSipCfgRetryResponse OBJECT-TYPE
    SYNTAX INTEGER(1..10)
    ACCESS read-write
    STATUS mandatory
    DESCRIPTION
        "This object will specify the number of times a user agent 
         will retry sending a Response and expecting a ACK."
    ::= { cSipCfgRetry 5 }

cSipCfgRetryPrack OBJECT-TYPE
    SYNTAX INTEGER(1..10)
    ACCESS read-write
    STATUS mandatory
    DESCRIPTION
        "This object will specify the number of times a user agent 
         will retry sending a PRACK (PRovisional ACKnowledgement)."
    ::= { cSipCfgRetry 6 }

cSipCfgRetryComet OBJECT-TYPE
    SYNTAX INTEGER(1..10)
    ACCESS read-write
    STATUS mandatory
    DESCRIPTION
        "This object will specify the number of times a user agent 
         will retry sending a COMET (COndition MET)."
    ::= { cSipCfgRetry 7 }

cSipCfgRetryReliableRsp OBJECT-TYPE
    SYNTAX INTEGER(1..10)
    ACCESS read-write
    STATUS mandatory
    DESCRIPTION
        "This object will specify the number of times a user agent 
         will retry sending a reliable response."
    ::= { cSipCfgRetry 8 }

cSipCfgPeerTable OBJECT-TYPE
    SYNTAX SEQUENCE OF CSipCfgPeerEntry
    ACCESS not-accessible
    STATUS mandatory
    DESCRIPTION
        "This table contains per dial-peer SIP related 
         configuration.   
        
         The table is a sparse table of dial-peer information.
         This means, it only reflects dial-peers being used 
         for SIP.  A dial-peer is being used for SIP if the 
         value of cvVoIPPeerCfgSessionProtocol 
         (CISCO-VOICE-DIAL-CONTROL-MIB) is 'sip'.
        
         Dial-peers are not created or destroyed via this
         table.  Only SIP related configuration can be 
         performed via this table once the dial-peer exists
         in the system and is visible in this table."
    ::= { cSipCfgPeer 1 }

cSipCfgPeerEntry OBJECT-TYPE
    SYNTAX CSipCfgPeerEntry
    ACCESS not-accessible
    STATUS mandatory
    DESCRIPTION
        "A row in the cSipCfgPeerTable."
    INDEX { cSipCfgPeerIndex }
    ::= { cSipCfgPeerTable 1 }

CSipCfgPeerEntry ::= SEQUENCE {
    cSipCfgPeerIndex INTEGER,
    cSipCfgPeerOutSessionTransport INTEGER,
    cSipCfgPeerReliable1xxRspStr SnmpAdminString,
    cSipCfgPeerReliable1xxRspHdr INTEGER,
    cSipCfgPeerUrlType INTEGER
    }

cSipCfgPeerIndex OBJECT-TYPE
    SYNTAX INTEGER(1..2147483647)
    ACCESS not-accessible
    STATUS mandatory
    DESCRIPTION
        "An arbitrary index that uniquely identifies a 
         dial-peer configured for SIP."
    ::= { cSipCfgPeerEntry 1 }

cSipCfgPeerOutSessionTransport OBJECT-TYPE
    SYNTAX INTEGER {
        system(1),
        udp(2),
        tcp(3)
        }
    ACCESS read-write
    STATUS mandatory
    DESCRIPTION
        "This object specifies the session transport 
         protocol that will be used by this dial-peer
         for outbound SIP messages.  
        
         The value 'system' is the default and indicates 
         that this dial-peer should use the value set by 
         cSipCfgOutSessionTransport instead."
    DEFVAL { system }
    ::= { cSipCfgPeerEntry 2 }

cSipCfgPeerReliable1xxRspStr OBJECT-TYPE
    SYNTAX SnmpAdminString
--    Rsyntax OCTET STRING(SIZE(0..255))
    ACCESS read-write
    STATUS mandatory
    DESCRIPTION
        "This object specifies the string that will be 
         placed in either the Supported or Require SIP 
         header, as specified by cSipCfgPeerReliable1xxRspHdr."
    DEFVAL { "100rel" }
    ::= { cSipCfgPeerEntry 3 }

cSipCfgPeerReliable1xxRspHdr OBJECT-TYPE
    SYNTAX INTEGER {
        system(1),
        supported(2),
        require(3),
        disabled(4)
        }
    ACCESS read-write
    STATUS mandatory
    DESCRIPTION
        "This object specifies behavior with respect to
         Support or Require headers in SIP messages sent
         and received via this dial-peer.
        
         If the originating gateway is configured for 'require',
         the Require header is added to the outgoing INVITEs
         with the value of cSipCfgPeerReliable1xxStr.  This
         requires the use of reliable provisional responses by
         the terminating gateway.  Sessions will be torn down
         if this use cannot be supported by that gateway.
        
         If the originating gateway is configured for 'supported',
         the Supported header is added to the outgoing INVITEs
         with the value of cSipCfgPeerReliable1xxStr.  This 
         requires that an attempt to use reliable provisional
         responses be made, but sessions can continue without them.
        
         If the originating gateway is configured for 'disabled',
         the value of cSipCfgReliable1xxStr will NOT be added to
         either the Require or Supported headers of outgoing INVITEs.
        
         The value 'system' is the default and indicates that this 
         dial-peer should use the value of  cSipCfgReliable1xxRspHdr
         instead."
    DEFVAL { system }
    ::= { cSipCfgPeerEntry 4 }

cSipCfgPeerUrlType OBJECT-TYPE
    SYNTAX INTEGER {
        system(1),
        sip(2),
        tel(3)
        }
    ACCESS read-write
    STATUS mandatory
    DESCRIPTION
        "This object specifies the URL type sent in outbound
         INVITES generated by this device.
        
         The value 'system' is the default and indicates that this 
         dial-peer should use the value of cSipCfgUrlType instead."
    DEFVAL { system }
    ::= { cSipCfgPeerEntry 5 }

cSipCfgOutSessionTransport OBJECT-TYPE
    SYNTAX INTEGER {
        udp(1),
        tcp(2)
        }
    ACCESS read-write
    STATUS mandatory
    DESCRIPTION
        "This object specifies the session transport 
         protocol that will be used for outbound SIP 
         messages.  This configuration is applicable
         to all dial-peers in the system having 
         cSipCfgPeerOutSessionTransport set to 'system'."
    DEFVAL { udp }
    ::= { cSipCfgPeer 2 }

cSipCfgReliable1xxRspStr OBJECT-TYPE
    SYNTAX SnmpAdminString
--    Rsyntax OCTET STRING(SIZE(0..255))
    ACCESS read-write
    STATUS mandatory
    DESCRIPTION
        "This object specifies the string that will be 
         placed in either the Supported or Require SIP 
         header, as specified by cSipCfgReliable1xxRspHdr."
    DEFVAL { "100rel" }
    ::= { cSipCfgPeer 3 }

cSipCfgReliable1xxRspHdr OBJECT-TYPE
    SYNTAX INTEGER {
        supported(1),
        require(2),
        disabled(3)
        }
    ACCESS read-write
    STATUS mandatory
    DESCRIPTION
        "This object specifies behavior with respect to
         Supported or Require headers in SIP messages sent
         and received via this dial-peer.
        
         If the originating gateway is configured for 'require',
         the Require header is added to the outgoing INVITEs
         with the value of cSipCfgReliable1xxStr.  This
         requires the use of reliable provisional responses by
         the terminating gateway.  Sessions will be torn down
         if this use cannot be supported by that gateway.
        
         If the originating gateway is configured for 'supported',
         the Supported header is added to the outgoing INVITEs
         with the value of cSipCfgReliable1xxStr.  This 
         requires that an attempt to use reliable provisional
         responses be made, but sessions can continue without them.
        
         If the originating gateway is configured for 'disabled',
         the value of cSipCfgReliable1xxStr will NOT be added to
         either the Require or Supported headers of outgoing INVITEs."
    DEFVAL { supported }
    ::= { cSipCfgPeer 4 }

cSipCfgUrlType OBJECT-TYPE
    SYNTAX INTEGER {
        sip(1),
        tel(2)
        }
    ACCESS read-write
    STATUS mandatory
    DESCRIPTION
        "This object specifies the URL type sent in outbound
         INVITES generated by this device."
    DEFVAL { sip }
    ::= { cSipCfgPeer 5 }

cSipStatsInfoTryingIns OBJECT-TYPE
    SYNTAX Counter
    ACCESS read-only
    STATUS mandatory
    DESCRIPTION
        "This object reflects the total number of Trying
         (100) responses received by the user agent.  
         Trying responses indicate that some unspecified
         action is being taken on behalf of this call, but
         the user has not yet been located.  Inbound Trying
         responses indicate that outbound INVITE request 
         sent out by this system have been received and
         are processed."
    REFERENCE
        "RFC 2543, Sections 5.1.1 & 7.1.1"
    ::= { cSipStatsInfo 1 }

cSipStatsInfoTryingOuts OBJECT-TYPE
    SYNTAX Counter
    ACCESS read-only
    STATUS mandatory
    DESCRIPTION
        "This object reflects the total number of Trying
         (100) responses sent by the user agent.
         Trying responses indicate that some unspecified
         action is being taken on behalf of this call, but
         the user has not yet been located.  Outbound Trying
         responses indicate this system is successfully 
         receiving INVITE requests and processing them on 
         behalf of the system initiating the INVITE."
    REFERENCE
        "RFC 2543, Sections 5.1.1 & 7.1.1"
    ::= { cSipStatsInfo 2 }

cSipStatsInfoRingingIns OBJECT-TYPE
    SYNTAX Counter
    ACCESS read-only
    STATUS mandatory
    DESCRIPTION
        "This object reflects the total number of Ringing
         (180) responses received by the user agent.
         A inbound Ringing response indicates that the UAS
         processing a INVITE initiated by this system has 
         found a possible location where the desired end user 
         has registered recently and is trying to alert the user."
    REFERENCE
        "RFC 2543, Sections 5.1.1 & 7.1.2"
    ::= { cSipStatsInfo 3 }

cSipStatsInfoRingingOuts OBJECT-TYPE
    SYNTAX Counter
    ACCESS read-only
    STATUS mandatory
    DESCRIPTION
        "This object reflects the total number of Ringing
         (180) responses sent by the user agent.
         A outbound Ringing response indicates that this
         system has processed an INVITE for a particular
         end user and found a possible location where that
         user has registered recently.  The system is trying
         to alert the end user and is conveying that status
         to the system that originated the INVITE."
    REFERENCE
        "RFC 2543, Sections 5.1.1 & 7.1.2"
    ::= { cSipStatsInfo 4 }

cSipStatsInfoForwardedIns OBJECT-TYPE
    SYNTAX Counter
    ACCESS read-only
    STATUS mandatory
    DESCRIPTION
        "This object reflects the total number of Call Is Being
         Forwarded (181) responses received by the user agent.
         A proxy server may use a Forwarded status code to
         indicate that the call is being forwarded to a different
         set of destinations.  Inbound Forwarded responses indicate 
         to this system that forwarding actions are taking place 
         with regard to calls initiated by this system."
    REFERENCE
        "RFC 2543, Sections 5.1.1 & 7.1.3"
    ::= { cSipStatsInfo 5 }

cSipStatsInfoForwardedOuts OBJECT-TYPE
    SYNTAX Counter
    ACCESS read-only
    STATUS mandatory
    DESCRIPTION
        "This object reflects the total number of Call Is Being
         Forwarded (181) responses sent by the user agent.
         A proxy server may use a Forwarded status code to
         indicate that the call is being forwarded to a different
         set of destinations.  Outbound Forwarded responses
         indicate this system is taking some forwarding action
         for calls and conveying that status to the system that
         initiated the calls."
    REFERENCE
        "RFC 2543, Sections 5.1.1 & 7.1.3"
    ::= { cSipStatsInfo 6 }

cSipStatsInfoQueuedIns OBJECT-TYPE
    SYNTAX Counter
    ACCESS read-only
    STATUS mandatory
    DESCRIPTION
        "This object reflects the total number of Queued
         (182) responses received by the user agent.
         Inbound Queued responses indicate that the users
         this system is attempting to call are temporarily
         unavailable but the SIP agents operating on behalf
         of those users wish to queue the calls rather than
         reject them.  When the called parties become available,
         this system can expect to receive the appropriate
         final status response.  The Reason-Phrase from the
         Queued response messages Status-Line may give further
         details about the status of the call.  Multiple 
         Queued responses to update this system about the status
         of the queued call my be received."
    REFERENCE
        "RFC 2543, Sections 5.1.1 & 7.1.4"
    ::= { cSipStatsInfo 7 }

cSipStatsInfoQueuedOuts OBJECT-TYPE
    SYNTAX Counter
    ACCESS read-only
    STATUS mandatory
    DESCRIPTION
        "This object reflects the total number of Queued
         (182) responses sent by the user agent.
         Outbound Queued responses indicate this system
         has determined that the called party is temporarily
         unavailable but the call is not rejected.  Rather 
         the call is queued until the called party becomes
         available.  Queued responses messages are sent to
         the system originating the call request to convey
         the current status of a queued call."
    REFERENCE
        "RFC 2543, Sections 5.1.1 & 7.1.4"
    ::= { cSipStatsInfo 8 }

cSipStatsInfoSessionProgIns OBJECT-TYPE
    SYNTAX Counter
    ACCESS read-only
    STATUS mandatory
    DESCRIPTION
        "This object reflects the total number of Session
         Progress (183) responses received by the user agent."
    ::= { cSipStatsInfo 9 }

cSipStatsInfoSessionProgOuts OBJECT-TYPE
    SYNTAX Counter
    ACCESS read-only
    STATUS mandatory
    DESCRIPTION
        "This object reflects the total number of Session
         Progress (183) responses sent by the user agent."
    ::= { cSipStatsInfo 10 }

cSipStatsSuccessOkIns OBJECT-TYPE
    SYNTAX Counter
    ACCESS read-only
    STATUS mandatory
    DESCRIPTION
        "This object reflects the total number of Ok
         (200) responses received by the user agent.
         The meaning of inbound Ok responses depends
         on the method used in the associated request.
        
         BYE      : The Ok response means the call has 
                    been terminated.
        
         CANCEL   : The Ok response means the search for 
                    the end user has been cancelled.
        
         INVITE   : The Ok response means the called party 
                    has agreed to participate in the call.
        
         OPTIONS  : The Ok response means the called party 
                    has agreed to share its capabilities.
        
         REGISTER : The Ok response means the registration
                    has succeeded."
    REFERENCE
        "RFC 2543, Sections 5.1.1 & 7.2.1"
    ::= { cSipStatsSuccess 1 }

cSipStatsSuccessOkOuts OBJECT-TYPE
    SYNTAX Counter
    ACCESS read-only
    STATUS mandatory
    DESCRIPTION
        "This object reflects the total number of Ok
         (200) responses sent by the user agent.
         The meaning of outbound Ok responses depends
         on the method used in the associated request.
        
         BYE      : The Ok response means the call has 
                    been terminated.
        
         CANCEL   : The Ok response means the search for 
                    the end user has been cancelled.
        
         INVITE   : The Ok response means the called party 
                    has agreed to participate in the call.
        
         OPTIONS  : The Ok response means the called party 
                    has agreed to share its capabilities.
        
         REGISTER : The Ok response means the registration
                    has succeeded."
    REFERENCE
        "RFC 2543, Sections 5.1.1 & 7.2.1"
    ::= { cSipStatsSuccess 2 }

cSipStatsRedirMultipleChoices OBJECT-TYPE
    SYNTAX Counter
    ACCESS read-only
    STATUS mandatory
    DESCRIPTION
        "This object reflects the total number of Multiple
         Choices (300) responses received by the user agent.
         Multiple Choices responses indicate that the called
         party can be reached at several different locations
         and the server cannot or prefers not to proxy the request."
    REFERENCE
        "RFC 2543, Section 5.1.1 & 7.3.1"
    ::= { cSipStatsRedirect 1 }

cSipStatsRedirMovedPerms OBJECT-TYPE
    SYNTAX Counter
    ACCESS read-only
    STATUS mandatory
    DESCRIPTION
        "This object reflects the total number of Moved 
         Permanently (301) responses received by the user agent.
         Moved Permanently responses indicate that the called party 
         can no longer be found at the address offered in the request 
         and the requesting UAC should retry at the new address given 
         by the Contact header field of the response."
    REFERENCE
        "RFC 2543, Sections 5.1.1 & 7.3.2"
    ::= { cSipStatsRedirect 2 }

cSipStatsRedirMovedTemps OBJECT-TYPE
    SYNTAX Counter
    ACCESS read-only
    STATUS mandatory
    DESCRIPTION
        "This object reflects the total number of Moved 
         Temporarily (302) responses received by the user agent.
         Moved Temporarily responses indicate the UAC should
         retry the request directed at the new address(es)
         given by the Contact header field of the response.
         The duration of this redirection can be indicated
         through the Expires header.  If no explicit expiration
         time is given, the new address(es) are only valid
         for this call."
    REFERENCE
        "RFC 2543, Sections 5.1.1 & 7.3.3"
    ::= { cSipStatsRedirect 3 }

cSipStatsRedirSeeOthers OBJECT-TYPE
    SYNTAX Counter
    ACCESS read-only
    STATUS mandatory
    DESCRIPTION
        "This object reflects the total number of See Other 
         (303) responses received by the user agent."
    REFERENCE
        "RFC 2543, Sections 5.1.1"
    ::= { cSipStatsRedirect 4 }

cSipStatsRedirUseProxys OBJECT-TYPE
    SYNTAX Counter
    ACCESS read-only
    STATUS mandatory
    DESCRIPTION
        "This object reflects the total number of Use Proxy 
         (305) responses received by the user agent.
         See Other responses indicate that requested resources
         must be accessed through the proxy given by the 
         Contact header field of the response.  The recipient
         of this response is expected to repeat this single
         request via the proxy."
    REFERENCE
        "RFC 2543, Sections 5.1.1 & 7.3.4"
    ::= { cSipStatsRedirect 5 }

cSipStatsRedirAltServices OBJECT-TYPE
    SYNTAX Counter
    ACCESS read-only
    STATUS mandatory
    DESCRIPTION
        "This object reflects the total number of Alternative
         Service (380) responses received by the user agent.
         Alternative Service responses indicate that the call
         was not successful, but alternative services are
         possible.  Those alternative services are described
         in the message body of the response."
    REFERENCE
        "RFC 2543, Sections 5.1.1 & 7.3.5"
    ::= { cSipStatsRedirect 6 }

cSipStatsClientBadRequestIns OBJECT-TYPE
    SYNTAX Counter
    ACCESS read-only
    STATUS mandatory
    DESCRIPTION
        "This object reflects the total number of Bad Request (400) 
         responses received by the user agent.
         Inbound Bad Request responses indicate that requests issued 
         by this system could not be understood due to malformed 
         syntax."
    REFERENCE
        "RFC 2543, Sections 5.1.1 & 7.4.1"
    ::= { cSipStatsErrClient 1 }

cSipStatsClientBadRequestOuts OBJECT-TYPE
    SYNTAX Counter
    ACCESS read-only
    STATUS mandatory
    DESCRIPTION
        "This object reflects the total number of Bad Request (400) 
         responses sent by the user agent.
         Outbound Bad Request responses indicate that requests 
         received by this system could not be understood due to 
         malformed syntax."
    REFERENCE
        "RFC 2543, Sections 5.1.1 & 7.4.1"
    ::= { cSipStatsErrClient 2 }

cSipStatsClientUnauthorizedIns OBJECT-TYPE
    SYNTAX Counter
    ACCESS read-only
    STATUS mandatory
    DESCRIPTION
        "This object reflects the total number of Unauthorized (401) 
         responses received by the user agent.  
         Inbound Unauthorized responses indicate that requests issued 
         by this system require user authentication."
    REFERENCE
        "RFC 2543, Sections 5.1.1 & 7.4.2"
    ::= { cSipStatsErrClient 3 }

cSipStatsClientUnauthorizedOuts OBJECT-TYPE
    SYNTAX Counter
    ACCESS read-only
    STATUS mandatory
    DESCRIPTION
        "This object reflects the total number of Unathorized (401) 
         responses sent by the user agent.
         Outbound Unauthorized responses indicate that requests 
         received by this system require user authentication."
    REFERENCE
        "RFC 2543, Sections 5.1.1 & 7.4.2"
    ::= { cSipStatsErrClient 4 }

cSipStatsClientPaymentReqdIns OBJECT-TYPE
    SYNTAX Counter
    ACCESS read-only
    STATUS mandatory
    DESCRIPTION
        "This object reflects the total number of Payment Required 
         (402) responses received by the user agent."
    REFERENCE
        "RFC 2543, Sections 5.1.1 & 7.4.3"
    ::= { cSipStatsErrClient 5 }

cSipStatsClientPaymentReqdOuts OBJECT-TYPE
    SYNTAX Counter
    ACCESS read-only
    STATUS mandatory
    DESCRIPTION
        "This object reflects the total number of Payment Required 
         (402) responses sent by the user agent."
    REFERENCE
        "RFC 2543, Sections 5.1.1 & 7.4.3"
    ::= { cSipStatsErrClient 6 }

cSipStatsClientForbiddenIns OBJECT-TYPE
    SYNTAX Counter
    ACCESS read-only
    STATUS mandatory
    DESCRIPTION
        "This object reflects the total number of Forbidden (403) 
         responses received by the user agent.
         Inbound Forbidden responses indicate that requests issued
         by this system are understood by the server but the server
         refuses to fulfill the request.  Authorization will not help
         and the requests should not be repeated."
    REFERENCE
        "RFC 2543, Sections 5.1.1 & 7.4.4"
    ::= { cSipStatsErrClient 7 }

cSipStatsClientForbiddenOuts OBJECT-TYPE
    SYNTAX Counter
    ACCESS read-only
    STATUS mandatory
    DESCRIPTION
        "This object reflects the total number of Forbidden (403) 
         responses sent by the user agent.
         Outbound Forbidden responses indicate that requests received
         by this system are understood but this system is refusing to
         fulfill the requests."
    REFERENCE
        "RFC 2543, Sections 5.1.1 & 7.4.4"
    ::= { cSipStatsErrClient 8 }

cSipStatsClientNotFoundIns OBJECT-TYPE
    SYNTAX Counter
    ACCESS read-only
    STATUS mandatory
    DESCRIPTION
        "This object reflects the total number of Not Found (404) 
         responses received by the user agent.
         Inbound Not Found responses indicate that the called party 
         does not exist at the domain specified in the Request-URI 
         or the domain is not handled by the recipient of the request."
    REFERENCE
        "RFC 2543, Sections 5.1.1 & 7.4.5"
    ::= { cSipStatsErrClient 9 }

cSipStatsClientNotFoundOuts OBJECT-TYPE
    SYNTAX Counter
    ACCESS read-only
    STATUS mandatory
    DESCRIPTION
        "This object reflects the total number of Not Found (404) 
         responses sent by the user agent.
         Outbound Not Found responses indicate that this system
         knows that the called party does not exist at the domain
         specified in the Request-URI or the domain is not handled
         by this system."
    REFERENCE
        "RFC 2543, Sections 5.1.1 & 7.4.5"
    ::= { cSipStatsErrClient 10 }

cSipStatsClientMethNotAllowedIns OBJECT-TYPE
    SYNTAX Counter
    ACCESS read-only
    STATUS mandatory
    DESCRIPTION
        "This object reflects the total number of Method Not Allowed 
         (405) received responses by the user agent.
         Inbound Method Not Allowed responses indicate that requests 
         issued by this system have specified a SIP method in the 
         Request-Line that is not allowed for the address identified 
         by the Request-URI."
    REFERENCE
        "RFC 2543, Sections 5.1.1 & 7.4.6"
    ::= { cSipStatsErrClient 11 }

cSipStatsClientMethNotAllowedOuts OBJECT-TYPE
    SYNTAX Counter
    ACCESS read-only
    STATUS mandatory
    DESCRIPTION
        "This object reflects the total number of Method Not Allowed 
         (405) received sent by the user agent.
         Outbound Method Not Allowed responses indicate that requests 
         received by this system have SIP methods specified in the 
         Request-Line that are not allowed for the address identified 
         by the Request-URI."
    REFERENCE
        "RFC 2543, Sections 5.1.1 & 7.4.6"
    ::= { cSipStatsErrClient 12 }

cSipStatsClientNotAcceptableIns OBJECT-TYPE
    SYNTAX Counter
    ACCESS read-only
    STATUS mandatory
    DESCRIPTION
        "This object reflects the total number of Not Acceptable 
         (406) responses received by the user agent.
         Inbound Not Acceptable responses indicate the resources 
         identified by requests issued by this system cannot generate 
         responses with content characteristics acceptable to this 
         system according to the accept headers sent in the requests."
    REFERENCE
        "RFC 2543, Sections 5.1.1 & 7.4.7"
    ::= { cSipStatsErrClient 13 }

cSipStatsClientNotAcceptableOuts OBJECT-TYPE
    SYNTAX Counter
    ACCESS read-only
    STATUS mandatory
    DESCRIPTION
        "This object reflects the total number of Not Acceptable (406) 
         responses sent by the user agent.
         Outbound Not Acceptable responses indicate that the resources
         identified by requests received by this system cannot generate
         responses with content characteristics acceptable to the 
         system sending the requests."
    REFERENCE
        "RFC 2543, Sections 5.1.1 & 7.4.7"
    ::= { cSipStatsErrClient 14 }

cSipStatsClientProxyAuthReqdIns OBJECT-TYPE
    SYNTAX Counter
    ACCESS read-only
    STATUS mandatory
    DESCRIPTION
        "This object reflects the total number of Proxy Authenticaion 
         Required (407) responses received by the user agent.
         Inbound Proxy Authentication Required responses indicate that 
         this system must authenticate itself with the proxy before 
         gaining access to the requested resource."
    REFERENCE
        "RFC 2543, Sections 5.1.1 & 7.4.8"
    ::= { cSipStatsErrClient 15 }

cSipStatsClientProxyAuthReqdOuts OBJECT-TYPE
    SYNTAX Counter
    ACCESS read-only
    STATUS mandatory
    DESCRIPTION
        "This object reflects the total number of Proxy Authenticaion 
         Required (407) responses sent by the user agent.
         Outbound Proxy Authentication Required responses indicate that
         the systems issuing requests being processed by this system 
         must authenticate themselves with this system before gaining 
         access to requested resources."
    REFERENCE
        "RFC 2543, Sections 5.1.1 & 7.4.8"
    ::= { cSipStatsErrClient 16 }

cSipStatsClientReqTimeoutIns OBJECT-TYPE
    SYNTAX Counter
    ACCESS read-only
    STATUS mandatory
    DESCRIPTION
        "This object reflects the total number of Request Timeout 
         (408) responses received by the user agent.
         Inbound Request Timeout responses indicate that requests 
         issued by this system are not being processed by the server 
         within the time indicated in the Expires header of the 
         request."
    REFERENCE
        "RFC 2543, Sections 5.1.1 & 7.4.9"
    ::= { cSipStatsErrClient 17 }

cSipStatsClientReqTimeoutOuts OBJECT-TYPE
    SYNTAX Counter
    ACCESS read-only
    STATUS mandatory
    DESCRIPTION
        "This object reflects the total number of Request Timeout 
         (408) responses sent by the user agent.
         Outbound Request Timeout responses indicate that this 
         system is not able to produce an appropriate response within 
         the time indicated in the Expires header of the request."
    REFERENCE
        "RFC 2543, Sections 5.1.1 & 7.4.9"
    ::= { cSipStatsErrClient 18 }

cSipStatsClientConflictIns OBJECT-TYPE
    SYNTAX Counter
    ACCESS read-only
    STATUS mandatory
    DESCRIPTION
        "This object reflects the total number of Conflict (409) 
         responses received by the user agent.
         Inbound Conflict responses indicate that requests issued
         by this system could not be completed due to a conflict
         with the current state of a requested resource."
    REFERENCE
        "RFC 2543, Sections 5.1.1 & 7.4.10"
    ::= { cSipStatsErrClient 19 }

cSipStatsClientConflictOuts OBJECT-TYPE
    SYNTAX Counter
    ACCESS read-only
    STATUS mandatory
    DESCRIPTION
        "This object reflects the total number of Conflict (409) 
         responses sent by the user agent.
         Outbound Conflict responses indicate that requests received
         by this system could not be completed due to a conflict
         with the current state of a requested resource."
    REFERENCE
        "RFC 2543, Sections 5.1.1 & 7.4.10"
    ::= { cSipStatsErrClient 20 }

cSipStatsClientGoneIns OBJECT-TYPE
    SYNTAX Counter
    ACCESS read-only
    STATUS mandatory
    DESCRIPTION
        "This object reflects the total number of Gone (410) 
         responses received by the user agent.
         Inbound Gone responses indicate that resources requested
         by this system are no longer available at the recipient server
         and no forwarding address is known."
    REFERENCE
        "RFC 2543, Sections 5.1.1 & 7.4.11"
    ::= { cSipStatsErrClient 21 }

cSipStatsClientGoneOuts OBJECT-TYPE
    SYNTAX Counter
    ACCESS read-only
    STATUS mandatory
    DESCRIPTION
        "This object reflects the total number of Gone (410) 
         responses sent by the user agent.
         Outbound Gone responses indicate that the requested
         resources are no longer available at this system and
         no forwarding address is known."
    REFERENCE
        "RFC 2543, Sections 5.1.1 & 7.4.11"
    ::= { cSipStatsErrClient 22 }

cSipStatsClientLengthRequiredIns OBJECT-TYPE
    SYNTAX Counter
    ACCESS read-only
    STATUS mandatory
    DESCRIPTION
        "This object reflects the total number of Length Required 
         (411) responses received by the user agent.
         Inbound Length Required responses indicate that requests 
         issued by this system are being refused by servers because 
         of no defined Content-Length header field."
    REFERENCE
        "RFC 2543, Sections 5.1.1 & 7.4.12"
    ::= { cSipStatsErrClient 23 }

cSipStatsClientLengthRequiredOuts OBJECT-TYPE
    SYNTAX Counter
    ACCESS read-only
    STATUS mandatory
    DESCRIPTION
        "This object reflects the total number of Length Required 
         (411) responses sent by the user agent.
         Outbound Length Required responses indicate that requests 
         received by this system are being refused because of no 
         defined Content-Length header field."
    REFERENCE
        "RFC 2543, Sections 5.1.1 & 7.4.12"
    ::= { cSipStatsErrClient 24 }

cSipStatsClientReqEntTooLargeIns OBJECT-TYPE
    SYNTAX Counter
    ACCESS read-only
    STATUS mandatory
    DESCRIPTION
        "This object reflects the total number of Request Entity Too 
         Large (413) responses received by the user agent.
         Inbound Request Entity Too Large responses indicate that 
         requests issued by this system are being refused because 
         the request is larger than the server is willing or able to 
         process."
    REFERENCE
        "RFC 2543, Sections 5.1.1 & 7.4.13"
    ::= { cSipStatsErrClient 25 }

cSipStatsClientReqEntTooLargeOuts OBJECT-TYPE
    SYNTAX Counter
    ACCESS read-only
    STATUS mandatory
    DESCRIPTION
        "This object reflects the total number of Request Entity Too 
         Large (413) responses sent by the user agent.
         Outbound Request Entity Too Large responses indicate that 
         requests received by this system are larger than this system 
         is willing or able to process."
    REFERENCE
        "RFC 2543, Sections 5.1.1 & 7.4.13"
    ::= { cSipStatsErrClient 26 }

cSipStatsClientReqURITooLargeIns OBJECT-TYPE
    SYNTAX Counter
    ACCESS read-only
    STATUS mandatory
    DESCRIPTION
        "This object reflects the total number of Request-URI Too 
         Large (414) responses received by the user agent.
         Inbound Request-URI Too Large responses indicate that 
         requests issued by this system are being refused because the 
         Request-URI is longer than the server is willing or able to 
         interpret."
    REFERENCE
        "RFC 2543, Sections 5.1.1 & 7.4.14"
    ::= { cSipStatsErrClient 27 }

cSipStatsClientReqURITooLargeOuts OBJECT-TYPE
    SYNTAX Counter
    ACCESS read-only
    STATUS mandatory
    DESCRIPTION
        "This object reflects the total number of Request-URI Too 
         Large (414) responses sent by the user agent.
         Outbound Request-URI Too Large responses indicate that 
         Request-URIs received by this system are longer than this 
         system is willing or able to interpret."
    REFERENCE
        "RFC 2543, Sections 5.1.1 & 7.4.14"
    ::= { cSipStatsErrClient 28 }

cSipStatsClientNoSupMediaTypeIns OBJECT-TYPE
    SYNTAX Counter
    ACCESS read-only
    STATUS mandatory
    DESCRIPTION
        "This object reflects the total number of Unsupported Media 
         Type (415) responses received by the user agent.
         Inbound Unsupported Media Type responses indicate that 
         requests issued by this system are being refused because the 
         message body of the request is in a format not supported by 
         the requested resource for the requested method."
    REFERENCE
        "RFC 2543, Sections 5.1.1 & 7.4.15"
    ::= { cSipStatsErrClient 29 }

cSipStatsClientNoSupMediaTypeOuts OBJECT-TYPE
    SYNTAX Counter
    ACCESS read-only
    STATUS mandatory
    DESCRIPTION
        "This object reflects the total number of Unsupported Media 
         Type (415) responses sent by the user agent.
         Outbound Unsupported Media Type responses indicate that the 
         body of requests received by this system are in a format not 
         supported by the requested resource for the requested method."
    REFERENCE
        "RFC 2543, Sections 5.1.1 & 7.4.15"
    ::= { cSipStatsErrClient 30 }

cSipStatsClientBadExtensionIns OBJECT-TYPE
    SYNTAX Counter
    ACCESS read-only
    STATUS mandatory
    DESCRIPTION
        "This object reflects the total number of Bad Extension (420) 
         responses received by the user agent.
         Inbound Bad Extension responses indicate that the recipient 
         did not understand the protocol extension specified in a 
         Require header field."
    REFERENCE
        "RFC 2543, Sections 5.1.1 & 7.5.16"
    ::= { cSipStatsErrClient 31 }

cSipStatsClientBadExtensionOuts OBJECT-TYPE
    SYNTAX Counter
    ACCESS read-only
    STATUS mandatory
    DESCRIPTION
        "This object reflects the total number of Bad Extension (420) 
         responses sent by the user agent.
         Outbound Bad Extension responses indicate that this system
         did not understand the protocol extension specified in a
         Require header field of requests."
    REFERENCE
        "RFC 2543, Sections 5.1.1 & 7.4.16"
    ::= { cSipStatsErrClient 32 }

cSipStatsClientTempNotAvailIns OBJECT-TYPE
    SYNTAX Counter
    ACCESS read-only
    STATUS mandatory
    DESCRIPTION
        "This object reflects the total number of Temporarily Not 
         Available (480) responses received by the user agent.
         Inbound Temporarily Not Available responses indicate that 
         the called party is currently unavailable."
    REFERENCE
        "RFC 2543, Sections 5.1.1 & 7.4.17"
    ::= { cSipStatsErrClient 33 }

cSipStatsClientTempNotAvailOuts OBJECT-TYPE
    SYNTAX Counter
    ACCESS read-only
    STATUS mandatory
    DESCRIPTION
        "This object reflects the total number of Temporarily Not 
         Available (480) responses sent by the user agent.
         Outbound Temporarily Not Available responses indicate that 
         the called party's end system was contacted successfully but 
         the called party is currently unavailable."
    REFERENCE
        "RFC 2543, Sections 5.1.1 & 7.4.17"
    ::= { cSipStatsErrClient 34 }

cSipStatsClientCallLegNoExistIns OBJECT-TYPE
    SYNTAX Counter
    ACCESS read-only
    STATUS mandatory
    DESCRIPTION
        "This object reflects the total number of Call Leg/Transaction 
         Does Not Exist (481) responses received by the user agent.
         Inbound Call Leg/Transaction Does Not Exist responses indicate
         that either BYE or CANCEL requests issued by this system were 
         received by a server and not matching call leg or transaction 
         existed."
    REFERENCE
        "RFC 2543, Sections 5.1.1 & 7.4.18"
    ::= { cSipStatsErrClient 35 }

cSipStatsClientCallLegNoExistOuts OBJECT-TYPE
    SYNTAX Counter
    ACCESS read-only
    STATUS mandatory
    DESCRIPTION
        "This object reflects the total number of Call Leg/Transaction 
         Does Not Exist (481) responses sent by the user agent.
         Outbound Call Leg/Transaction Does Not Exist responses 
         indicate that BYE or CANCEL requests have been received by 
         this system and not call leg or transaction matching that 
         request exists."
    REFERENCE
        "RFC 2543, Sections 5.1.1 & 7.4.18"
    ::= { cSipStatsErrClient 36 }

cSipStatsClientLoopDetectedIns OBJECT-TYPE
    SYNTAX Counter
    ACCESS read-only
    STATUS mandatory
    DESCRIPTION
        "This object reflects the total number of Loop Detected (482) 
         responses received by the user agent.
         Inbound Loop Dectected responses indicate that requests issued
         by this system were received at servers and the server found 
         itself in the Via path more than once."
    REFERENCE
        "RFC 2543, Sections 5.1.1 & 7.4.19"
    ::= { cSipStatsErrClient 37 }

cSipStatsClientLoopDetectedOuts OBJECT-TYPE
    SYNTAX Counter
    ACCESS read-only
    STATUS mandatory
    DESCRIPTION
        "This object reflects the total number of Loop Detected (482) 
         responses sent by the user agent.
         Outbound Loop Detected responses indicate that requests 
         received by this system contain a Via path with this system 
         appearing more than once."
    REFERENCE
        "RFC 2543, Sections 5.1.1 & 7.4.19"
    ::= { cSipStatsErrClient 38 }

cSipStatsClientTooManyHopsIns OBJECT-TYPE
    SYNTAX Counter
    ACCESS read-only
    STATUS mandatory
    DESCRIPTION
        "This object reflects the total number of Too Many Hops (483) 
         responses received by the user agent.
         Inbound Too Many Hops responses indicate that requests issued
         by this system contain more Via entries (hops) than allowed by
         the Max-Forwards header field of the requests."
    REFERENCE
        "RFC 2543, Sections 5.1.1 & 7.4.20"
    ::= { cSipStatsErrClient 39 }

cSipStatsClientTooManyHopsOuts OBJECT-TYPE
    SYNTAX Counter
    ACCESS read-only
    STATUS mandatory
    DESCRIPTION
        "This object reflects the total number of Too Many Hops (483) 
         responses sent by the user agent.
         Outbound Too Many Hops responses indicate that requests
         received by this system contain more Via entries (hops) than
         are allowed by the Max-Forwards header field of the requests."
    REFERENCE
        "RFC 2543, Sections 5.1.1 & 7.4.20"
    ::= { cSipStatsErrClient 40 }

cSipStatsClientAddrIncompleteIns OBJECT-TYPE
    SYNTAX Counter
    ACCESS read-only
    STATUS mandatory
    DESCRIPTION
        "This object reflects the total number of Address Incomplete 
         (484) responses received by the user agent.
         Inbound Address Incomplete responses indicate that requests 
         issued by this system had To addresses or Request-URIs that 
         were incomplete."
    REFERENCE
        "RFC 2543, Sections 5.1.1 & 7.4.21"
    ::= { cSipStatsErrClient 41 }

cSipStatsClientAddrIncompleteOuts OBJECT-TYPE
    SYNTAX Counter
    ACCESS read-only
    STATUS mandatory
    DESCRIPTION
        "This object reflects the total number of Address Incomplete 
         (484) responses sent by the user agent.
         Outbound Address Incomplete responses indicate that requests 
         received by this system had To addresses or Request-URIs that 
         were incomplete."
    REFERENCE
        "RFC 2543, Sections 5.1.1 & 7.4.21"
    ::= { cSipStatsErrClient 42 }

cSipStatsClientAmbiguousIns OBJECT-TYPE
    SYNTAX Counter
    ACCESS read-only
    STATUS mandatory
    DESCRIPTION
        "This object reflects the total number of Ambiguous (485) 
         responses received by the user agent.
         Inbound Ambiguous responses indicate that requests issued
         by this system provided ambiguous address information."
    REFERENCE
        "RFC 2543, Sections 5.1.1 & 7.4.22"
    ::= { cSipStatsErrClient 43 }

cSipStatsClientAmbiguousOuts OBJECT-TYPE
    SYNTAX Counter
    ACCESS read-only
    STATUS mandatory
    DESCRIPTION
        "This object reflects the total number of Ambiguous (485) 
         responses sent by the user agent.
         Outbound Ambiguous responses indicate that requests received
         by this system contained ambiguous address information."
    REFERENCE
        "RFC 2543, Sections 5.1.1 & 7.4.22"
    ::= { cSipStatsErrClient 44 }

cSipStatsClientBusyHereIns OBJECT-TYPE
    SYNTAX Counter
    ACCESS read-only
    STATUS mandatory
    DESCRIPTION
        "This object reflects the total number of Busy Here (486) 
         responses received by the user agent.
         Inbound Busy Here responses indicate that the
         called party is currently not willing or not able to
         take additional calls."
    REFERENCE
        "RFC 2543, Section 5.1.1 & 7.4.23"
    ::= { cSipStatsErrClient 45 }

cSipStatsClientBusyHereOuts OBJECT-TYPE
    SYNTAX Counter
    ACCESS read-only
    STATUS mandatory
    DESCRIPTION
        "This object reflects the total number of Busy Here (486) 
         responses sent by the user agent.
         Outbound Busy Here responses indicate that the
         called party's end system was contacted successfully but the
         called party is currently not willing or able to take 
         additional calls."
    REFERENCE
        "RFC 2543, Sections 5.1.1 & 7.4.23"
    ::= { cSipStatsErrClient 46 }

cSipStatsClientReqTermIns OBJECT-TYPE
    SYNTAX Counter
    ACCESS read-only
    STATUS mandatory
    DESCRIPTION
        "This object reflects the total number of Request Terminated 
         (487) responses received by the user agent.
         Request Terminated responses are issued if the original 
         request was terminated via CANCEL or BYE."
    REFERENCE
        "draft-ietf-sip-rfc2543bis-01.txt, Section 7.4.24.487"
    ::= { cSipStatsErrClient 47 }

cSipStatsClientReqTermOuts OBJECT-TYPE
    SYNTAX Counter
    ACCESS read-only
    STATUS mandatory
    DESCRIPTION
        "This object reflects the total number of Request Terminated 
         (487) responses sent by the user agent.
         Request Terminated responses are issued if the original 
         request was terminated via CANCEL or BYE."
    REFERENCE
        "draft-ietf-sip-rfc2543bis-01.txt, Section 7.4.24.487"
    ::= { cSipStatsErrClient 48 }

cSipStatsClientNoAcceptHereIns OBJECT-TYPE
    SYNTAX Counter
    ACCESS read-only
    STATUS mandatory
    DESCRIPTION
        "This object reflects the total number of Not Acceptable Here
         (488) responses received by the user agent.
         The response has the same meaning as 606 (Not Acceptable), 
         but only applies to the specific entity addressed by the 
         Request-URI and the request may succeed elsewhere."
    REFERENCE
        "draft-ietf-sip-rfc2543bis-01.txt, Section 7.4.24.488"
    ::= { cSipStatsErrClient 49 }

cSipStatsClientNoAcceptHereOuts OBJECT-TYPE
    SYNTAX Counter
    ACCESS read-only
    STATUS mandatory
    DESCRIPTION
        "This object reflects the total number of Not Acceptable Here
         (488) responses sent by the user agent.
         The response has the same meaning as 606 (Not Acceptable), 
         but only applies to the specific entity addressed by the 
         Request-URI and the request may succeed elsewhere."
    REFERENCE
        "draft-ietf-sip-rfc2543bis-01.txt, Section 7.4.24.488"
    ::= { cSipStatsErrClient 50 }

cSipStatsServerIntErrorIns OBJECT-TYPE
    SYNTAX Counter
    ACCESS read-only
    STATUS mandatory
    DESCRIPTION
        "This object reflects the total number of Internal Server Error
         (500) responses received by the user agent.
         Inbound Internal Server Error responses indicate that servers 
         to which this system is sending requests have encountered 
         unexpected conditions that prevent them from fulfilling the 
         requests."
    REFERENCE
        "RFC 2543, Sections 5.1.1 & 7.5.1"
    ::= { cSipStatsErrServer 1 }

cSipStatsServerIntErrorOuts OBJECT-TYPE
    SYNTAX Counter
    ACCESS read-only
    STATUS mandatory
    DESCRIPTION
        "This object reflects the total number of Internal Server Error
         (500) responses sent by the user agent.
         Outbound Internal Server Error responses indicate that this 
         system has encountered unexpected conditions that prevent it 
         from fulfilling received requests."
    REFERENCE
        "RFC 2543, Sections 5.1.1 & 7.5.1"
    ::= { cSipStatsErrServer 2 }

cSipStatsServerNotImplementedIns OBJECT-TYPE
    SYNTAX Counter
    ACCESS read-only
    STATUS mandatory
    DESCRIPTION
        "This object reflects the total number of Not Implemented 
         (501) responses received by the user agent.
         Inbound Not Implemented responses indicate that servers to 
         which this system is sending requests do not support the 
         functionality required to fulfill the requests."
    REFERENCE
        "RFC 2543, Sections 5.1.1 & 7.5.2"
    ::= { cSipStatsErrServer 3 }

cSipStatsServerNotImplementedOuts OBJECT-TYPE
    SYNTAX Counter
    ACCESS read-only
    STATUS mandatory
    DESCRIPTION
        "This object reflects the total number of Not Implemented 
         (501) responses sent by the user agent.
         Outbound Not Implemented responses indicate that this system
         does not support the functionality required to fulfill the 
         requests."
    REFERENCE
        "RFC 2543, Sections 5.1.1 & 7.5.2"
    ::= { cSipStatsErrServer 4 }

cSipStatsServerBadGatewayIns OBJECT-TYPE
    SYNTAX Counter
    ACCESS read-only
    STATUS mandatory
    DESCRIPTION
        "This object reflects the total number of Bad Gateway (502) 
         responses received by the user agent."
    REFERENCE
        "RFC 2543, Sections 5.1.1 & 7.5.3"
    ::= { cSipStatsErrServer 5 }

cSipStatsServerBadGatewayOuts OBJECT-TYPE
    SYNTAX Counter
    ACCESS read-only
    STATUS mandatory
    DESCRIPTION
        "This object reflects the total number of Bad Gateway (502) 
         responses sent by the user agent."
    REFERENCE
        "RFC 2543, Sections 5.1.1 & 7.5.3"
    ::= { cSipStatsErrServer 6 }

cSipStatsServerServiceUnavailIns OBJECT-TYPE
    SYNTAX Counter
    ACCESS read-only
    STATUS mandatory
    DESCRIPTION
        "This object reflects the total number of Service Unavailable 
         (503) responses received by the user agent.
         Inbound Service Unavailable responses indicate that the server
         servicing this system's request is temporarily unavailable to
         handle the request."
    REFERENCE
        "RFC 2543, Sections 5.1.1 & 7.5.4"
    ::= { cSipStatsErrServer 7 }

cSipStatsServerServiceUnavailOuts OBJECT-TYPE
    SYNTAX Counter
    ACCESS read-only
    STATUS mandatory
    DESCRIPTION
        "This object reflects the total number of Service Unavailable 
         (503) responses sent by the user agent.
         Outbound Service Unavailable responses indicate that this
         system is temporarily unable to handle received requests."
    REFERENCE
        "RFC 2543, Sections 5.1.1 & 7.5.4"
    ::= { cSipStatsErrServer 8 }

cSipStatsServerGatewayTimeoutIns OBJECT-TYPE
    SYNTAX Counter
    ACCESS read-only
    STATUS mandatory
    DESCRIPTION
        "This object reflects the total number of Gateway Time-out 
         (504) responses received by the user agent.
         Inbound Gateway Time-out responses indicate that the server
         attempting to complete this system's request did not receive
         a timely response from yet another system it was accessing to
         complete the request."
    REFERENCE
        "RFC 2543, Sections 5.1.1 & 7.5.5"
    ::= { cSipStatsErrServer 9 }

cSipStatsServerGatewayTimeoutOuts OBJECT-TYPE
    SYNTAX Counter
    ACCESS read-only
    STATUS mandatory
    DESCRIPTION
        "This object reflects the total number of Gateway Time-out 
         (504) responses sent by the user agent.
         Outbound Gateway Time-out responses indicate that this system
         did not receive a timely response from the system it had
         accessed to assist in completing a received request."
    REFERENCE
        "RFC 2543, Sections 5.1.1 & 7.5.5"
    ::= { cSipStatsErrServer 10 }

cSipStatsServerBadSipVersionIns OBJECT-TYPE
    SYNTAX Counter
    ACCESS read-only
    STATUS mandatory
    DESCRIPTION
        "This object reflects the total number of SIP Version Not 
         Supported (505) responses received by the user agent.
         Inbound SIP Version Not Supported responses indicate that 
         the server does not support, or refuses to support, the SIP 
         protocol version that was used in the request message."
    REFERENCE
        "RFC 2543, Sections 5.1.1 & 7.5.6"
    ::= { cSipStatsErrServer 11 }

cSipStatsServerBadSipVersionOuts OBJECT-TYPE
    SYNTAX Counter
    ACCESS read-only
    STATUS mandatory
    DESCRIPTION
        "This object reflects the total number of SIP Version Not 
         Supported (505) responses sent by the user agent.
         Outbound SIP Version Not Supported responses indicate that 
         this system does not support, or refuses to support, the SIP 
         protocl version used in received requests."
    REFERENCE
        "RFC 2543, Sections 5.1.1 & 7.5.6"
    ::= { cSipStatsErrServer 12 }

cSipStatsServerPrecondFailureIns OBJECT-TYPE
    SYNTAX Counter
    ACCESS read-only
    STATUS mandatory
    DESCRIPTION
        "This object reflects the total number of Precondition 
         Failure (580) responses received by the user agent.
         This response is returned by a UAS if it is unable to
         perform the mandatory preconditions for the session."
    REFERENCE
        "draft-manyfolks-sip-resource-01.txt, Section 6"
    ::= { cSipStatsErrServer 13 }

cSipStatsServerPrecondFailureOuts OBJECT-TYPE
    SYNTAX Counter
    ACCESS read-only
    STATUS mandatory
    DESCRIPTION
        "This object reflects the total number of Precondition 
         Failure (580) responses sent by the user agent.
         This response is returned by a UAS if it is unable to
         perform the mandatory preconditions for the session."
    REFERENCE
        "draft-manyfolks-sip-resource-01.txt, Section 6"
    ::= { cSipStatsErrServer 14 }

cSipStatsGlobalBusyEverywhereIns OBJECT-TYPE
    SYNTAX Counter
    ACCESS read-only
    STATUS mandatory
    DESCRIPTION
        "This object reflects the total number of Busy
         Everywhere (600) responses received by the user agent.
         Inbound Busy Everywhere responses indicate that the 
         called party's end system was contacted successfully
         but the called party is busy and does not wish to take
         the call at this time."
    REFERENCE
        "RFC 2543, Sections 5.1.1 & 7.6.1"
    ::= { cSipStatsGlobalFail 1 }

cSipStatsGlobalBusyEverywhereOuts OBJECT-TYPE
    SYNTAX Counter
    ACCESS read-only
    STATUS mandatory
    DESCRIPTION
        "This object reflects the total number of Busy
         Everywhere (600) responses sent by the user agent.
         Outbound Busy Everywhere responses indicate that 
         this system has successfully contacted a called party's
         end system and the called party does not wish to take
         the call at this time."
    REFERENCE
        "RFC 2543, Sections 5.1.1 & 7.6.1"
    ::= { cSipStatsGlobalFail 2 }

cSipStatsGlobalDeclineIns OBJECT-TYPE
    SYNTAX Counter
    ACCESS read-only
    STATUS mandatory
    DESCRIPTION
        "This object reflects the total number of Decline
         (603) responses received by the user agent.
         Decline responses indicate that the called party's end 
         system was contacted successfully but the called party 
         explicitly does not wish to, or cannot, participate."
    REFERENCE
        "RFC 2543, Sections 5.1.1 & 7.6.2"
    ::= { cSipStatsGlobalFail 3 }

cSipStatsGlobalDeclineOuts OBJECT-TYPE
    SYNTAX Counter
    ACCESS read-only
    STATUS mandatory
    DESCRIPTION
        "This object reflects the total number of Decline
         (603) responses sent by the user agent.
         Outbound Decline responses indicate that this system
         has successfully contacted a called party's end system
         and the called party explicitly does not wish to, or
         cannot, participate."
    REFERENCE
        "RFC 2543, Sections 5.1.1 & 7.6.2"
    ::= { cSipStatsGlobalFail 4 }

cSipStatsGlobalNotAnywhereIns OBJECT-TYPE
    SYNTAX Counter
    ACCESS read-only
    STATUS mandatory
    DESCRIPTION
        "This object reflects the total number of Does Not
         Exist Anywhere (604) responses received by the user agent.
         Inbound Does Not Exist Anywhere responses indicate that
         the server handling this system's request has authoritative
         information that the called party indicated in the To
         request field does not exist anywhere."
    REFERENCE
        "RFC 2543, Sections 5.1.1 & 7.6.3"
    ::= { cSipStatsGlobalFail 5 }

cSipStatsGlobalNotAnywhereOuts OBJECT-TYPE
    SYNTAX Counter
    ACCESS read-only
    STATUS mandatory
    DESCRIPTION
        "This object reflects the total number of Does Not
         Exist Anywhere (604) responses sent by the user agent.
         Outbound Does Not Exist Anywhere responses indicate that
         this system has authoritative information that the called
         party in the To field of received requests does not exist
         anywhere."
    REFERENCE
        "RFC 2543, Sections 5.1.1 & 7.6.3"
    ::= { cSipStatsGlobalFail 6 }

cSipStatsGlobalNotAcceptableIns OBJECT-TYPE
    SYNTAX Counter
    ACCESS read-only
    STATUS mandatory
    DESCRIPTION
        "This object reflects the total number of Not Acceptable
         (606) responses received by the user agent.
         Inbound Not Acceptable responses indicate that the called
         party's end system was contacted successfully but some
         aspect of the session description is not acceptable."
    REFERENCE
        "RFC 2543, Sections 5.1.1 & 7.6.4"
    ::= { cSipStatsGlobalFail 7 }

cSipStatsGlobalNotAcceptableOuts OBJECT-TYPE
    SYNTAX Counter
    ACCESS read-only
    STATUS mandatory
    DESCRIPTION
        "This object reflects the total number of Not Acceptable
         (606) responses sent by the user agent.
         Outbound Not Acceptable responses indicate that the called
         party wishes to communicate, but cannot adequately support
         the session described in the request."
    REFERENCE
        "RFC 2543, Sections 5.1.1 & 7.6.4"
    ::= { cSipStatsGlobalFail 8 }

cSipStatsTrafficInviteIns OBJECT-TYPE
    SYNTAX Counter
    ACCESS read-only
    STATUS mandatory
    DESCRIPTION
        "This object reflects the total number of INVITE requests 
         received by the user agent."
    REFERENCE
        "RFC 2543, Section 4.2.1"
    ::= { cSipStatsTraffic 1 }

cSipStatsTrafficInviteOuts OBJECT-TYPE
    SYNTAX Counter
    ACCESS read-only
    STATUS mandatory
    DESCRIPTION
        "This object reflects the total number of INVITE requests sent
         by the user agent."
    REFERENCE
        "RFC 2543, Section 4.2.1"
    ::= { cSipStatsTraffic 2 }

cSipStatsTrafficAckIns OBJECT-TYPE
    SYNTAX Counter
    ACCESS read-only
    STATUS mandatory
    DESCRIPTION
        "This object reflects the total number of ACK requests 
         received by the user agent."
    REFERENCE
        "RFC 2543, Section 4.2.2"
    ::= { cSipStatsTraffic 3 }

cSipStatsTrafficAckOuts OBJECT-TYPE
    SYNTAX Counter
    ACCESS read-only
    STATUS mandatory
    DESCRIPTION
        "This object reflects the total number of ACK requests sent
         by the user agent."
    REFERENCE
        "RFC 2543, Section 4.2.2"
    ::= { cSipStatsTraffic 4 }

cSipStatsTrafficByeIns OBJECT-TYPE
    SYNTAX Counter
    ACCESS read-only
    STATUS mandatory
    DESCRIPTION
        "This object reflects the total number of BYE requests 
         received by the user agent."
    REFERENCE
        "RFC 2543, Section 4.2.4"
    ::= { cSipStatsTraffic 5 }

cSipStatsTrafficByeOuts OBJECT-TYPE
    SYNTAX Counter
    ACCESS read-only
    STATUS mandatory
    DESCRIPTION
        "This object reflects the total number of BYE requests sent
         by the user agent."
    REFERENCE
        "RFC 2543, Section 4.2.4"
    ::= { cSipStatsTraffic 6 }

cSipStatsTrafficCancelIns OBJECT-TYPE
    SYNTAX Counter
    ACCESS read-only
    STATUS mandatory
    DESCRIPTION
        "This object reflects the total number of CANCEL requests 
         received by the user agent."
    REFERENCE
        "RFC 2543, Section 4.2.5"
    ::= { cSipStatsTraffic 7 }

cSipStatsTrafficCancelOuts OBJECT-TYPE
    SYNTAX Counter
    ACCESS read-only
    STATUS mandatory
    DESCRIPTION
        "This object reflects the total number of CANCEL requests sent
         by the user agent."
    REFERENCE
        "RFC 2543, Section 4.2.5"
    ::= { cSipStatsTraffic 8 }

cSipStatsTrafficOptionsIns OBJECT-TYPE
    SYNTAX Counter
    ACCESS read-only
    STATUS mandatory
    DESCRIPTION
        "This object reflects the total number of OPTIONS requests 
         received by the user agent."
    REFERENCE
        "RFC 2543, Section 4.2.3"
    ::= { cSipStatsTraffic 9 }

cSipStatsTrafficOptionsOuts OBJECT-TYPE
    SYNTAX Counter
    ACCESS read-only
    STATUS mandatory
    DESCRIPTION
        "This object reflects the total number of OPTIONS requests sent
         by the user agent."
    REFERENCE
        "RFC 2543, Section 4.2.3"
    ::= { cSipStatsTraffic 10 }

cSipStatsTrafficRegisterIns OBJECT-TYPE
    SYNTAX Counter
    ACCESS read-only
    STATUS mandatory
    DESCRIPTION
        "This object reflects the total number of REGISTER requests 
         received by the user agent."
    REFERENCE
        "RFC 2543, Section 4.2.6"
    ::= { cSipStatsTraffic 11 }

cSipStatsTrafficRegisterOuts OBJECT-TYPE
    SYNTAX Counter
    ACCESS read-only
    STATUS mandatory
    DESCRIPTION
        "This object reflects the total number of REGISTER requests 
         sent by the user agent."
    REFERENCE
        "RFC 2543, Section 4.2.6"
    ::= { cSipStatsTraffic 12 }

cSipStatsTrafficCometIns OBJECT-TYPE
    SYNTAX Counter
    ACCESS read-only
    STATUS mandatory
    DESCRIPTION
        "This object reflects the total number of COndition MET 
         requests received by the user agent."
    REFERENCE
        "draft-manyfolks-sip-resource-01.txt, Section 5"
    ::= { cSipStatsTraffic 13 }

cSipStatsTrafficCometOuts OBJECT-TYPE
    SYNTAX Counter
    ACCESS read-only
    STATUS mandatory
    DESCRIPTION
        "This object reflects the total number of COndition MET 
         requests sent by the user agent."
    REFERENCE
        "draft-manyfolks-sip-resource-01.txt, Section 5"
    ::= { cSipStatsTraffic 14 }

cSipStatsTrafficPrackIns OBJECT-TYPE
    SYNTAX Counter
    ACCESS read-only
    STATUS mandatory
    DESCRIPTION
        "This object reflects the total number of PRovisonal 
         ACKnowledgement requests received by the user agent."
    REFERENCE
        "draft-ietf-sip-100rel-02.txt"
    ::= { cSipStatsTraffic 15 }

cSipStatsTrafficPrackOuts OBJECT-TYPE
    SYNTAX Counter
    ACCESS read-only
    STATUS mandatory
    DESCRIPTION
        "This object reflects the total number of PRovisonal 
         ACKnowledgement requests sent by the user agent."
    REFERENCE
        "draft-ietf-sip-100rel-02.txt"
    ::= { cSipStatsTraffic 16 }

cSipStatsRetryInvites OBJECT-TYPE
    SYNTAX Counter
    ACCESS read-only
    STATUS mandatory
    DESCRIPTION
        "This object reflects the total number of INVITE retries that 
         have been sent by the user agent.   If the number of 'first 
         attempt' INVITES is of interest, subtract the value of this 
         object from cSipStatsTrafficInviteOut."
    ::= { cSipStatsRetry 1 }

cSipStatsRetryByes OBJECT-TYPE
    SYNTAX Counter
    ACCESS read-only
    STATUS mandatory
    DESCRIPTION
        "This object reflects the total number of BYE retries that have
         been sent by the user agent."
    ::= { cSipStatsRetry 2 }

cSipStatsRetryCancels OBJECT-TYPE
    SYNTAX Counter
    ACCESS read-only
    STATUS mandatory
    DESCRIPTION
        "This object reflects the total number of CANCEL retries that 
         have been sent by the user agent."
    ::= { cSipStatsRetry 3 }

cSipStatsRetryRegisters OBJECT-TYPE
    SYNTAX Counter
    ACCESS read-only
    STATUS mandatory
    DESCRIPTION
        "This object reflects the total number of REGISTER retries that
         have been sent by the user agent."
    ::= { cSipStatsRetry 4 }

cSipStatsRetryResponses OBJECT-TYPE
    SYNTAX Counter
    ACCESS read-only
    STATUS mandatory
    DESCRIPTION
        "This object reflects the total number of Response (while 
         expecting a ACK) retries that have been sent by the user
         agent."
    ::= { cSipStatsRetry 5 }

cSipStatsRetryPracks OBJECT-TYPE
    SYNTAX Counter
    ACCESS read-only
    STATUS mandatory
    DESCRIPTION
        "This object reflects the total number of PRovisional
         ACKnowledgement retries sent by the user agent."
    ::= { cSipStatsRetry 6 }

cSipStatsRetryComets OBJECT-TYPE
    SYNTAX Counter
    ACCESS read-only
    STATUS mandatory
    DESCRIPTION
        "This object reflects the total number of COndition
         MET retries sent by the user agent."
    ::= { cSipStatsRetry 7 }

cSipStatsRetryReliable1xxRsps OBJECT-TYPE
    SYNTAX Counter
    ACCESS read-only
    STATUS mandatory
    DESCRIPTION
        "This object reflects the total number of Reliable
         1xx Response retries sent by the user agent."
    ::= { cSipStatsRetry 8 }

ciscoSipBaseConfigGroup OBJECT IDENTIFIER ::= { ciscoSipUaMIBGroups 1 }
-- OBJECT-GROUP
--  Status
--    deprecated
--  Descr
--    A collection of objects providing basic SIP User Agent 
--     configuration.
--  objects
--    cSipCfgUserLocationServerAddr, cSipCfgTransport, 
--    cSipCfgVersion

ciscoSipTimerConfigGroup OBJECT IDENTIFIER ::= { ciscoSipUaMIBGroups 2 }
-- OBJECT-GROUP
--  Status
--    deprecated
--  Descr
--    A collection of objects providing basic SIP User Agent
--     timer configuration.
--  objects
--    cSipCfgTimerTrying, cSipCfgTimerExpires, cSipCfgTimerConnect, 
--    cSipCfgTimerDisconnect

ciscoSipRetryConfigGroup OBJECT IDENTIFIER ::= { ciscoSipUaMIBGroups 3 }
-- OBJECT-GROUP
--  Status
--    deprecated
--  Descr
--    A collection of objects providing basic SIP User Agent
--     retry configuration.
--  objects
--    cSipCfgRetryInvite, cSipCfgRetryBye, cSipCfgRetryCancel, 
--    cSipCfgRetryRegister, cSipCfgRetryResponse

ciscoSipStatsInfoStatusCodesGroup OBJECT IDENTIFIER ::= { ciscoSipUaMIBGroups 4 }
-- OBJECT-GROUP
--  Status
--    mandatory
--  Descr
--    A collection of objects providing basic SIP User Agent
--     Informational status code response messages statistics.
--  objects
--    cSipStatsInfoTryingIns, cSipStatsInfoTryingOuts, 
--    cSipStatsInfoRingingIns, cSipStatsInfoRingingOuts, 
--    cSipStatsInfoForwardedIns, cSipStatsInfoForwardedOuts, 
--    cSipStatsInfoQueuedIns, cSipStatsInfoQueuedOuts, 
--    cSipStatsInfoSessionProgIns, cSipStatsInfoSessionProgOuts

ciscoSipStatsSuccessStatusCodesGroup OBJECT IDENTIFIER ::= { ciscoSipUaMIBGroups 5 }
-- OBJECT-GROUP
--  Status
--    mandatory
--  Descr
--    A collection of objects providing basic SIP User Agent
--     Success status code response messages statistics.
--  objects
--    cSipStatsSuccessOkIns, cSipStatsSuccessOkOuts

ciscoSipStatsRedirStatusCodesGroup OBJECT IDENTIFIER ::= { ciscoSipUaMIBGroups 6 }
-- OBJECT-GROUP
--  Status
--    mandatory
--  Descr
--    A collection of objects providing basic SIP User Agent
--     Redirection status code response messages statistics.
--  objects
--    cSipStatsRedirMultipleChoices, cSipStatsRedirMovedPerms, 
--    cSipStatsRedirMovedTemps, cSipStatsRedirSeeOthers, 
--    cSipStatsRedirUseProxys, cSipStatsRedirAltServices

ciscoSipStatsClientStatusCodesGroup OBJECT IDENTIFIER ::= { ciscoSipUaMIBGroups 7 }
-- OBJECT-GROUP
--  Status
--    deprecated
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientLengthRequiredIns, 
--    cSipStatsClientLengthRequiredOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts

ciscoSipStatsServerStatusCodesGroup OBJECT IDENTIFIER ::= { ciscoSipUaMIBGroups 8 }
-- OBJECT-GROUP
--  Status
--    deprecated
--  Descr
--    A collection of objects providing basic SIP User Agent
--     Server Error status code response messages statistics.
--  objects
--    cSipStatsServerIntErrorIns, cSipStatsServerIntErrorOuts, 
--    cSipStatsServerNotImplementedIns, 
--    cSipStatsServerNotImplementedOuts, 
--    cSipStatsServerBadGatewayIns, cSipStatsServerBadGatewayOuts, 
--    cSipStatsServerServiceUnavailIns, 
--    cSipStatsServerServiceUnavailOuts, 
--    cSipStatsServerGatewayTimeoutIns, 
--    cSipStatsServerGatewayTimeoutOuts, 
--    cSipStatsServerBadSipVersionIns, 
--    cSipStatsServerBadSipVersionOuts

ciscoSipStatsGlobalStatusCodesGroup OBJECT IDENTIFIER ::= { ciscoSipUaMIBGroups 9 }
-- OBJECT-GROUP
--  Status
--    mandatory
--  Descr
--    A collection of objects providing basic SIP User Agent
--     Global Failure status code response messages statistics.
--  objects
--    cSipStatsGlobalBusyEverywhereIns, 
--    cSipStatsGlobalBusyEverywhereOuts, cSipStatsGlobalDeclineIns, 
--    cSipStatsGlobalDeclineOuts, cSipStatsGlobalNotAnywhereIns, 
--    cSipStatsGlobalNotAnywhereOuts, 
--    cSipStatsGlobalNotAcceptableIns, 
--    cSipStatsGlobalNotAcceptableOuts

ciscoSipTrafficStatsGroup OBJECT IDENTIFIER ::= { ciscoSipUaMIBGroups 10 }
-- OBJECT-GROUP
--  Status
--    deprecated
--  Descr
--    A collection of objects providing basic SIP User Agent
--     inbound and outbound traffic statistics.
--  objects
--    cSipStatsTrafficInviteIns, cSipStatsTrafficInviteOuts, 
--    cSipStatsTrafficAckIns, cSipStatsTrafficAckOuts, 
--    cSipStatsTrafficByeIns, cSipStatsTrafficByeOuts, 
--    cSipStatsTrafficCancelIns, cSipStatsTrafficCancelOuts, 
--    cSipStatsTrafficOptionsIns, cSipStatsTrafficOptionsOuts, 
--    cSipStatsTrafficRegisterIns, cSipStatsTrafficRegisterOuts

ciscoSipRetryStatsGroup OBJECT IDENTIFIER ::= { ciscoSipUaMIBGroups 11 }
-- OBJECT-GROUP
--  Status
--    deprecated
--  Descr
--    A collection of objects providing basic SIP User Agent
--     retry statistics.
--  objects
--    cSipStatsRetryInvites, cSipStatsRetryByes, 
--    cSipStatsRetryCancels, cSipStatsRetryRegisters, 
--    cSipStatsRetryResponses

ciscoSipBaseConfigGroupRev1 OBJECT IDENTIFIER ::= { ciscoSipUaMIBGroups 12 }
-- OBJECT-GROUP
--  Status
--    mandatory
--  Descr
--    A collection of objects providing basic SIP User Agent 
--     configuration.
--  objects
--    cSipCfgUserLocationServerAddr, cSipCfgTransport, 
--    cSipCfgVersion, cSipCfgMaxForwards

ciscoSipTimerConfigGroupRev1 OBJECT IDENTIFIER ::= { ciscoSipUaMIBGroups 13 }
-- OBJECT-GROUP
--  Status
--    mandatory
--  Descr
--    A collection of objects providing basic SIP User Agent
--     timer configuration.
--  objects
--    cSipCfgTimerTrying, cSipCfgTimerExpires, cSipCfgTimerConnect, 
--    cSipCfgTimerDisconnect, cSipCfgTimerPrack, cSipCfgTimerComet, 
--    cSipCfgTimerReliableRsp

ciscoSipRetryConfigGroupRev1 OBJECT IDENTIFIER ::= { ciscoSipUaMIBGroups 14 }
-- OBJECT-GROUP
--  Status
--    mandatory
--  Descr
--    A collection of objects providing basic SIP User Agent
--     retry configuration.
--  objects
--    cSipCfgRetryInvite, cSipCfgRetryBye, cSipCfgRetryCancel, 
--    cSipCfgRetryRegister, cSipCfgRetryResponse, cSipCfgRetryPrack, 
--    cSipCfgRetryComet, cSipCfgRetryReliableRsp

ciscoSipTrafficStatsGroupRev1 OBJECT IDENTIFIER ::= { ciscoSipUaMIBGroups 15 }
-- OBJECT-GROUP
--  Status
--    mandatory
--  Descr
--    A collection of objects providing basic SIP User Agent
--     inbound and outbound traffic statistics.
--  objects
--    cSipStatsTrafficInviteIns, cSipStatsTrafficInviteOuts, 
--    cSipStatsTrafficAckIns, cSipStatsTrafficAckOuts, 
--    cSipStatsTrafficByeIns, cSipStatsTrafficByeOuts, 
--    cSipStatsTrafficCancelIns, cSipStatsTrafficCancelOuts, 
--    cSipStatsTrafficOptionsIns, cSipStatsTrafficOptionsOuts, 
--    cSipStatsTrafficRegisterIns, cSipStatsTrafficRegisterOuts, 
--    cSipStatsTrafficCometIns, cSipStatsTrafficCometOuts, 
--    cSipStatsTrafficPrackIns, cSipStatsTrafficPrackOuts

ciscoSipStatsServerStatusCodesGroupRev1 OBJECT IDENTIFIER ::= { ciscoSipUaMIBGroups 16 }
-- OBJECT-GROUP
--  Status
--    mandatory
--  Descr
--    A collection of objects providing basic SIP User Agent
--     Server Error status code response messages statistics.
--  objects
--    cSipStatsServerIntErrorIns, cSipStatsServerIntErrorOuts, 
--    cSipStatsServerNotImplementedIns, 
--    cSipStatsServerNotImplementedOuts, 
--    cSipStatsServerBadGatewayIns, cSipStatsServerBadGatewayOuts, 
--    cSipStatsServerServiceUnavailIns, 
--    cSipStatsServerServiceUnavailOuts, 
--    cSipStatsServerGatewayTimeoutIns, 
--    cSipStatsServerGatewayTimeoutOuts, 
--    cSipStatsServerBadSipVersionIns, 
--    cSipStatsServerBadSipVersionOuts, 
--    cSipStatsServerPrecondFailureIns, 
--    cSipStatsServerPrecondFailureOuts

ciscoSipRetryStatsGroupRev1 OBJECT IDENTIFIER ::= { ciscoSipUaMIBGroups 17 }
-- OBJECT-GROUP
--  Status
--    mandatory
--  Descr
--    A collection of objects providing basic SIP User Agent
--     retry statistics.
--  objects
--    cSipStatsRetryInvites, cSipStatsRetryByes, 
--    cSipStatsRetryCancels, cSipStatsRetryRegisters, 
--    cSipStatsRetryResponses, cSipStatsRetryPracks, 
--    cSipStatsRetryComets, cSipStatsRetryReliable1xxRsps

ciscoSipStatsClientStatusCodesGroupRev1 OBJECT IDENTIFIER ::= { ciscoSipUaMIBGroups 18 }
-- OBJECT-GROUP
--  Status
--    mandatory
--  Descr
--    A collection of objects providing basic SIP User Agent
--     Client Error status code response messages statistics.
--  objects
--    cSipStatsClientBadRequestIns, cSipStatsClientBadRequestOuts, 
--    cSipStatsClientUnauthorizedIns, 
--    cSipStatsClientUnauthorizedOuts, 
--    cSipStatsClientPaymentReqdIns, cSipStatsClientPaymentReqdOuts, 
--    cSipStatsClientForbiddenIns, cSipStatsClientForbiddenOuts, 
--    cSipStatsClientNotFoundIns, cSipStatsClientNotFoundOuts, 
--    cSipStatsClientMethNotAllowedIns, 
--    cSipStatsClientMethNotAllowedOuts, 
--    cSipStatsClientNotAcceptableIns, 
--    cSipStatsClientNotAcceptableOuts, 
--    cSipStatsClientProxyAuthReqdIns, 
--    cSipStatsClientProxyAuthReqdOuts, 
--    cSipStatsClientReqTimeoutIns, cSipStatsClientReqTimeoutOuts, 
--    cSipStatsClientConflictIns, cSipStatsClientConflictOuts, 
--    cSipStatsClientGoneIns, cSipStatsClientGoneOuts, 
--    cSipStatsClientLengthRequiredIns, 
--    cSipStatsClientLengthRequiredOuts, 
--    cSipStatsClientReqEntTooLargeIns, 
--    cSipStatsClientReqEntTooLargeOuts, 
--    cSipStatsClientReqURITooLargeIns, 
--    cSipStatsClientReqURITooLargeOuts, 
--    cSipStatsClientNoSupMediaTypeIns, 
--    cSipStatsClientNoSupMediaTypeOuts, 
--    cSipStatsClientBadExtensionIns, 
--    cSipStatsClientBadExtensionOuts, 
--    cSipStatsClientTempNotAvailIns, 
--    cSipStatsClientTempNotAvailOuts, 
--    cSipStatsClientCallLegNoExistIns, 
--    cSipStatsClientCallLegNoExistOuts, 
--    cSipStatsClientLoopDetectedIns, 
--    cSipStatsClientLoopDetectedOuts, 
--    cSipStatsClientTooManyHopsIns, cSipStatsClientTooManyHopsOuts, 
--    cSipStatsClientAddrIncompleteIns, 
--    cSipStatsClientAddrIncompleteOuts, 
--    cSipStatsClientAmbiguousIns, cSipStatsClientAmbiguousOuts, 
--    cSipStatsClientBusyHereIns, cSipStatsClientBusyHereOuts, 
--    cSipStatsClientReqTermIns, cSipStatsClientReqTermOuts, 
--    cSipStatsClientNoAcceptHereIns, 
--    cSipStatsClientNoAcceptHereOuts

ciscoSipCfgPeerGroup OBJECT IDENTIFIER ::= { ciscoSipUaMIBGroups 19 }
-- OBJECT-GROUP
--  Status
--    mandatory
--  Descr
--    A collection of objects providing SIP related configuration
--     of Dial Peers.
--  objects
--    cSipCfgPeerOutSessionTransport, cSipCfgPeerReliable1xxRspStr, 
--    cSipCfgPeerReliable1xxRspHdr, cSipCfgPeerUrlType, 
--    cSipCfgOutSessionTransport, cSipCfgReliable1xxRspStr, 
--    cSipCfgReliable1xxRspHdr, cSipCfgUrlType

ciscoSipCompliance OBJECT IDENTIFIER ::= { ciscoSipUaMIBCompliances 1 }
-- MODULE-COMPLIANCE
--  Status
--    deprecated
--  Descr
--    The compliance statement for SIP user agent entities.
--  Module
--    >>current<<
--   MandGroup
--    ciscoSipBaseConfigGroup
--   MandGroup
--    ciscoSipStatsInfoStatusCodesGroup
--   MandGroup
--    ciscoSipStatsSuccessStatusCodesGroup
--   MandGroup
--    ciscoSipStatsGlobalStatusCodesGroup
--   MandGroup
--    ciscoSipTrafficStatsGroup
--   OptGroup
--    ciscoSipTimerConfigGroup
--   OptGroup
--    ciscoSipRetryConfigGroup
--   OptGroup
--    ciscoSipRetryStatsGroup
--   OptGroup
--    ciscoSipStatsRedirStatusCodesGroup
--   OptGroup
--    ciscoSipStatsClientStatusCodesGroup
--   OptGroup
--    ciscoSipStatsServerStatusCodesGroup
--   ObjVar
--    cSipCfgUserLocationServerAddr
--   ObjVar
--    cSipCfgTransport

ciscoSipComplianceRev1 OBJECT IDENTIFIER ::= { ciscoSipUaMIBCompliances 2 }
-- MODULE-COMPLIANCE
--  Status
--    mandatory
--  Descr
--    The compliance statement for SIP user agent entities.
--  Module
--    >>current<<
--   MandGroup
--    ciscoSipBaseConfigGroupRev1
--   MandGroup
--    ciscoSipStatsInfoStatusCodesGroup
--   MandGroup
--    ciscoSipStatsSuccessStatusCodesGroup
--   MandGroup
--    ciscoSipStatsGlobalStatusCodesGroup
--   MandGroup
--    ciscoSipTrafficStatsGroupRev1
--   OptGroup
--    ciscoSipTimerConfigGroupRev1
--   OptGroup
--    ciscoSipRetryConfigGroupRev1
--   OptGroup
--    ciscoSipRetryStatsGroupRev1
--   OptGroup
--    ciscoSipStatsRedirStatusCodesGroup
--   OptGroup
--    ciscoSipStatsClientStatusCodesGroupRev1
--   OptGroup
--    ciscoSipStatsServerStatusCodesGroupRev1
--   ObjVar
--    cSipCfgUserLocationServerAddr
--   ObjVar
--    cSipCfgTransport
--   ObjVar
--    cSipCfgMaxForwards
--   OptGroup
--    ciscoSipCfgPeerGroup


END
