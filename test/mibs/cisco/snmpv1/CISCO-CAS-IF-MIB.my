-- MIB file created 08-Sep-2004 18:30:44, by
--   SMICng version 2.2.11-beta(PRO)(Solaris), January 20, 2001. Enterprise key cisco.com

CISCO-CAS-IF-MIB DEFINITIONS ::= BEGIN

-- From file: "CISCO-CAS-IF-MIB.my"
-- Compile options "4 7 F H N W 03 06 0B 0G 0N 0T"

IMPORTS
    RowStatus, TruthValue, DisplayString
            FROM SNMPv2-TC-v1
    InterfaceIndex, ifIndex
            FROM IF-MIB
    CountryCode
            FROM CISCO-TC
    ciscoMgmt
            FROM CISCO-SMI
    OBJECT-TYPE
            FROM RFC-1212;

ciscoCasIfMIB OBJECT IDENTIFIER ::= { ciscoMgmt 85 }
-- MODULE-IDENTITY
--  LastUpdated
--    200304180000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-voice@cisco.com
--  Descr
--    Channel Associated Signal Interface MIB module.
--     This MIB manages the generic CAS (Channel Associated
--     Signal)or DS0 clear channel Interfaces in the router.
--  RevDate
--    200304180000Z
--  RevDescr
--    Extend ccasGrpCfgServiceType to include 
--     h248 (9) and ds0xconn (10)
--  RevDate
--    200210020000Z
--  RevDescr
--    Extend ccasGrpCfgServiceType to include 
--     trunkingService(8).
--  RevDate
--    9901180000Z
--  RevDescr
--    Add ccasXgcpCfgTable to configure continuity test
--     (COT) tone frequencies. 
--     Add object ccasGrpCfgServiceType for displaying service 
--     type.
--     Extend ccsaGrpCfgType to include fgdOS, fgdEANA and 
--     nullSignaling

ccasIfObjects   OBJECT IDENTIFIER ::= { ciscoCasIfMIB 1 }
ccasDS1Objects  OBJECT IDENTIFIER ::= { ccasIfObjects 1 }
ccasGrpObjects  OBJECT IDENTIFIER ::= { ccasIfObjects 2 }
ccasChannelObjects OBJECT IDENTIFIER ::= { ccasIfObjects 3 }
ccasVoiceCfgObjects OBJECT IDENTIFIER ::= { ccasIfObjects 4 }
ccasXgcpCfgObjects OBJECT IDENTIFIER ::= { ccasIfObjects 5 }
ccasGrpGeneralObjects OBJECT IDENTIFIER ::= { ccasGrpObjects 1 }
ccasGrpEMObjects OBJECT IDENTIFIER ::= { ccasGrpObjects 2 }
ccasGrpLineObjects OBJECT IDENTIFIER ::= { ccasGrpObjects 3 }
ccasGrpStaObjects OBJECT IDENTIFIER ::= { ccasGrpObjects 4 }
ccasGrpABCDObjects OBJECT IDENTIFIER ::= { ccasGrpObjects 5 }
ccasIfMIBConformance OBJECT IDENTIFIER ::= { ciscoCasIfMIB 3 }
ccasIfMIBCompliances OBJECT IDENTIFIER ::= { ccasIfMIBConformance 1 }
ccasIfMIBGroups OBJECT IDENTIFIER ::= { ccasIfMIBConformance 2 }

ccasDs1IfCfgTable OBJECT-TYPE
    SYNTAX SEQUENCE OF CcasDs1IfCfgEntry
    ACCESS not-accessible
    STATUS mandatory
    DESCRIPTION
        "The CAS/DS0 General Configuration Table for T1/E1.  It
         contains the CAS/DS0 related standard configuration 
         information for T1/E1."
    ::= { ccasDS1Objects 1 }

ccasDs1IfCfgEntry OBJECT-TYPE
    SYNTAX CcasDs1IfCfgEntry
    ACCESS not-accessible
    STATUS mandatory
    DESCRIPTION
        "An entry in the configuration table for each T1/E1.
         The entry is created when a T1/E1 hardware is detected."
    INDEX { ifIndex }
    ::= { ccasDs1IfCfgTable 1 }

CcasDs1IfCfgEntry ::= SEQUENCE {
    ccasDs1IfCfgDs0ChannelsConfigurable OCTET STRING
    }

ccasDs1IfCfgDs0ChannelsConfigurable OBJECT-TYPE
    SYNTAX OCTET STRING(SIZE(0..4))
    ACCESS read-only
    STATUS mandatory
    DESCRIPTION
        "This object contains the bit map of the available DS0
         channel in the DS1.
         The MSB (most significant bit) is DS0 channel number 1. 
         The missing bytes is default to a value of 0.
         A 1-bit indicates the channel is available for
         configuration and a 0-bit indicates it isn't.
         The length of this object is either 3 octets (for T1)
         or 4 octets (for E1).
         
         The most significant bit is transmitted first."
    ::= { ccasDs1IfCfgEntry 1 }

ccasGrpCfgTable OBJECT-TYPE
    SYNTAX SEQUENCE OF CcasGrpCfgEntry
    ACCESS not-accessible
    STATUS mandatory
    DESCRIPTION
        "The CAS/DS0 Group Standard Configuration Table.  It
         contains the general configuration information for the
         CAS/DS0 group of T1/E1 interfaces."
    ::= { ccasGrpGeneralObjects 1 }

ccasGrpCfgEntry OBJECT-TYPE
    SYNTAX CcasGrpCfgEntry
    ACCESS not-accessible
    STATUS mandatory
    DESCRIPTION
        "A CAS/DS0 group entry. Each entry consists of the CAS
         group type and the CAS/DS0 group associated DS0
         channels in a T1/E1.
         The value of ccasGrpCfgDs0Channels must be specified
         with at least one available DS0 channel in the CAS
         group associated T1/E1 before a new row in this table
         can become active(1).
         The entry of this table can only be created if the
         CAS/DS0 group associated DS1 ifEntry already exists."
    INDEX { ifIndex, ccasGrpCfgIndex }
    ::= { ccasGrpCfgTable 1 }

CcasGrpCfgEntry ::= SEQUENCE {
    ccasGrpCfgIndex INTEGER,
    ccasGrpCfgType INTEGER,
    ccasGrpCfgDs0Channels OCTET STRING,
    ccasGrpCfgServiceType INTEGER,
    ccasGrpCfgRowStatus RowStatus
    }

ccasGrpCfgIndex OBJECT-TYPE
    SYNTAX INTEGER(0..30)
    ACCESS not-accessible
    STATUS mandatory
    DESCRIPTION
        "An arbitrary index that uniquely identifies a DS0 group
         in a T1/E1."
    ::= { ccasGrpCfgEntry 1 }

ccasGrpCfgType OBJECT-TYPE
    SYNTAX INTEGER {
        emWinkStart(1),
        emWinkStartFgd(2),
        emImmedStart(3),
        emDelayDial(4),
        fxsLoopStart(5),
        fxsGroundStart(6),
        sasLoopStart(7),
        sasGroundStart(8),
        r2Analog(9),
        r2Digital(10),
        r2Pulse(11),
        p7(12),
        fxoLoopStart(13),
        fxoGroundStart(14),
        fgdOS(15),
        nullSignaling(16),
        r1Itu(17),
        r1Modified(18),
        r1Turkey(19),
        fgdEANA(20)
        }
    ACCESS read-write
    STATUS mandatory
    DESCRIPTION
        "The Signaling type of the DS0 group.
         emWinkStart    - CAS E&M Wink Start.                   
         emWinkStartFgd - CAS E&M Wink Start with Feature
                          group D.
         emImmedStart   - CAS E&M Immediate Start.     
         emDelayDial    - CAS E&M Delay Dial.                   
         fxsLoopStart   - CAS FXS Loop Start.
         fxsGroundStart - CAS FXS Ground Start.
         sasLoopStart   - CAS SAS Loop Start.
         sasGroundStart - CAS SAS Ground Start.
         r2Analog       - R2 ITU Q411.
         r2Digital      - R2 ITU Q421.
         r2Pulse        - R2 ITU Supplement 7. 
         p7             - P7 switch.
         fgdOS          - Bellcore Feature Group D : 
                                 Operator Services Signaling 
         nullSignaling  - 64k clear channel
         r1Itu          - R1 ITU.
         r1Modified     - R1 Modified.
         r1Turkey       - R1 Turkey.
         fgdEANA        - FGD Exchange Access North American."
    REFERENCE
        "EIA/TIA-464B, chapter 6.2.1.1 Signaling Interface Types.
         ITU-T Q411 - Specifications of signalling system R2 line
                      signalling, analogue version.
         ITU-T Q421 - Specifications of signalling system R2 line
                      signalling, digital version. 
         ITU-T R2 Supplement 7 - Specifications of signalling system
                      R2 line signalling, pulsed version.
         Bellcore, TR-NPL-000258 -  Feature Group D
                   section 3.4 for Exchange Access North American 
                   section 3.6 for Operator Services Signaling "
    DEFVAL { emWinkStart }
    ::= { ccasGrpCfgEntry 2 }

ccasGrpCfgDs0Channels OBJECT-TYPE
    SYNTAX OCTET STRING(SIZE(4))
    ACCESS read-write
    STATUS mandatory
    DESCRIPTION
        "This object contains the bit map of the selected DS0 
         channels to be added into this group.
         The MSB (most significant bit) is DS0 channel number 1.
         For T1, only higher 24 bits are used to specify the
         the CAS channels for the CAS group.
         A 1-bit indicates the channel to be added into group
         and a 0-bit indicates it isn't."
    DEFVAL { '00000000'H }
    ::= { ccasGrpCfgEntry 3 }

ccasGrpCfgServiceType OBJECT-TYPE
    SYNTAX INTEGER {
        none(1),
        casServSw56(2),
        casServModem(3),
        casServAuto(4),
        sgcp(5),
        mgcp(6),
        other(7),
        trunkingService(8),
        h248(9),
        ds0xconn(10)
        }
    ACCESS read-write
    STATUS mandatory
    DESCRIPTION
        "Specify the Service type of the CAS/DS0 group.
         none - no service type 
         casServSw56 -  sw56 service for CAS
         casServModme -  modem service for CAS
         casServAuto -  auto service for CAS
         sgcp -  Simple Gateway Control Protocol
                 (SGCP) service. Used when DS0 is  
                 configured for null signaling.
         mgcp -  Media Gateway Control Protocol 
                 (MGCP) service. Used when DS0 is  
                 configured for null signaling.
         other - none of the above and the below.  
         trunkingService - 
                 This DS0 group is handled by
                 trunking service application. 
         h248 - ITU H.248 Media Gateway Control 
                service. Used when DS0 is
                configured for null signaling.
         ds0xconn - Used for DS0 cross connection."
    DEFVAL { none }
    ::= { ccasGrpCfgEntry 5 }

ccasGrpCfgRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or modify
         or delete an existing row in this table. The
         corresponding instance of ccasGrpCfgType can not be
         modified while this object has the value 'active'. "
    ::= { ccasGrpCfgEntry 4 }

ccasGrpEMCfgTable OBJECT-TYPE
    SYNTAX SEQUENCE OF CcasGrpEMCfgEntry
    ACCESS not-accessible
    STATUS mandatory
    DESCRIPTION
        "The CAS Group E&M Standard Configuration Table. It
         contains the CAS E&M group standard configuration
         information of T1/E1."
    ::= { ccasGrpEMObjects 1 }

ccasGrpEMCfgEntry OBJECT-TYPE
    SYNTAX CcasGrpEMCfgEntry
    ACCESS not-accessible
    STATUS mandatory
    DESCRIPTION
        "An entry in the configuration table for each CAS E&M
         Group in the T1/E1.
         The entry is created when the ccasGrpCfgType is
         configured as 'em' on a T1/E1 via configuration
         command.
         The entry is deleted when the CAS Group is
         de-configured from T1/E1."
    INDEX { ifIndex, ccasGrpCfgIndex }
    ::= { ccasGrpEMCfgTable 1 }

CcasGrpEMCfgEntry ::= SEQUENCE {
    ccasGrpEMCfgDialType INTEGER,
    ccasGrpEMCfgDnisAni OCTET STRING
    }

ccasGrpEMCfgDialType OBJECT-TYPE
    SYNTAX INTEGER {
        dtmf(1),
        pulse(2),
        mf(3)
        }
    ACCESS read-write
    STATUS mandatory
    DESCRIPTION
        "Specify the addressing type of the CAS group.
         dtmf  - Dual Tone Multi-Frequency (DTMF) digit.
         pulse - dial pulse.
         mf    - Multi-Frequency (MF) digit.
         The default value of this object is dtmf(1)."
    ::= { ccasGrpEMCfgEntry 1 }

ccasGrpEMCfgDnisAni OBJECT-TYPE
    SYNTAX OCTET STRING(SIZE(1..2))
        -- BITS are:
        --   incomingDnis(0)
        --   incomingAni(1)
        --   outgoingDnis(2)
        --   outgoingAni(3)
    ACCESS read-write
    STATUS mandatory
    DESCRIPTION
        "Specify the type of Destination Number Identification
         Service (DNIS) and Automatic Number Identification
         (ANI) support.
         MF tone supports both ANI and DNIS services. The DTMF
         tone only supports both incoming and outgoing DNIS.
         incomingDnis     - support incoming DNIS feature.
         incomingAni      - support incoming ANI feature.
         outgoingDnis     - support outgoing DNIS feature.
         outgoingAni      - support outgoing ANI feature.
         The default value of this object is '00'H."
    ::= { ccasGrpEMCfgEntry 2 }

ccasGrpEMTmTable OBJECT-TYPE
    SYNTAX SEQUENCE OF CcasGrpEMTmEntry
    ACCESS not-accessible
    STATUS mandatory
    DESCRIPTION
        "The E&M interface Timing Parameters table. It 
         contains the configuration of the various E&M signaling
         protocol timing parameters."
    ::= { ccasGrpEMObjects 2 }

ccasGrpEMTmEntry OBJECT-TYPE
    SYNTAX CcasGrpEMTmEntry
    ACCESS not-accessible
    STATUS mandatory
    DESCRIPTION
        "An entry in the E&M Timing Parameters Table for
         each E&M interface."
    INDEX { ifIndex, ccasGrpCfgIndex }
-- Augments ccasGrpEMCfgEntry
    ::= { ccasGrpEMTmTable 1 }

CcasGrpEMTmEntry ::= SEQUENCE {
    ccasGrpEMTmClearWaitDuration INTEGER,
    ccasGrpEMTmMaxWinkWaitDuration INTEGER,
    ccasGrpEMTmMaxWinkDuration INTEGER,
    ccasGrpEMTmDelayStart INTEGER,
    ccasGrpEMTmMaxDelayDuration INTEGER,
    ccasGrpEMTmMinDelayPulseWidth INTEGER,
    ccasGrpEMTmDigitDuration INTEGER,
    ccasGrpEMTmInterDigitDuration INTEGER,
    ccasGrpEMTmPulseRate INTEGER,
    ccasGrpEMTmPulseInterDigitDuration INTEGER
    }

ccasGrpEMTmClearWaitDuration OBJECT-TYPE
    SYNTAX INTEGER(200..2000)
--  Units
--    milliseconds
    ACCESS read-write
    STATUS mandatory
    DESCRIPTION
        "Time of Inactive incoming seizure signal to declare call
         cleared.
         This object is relevant to the interfaces in the CAS
         group if the ccasGrpCfgType object is emWinkStart(1) or
         emWinkStartFgd(2).
         The default value of this object is 400 milliseconds."
    ::= { ccasGrpEMTmEntry 1 }

ccasGrpEMTmMaxWinkWaitDuration OBJECT-TYPE
    SYNTAX INTEGER(100..5000)
--  Units
--    milliseconds
    ACCESS read-write
    STATUS mandatory
    DESCRIPTION
        "Maximum wink wait duration for sending out wink start
         signaling. 
         This object is relevant to the interfaces in the CAS
         group if the ccasGrpCfgType object
         is emWinkStart(1) or emWinkStartFgd(2).
         The default value of this object is 200 milliseconds."
    ::= { ccasGrpEMTmEntry 2 }

ccasGrpEMTmMaxWinkDuration OBJECT-TYPE
    SYNTAX INTEGER(100..3000)
--  Units
--    milliseconds
    ACCESS read-write
    STATUS mandatory
    DESCRIPTION
        "Maximum wink duration for sending out wink start
         signaling.
         This object is relevant to the interfaces in the CAS 
         group if the ccasGrpCfgType object is emWinkStart(1)
         or emWinkStartFgd(2).
         The default value of this object is 200 milliseconds."
    ::= { ccasGrpEMTmEntry 3 }

ccasGrpEMTmDelayStart OBJECT-TYPE
    SYNTAX INTEGER(20..2000)
--  Units
--    milliseconds
    ACCESS read-write
    STATUS mandatory
    DESCRIPTION
        "Timing of generation of outgoing delayed start signal
         from detection of incoming seizure. 
         This object is relevant to the interfaces of the CAS
         group if the ccasGrpCfgType object is emDelayDial(4).
         The default value of this object is 300 milliseconds."
    ::= { ccasGrpEMTmEntry 4 }

ccasGrpEMTmMaxDelayDuration OBJECT-TYPE
    SYNTAX INTEGER(100..5000)
--  Units
--    milliseconds
    ACCESS read-write
    STATUS mandatory
    DESCRIPTION
        "Maximum delay signal duration for sending out delay dial
         signaling. 
         This object is relevant to the interfaces in the CAS
         group if the ccasGrpCfgType object is emDelayDial(4).
         The default value of this object is 2000 milliseconds."
    ::= { ccasGrpEMTmEntry 5 }

ccasGrpEMTmMinDelayPulseWidth OBJECT-TYPE
    SYNTAX INTEGER(0|140..5000)
--  Units
--    milliseconds
    ACCESS read-write
    STATUS mandatory
    DESCRIPTION
        "Minimum delay-dial pulse duration for incoming call.
         If the value of this object is 0, then no delay-dial
         is sent to the far end for the incoming call.
         This object is relevant to the interfaces in the CAS
         group if the ccasGrpCfgType object is emDelayDial(4).
         The default value of this object is 140 milliseconds."
    ::= { ccasGrpEMTmEntry 6 }

ccasGrpEMTmDigitDuration OBJECT-TYPE
    SYNTAX INTEGER(50..500)
--  Units
--    milliseconds
    ACCESS read-write
    STATUS mandatory
    DESCRIPTION
        "Outgoing DTMF/MF digit duration in milliseconds.
         This object is not relevant to the addressing timing of
         the interfaces in the CAS group if ccasGrpCfgDialType
         is dtmf or R2 tone.
         The default value of this object is 100 milliseconds."
    ::= { ccasGrpEMTmEntry 7 }

ccasGrpEMTmInterDigitDuration OBJECT-TYPE
    SYNTAX INTEGER(50..500)
--  Units
--    milliseconds
    ACCESS read-write
    STATUS mandatory
    DESCRIPTION
        "Outgoing DTMF/MF inter-digit duration in milliseconds.
         This object is not relevant to the addressing timing of
         the interfaces in the CAS group if ccasGrpCfgDialType
         is dtmf or R2 tone.
         The default value of this object is 100 milliseconds."
    ::= { ccasGrpEMTmEntry 8 }

ccasGrpEMTmPulseRate OBJECT-TYPE
    SYNTAX INTEGER(10..20)
--  Units
--    pulses per second
    ACCESS read-write
    STATUS mandatory
    DESCRIPTION
        "Outgoing Pulse dialing rate in pulses per second (pps).
         This object is relevant to the addressing timing of the
         interfaces in the CAS group only if ccasGrpCfgDialType
         is pulse.
         The default value of this object is 10 pps."
    ::= { ccasGrpEMTmEntry 9 }

ccasGrpEMTmPulseInterDigitDuration OBJECT-TYPE
    SYNTAX INTEGER(100..1000)
--  Units
--    milliseconds
    ACCESS read-write
    STATUS mandatory
    DESCRIPTION
        "Outgoing Pulse dialing inter-digit timing in
         milliseconds.
         This object is relevant to the addressing timing of the
         interfaces in the CAS group only if ccasGrpCfgDialType
         is pulse.
         The default value of this object is 500 milliseconds."
    ::= { ccasGrpEMTmEntry 10 }

ccasGrpLineCfgTable OBJECT-TYPE
    SYNTAX SEQUENCE OF CcasGrpLineCfgEntry
    ACCESS not-accessible
    STATUS mandatory
    DESCRIPTION
        "The CAS Group FXS/SAS Standard Configuration Table.  It
         contains the CAS FXS/SAS group standard configuration
         information of T1/E1."
    ::= { ccasGrpLineObjects 1 }

ccasGrpLineCfgEntry OBJECT-TYPE
    SYNTAX CcasGrpLineCfgEntry
    ACCESS not-accessible
    STATUS mandatory
    DESCRIPTION
        "An entry in the configuration table for each CAS
         FXS/SAS Group in the T1/E1.
         The entry is created when the ccasGrpCfgType is
         configured as 'fxs' or 'sas' on a T1/E1 via
         configuration command. The entry is deleted when the
         CAS Group is de-configured from T1/E1."
    INDEX { ifIndex, ccasGrpCfgIndex }
    ::= { ccasGrpLineCfgTable 1 }

CcasGrpLineCfgEntry ::= SEQUENCE {
    ccasGrpLineCfgNumberRings INTEGER,
    ccasGrpLineCfgSupDisconnect TruthValue,
    ccasGrpLineCfgDialType INTEGER
    }

ccasGrpLineCfgNumberRings OBJECT-TYPE
    SYNTAX INTEGER(0..10)
--  Units
--    rings
    ACCESS read-write
    STATUS mandatory
    DESCRIPTION
        "The number of rings detected before closing loop.
         If the value of this object is 0, then the managed
         system answers immediately after the interface detects
         a incoming seizure if the ccasGrpCfgType is
         'fxsGroundStart' or 'sasGroundStart'.
        
         The default value of this object is 1 ring."
    ::= { ccasGrpLineCfgEntry 1 }

ccasGrpLineCfgSupDisconnect OBJECT-TYPE
    SYNTAX TruthValue
--    Rsyntax INTEGER {
--        true(1),
--        false(2)
--        }
    ACCESS read-write
    STATUS mandatory
    DESCRIPTION
        " Specifies whether a supervisory disconnect signal will 
          be presented to the interface when the connected party
          at the interface hangs up. this object is only relevant
          to the ccasGrpCfgType is fxsLoopStart or sasLoopStart.
          The default value of this object is 'true'."
    ::= { ccasGrpLineCfgEntry 2 }

ccasGrpLineCfgDialType OBJECT-TYPE
    SYNTAX INTEGER {
        dtmf(1),
        pulse(2)
        }
    ACCESS read-write
    STATUS mandatory
    DESCRIPTION
        "Specify the addressing type of the CAS group.
         dtmf  - Dual Tone Multi-Frequency (DTMF) digit.
         pulse - dial pulse.
         The default value of this object is dtmf(1)."
    ::= { ccasGrpLineCfgEntry 3 }

ccasGrpLineTmTable OBJECT-TYPE
    SYNTAX SEQUENCE OF CcasGrpLineTmEntry
    ACCESS not-accessible
    STATUS mandatory
    DESCRIPTION
        "The FXS/SAS interface Timing Parameters table. It
         contains the configuration of the various FXS/SAS
         signaling protocol timing parameters."
    ::= { ccasGrpLineObjects 2 }

ccasGrpLineTmEntry OBJECT-TYPE
    SYNTAX CcasGrpLineTmEntry
    ACCESS not-accessible
    STATUS mandatory
    DESCRIPTION
        "An entry in the FXS/SAS Timing Parameters Table for
         each FXS/SAS interface."
    INDEX { ifIndex, ccasGrpCfgIndex }
-- Augments ccasGrpLineCfgEntry
    ::= { ccasGrpLineTmTable 1 }

CcasGrpLineTmEntry ::= SEQUENCE {
    ccasGrpLineTmDigitDuration INTEGER,
    ccasGrpLineTmInterDigitDuration INTEGER,
    ccasGrpLineTmPulseRate INTEGER,
    ccasGrpLineTmPulseInterDigitDuration INTEGER
    }

ccasGrpLineTmDigitDuration OBJECT-TYPE
    SYNTAX INTEGER(50..500)
--  Units
--    milliseconds
    ACCESS read-write
    STATUS mandatory
    DESCRIPTION
        "Outgoing DTMF digit duration in milliseconds.
         This object is not relevant to the addressing timing of
         the interfaces in the CAS group if ccasGrpLineCfgDialType
         is dtmf.
         The default value of this object is 100 milliseconds."
    ::= { ccasGrpLineTmEntry 1 }

ccasGrpLineTmInterDigitDuration OBJECT-TYPE
    SYNTAX INTEGER(50..500)
--  Units
--    milliseconds
    ACCESS read-write
    STATUS mandatory
    DESCRIPTION
        "Outgoing DTMF inter-digit duration in milliseconds.
         This object is not relevant to the addressing timing
         of the interfaces in the CAS group if
         ccasGrpLineCfgDialType is dtmf.
         The default value of this object is 100 milliseconds."
    ::= { ccasGrpLineTmEntry 2 }

ccasGrpLineTmPulseRate OBJECT-TYPE
    SYNTAX INTEGER(10..20)
--  Units
--    pulses per second
    ACCESS read-write
    STATUS mandatory
    DESCRIPTION
        "Outgoing Pulse dialing rate in pulses per second (pps).
         This object is relevant to the addressing timing of the
         interfaces in the CAS group only if ccasGrpStaCfgDialType
         is pulse.
         The default value of this object is 10 pps."
    ::= { ccasGrpLineTmEntry 3 }

ccasGrpLineTmPulseInterDigitDuration OBJECT-TYPE
    SYNTAX INTEGER(100..1000)
--  Units
--    milliseconds
    ACCESS read-write
    STATUS mandatory
    DESCRIPTION
        "Outgoing Pulse dialing inter-digit timing in
         milliseconds. This object is relevant to the addressing
         timing of the interfaces in the CAS group only if
         ccasGrpStaCfgDialType is pulse.
         The default value of this object is 500 milliseconds."
    ::= { ccasGrpLineTmEntry 4 }

ccasGrpStaCfgTable OBJECT-TYPE
    SYNTAX SEQUENCE OF CcasGrpStaCfgEntry
    ACCESS not-accessible
    STATUS mandatory
    DESCRIPTION
        "The FXO/SAO standard configuration table. It contains
         FXO/SAO configuration parameters, one entry per FXO/SAO
         interface.
         The configuration information of this table is set by 
         its default setting when the CAS group is created by 
         the configuration commands."
    ::= { ccasGrpStaObjects 1 }

ccasGrpStaCfgEntry OBJECT-TYPE
    SYNTAX CcasGrpStaCfgEntry
    ACCESS not-accessible
    STATUS mandatory
    DESCRIPTION
        "An entry in the standard configuration table for
         each FXO/SAO Group.
         The entry is created when the ccasGrpCfgType is
         configured as 'fxo' or 'sao' on a T1/E1 via
         configuration command. The entry is deleted when the
         CAS Group is de-configured from T1/E1."
    INDEX { ifIndex, ccasGrpCfgIndex }
    ::= { ccasGrpStaCfgTable 1 }

CcasGrpStaCfgEntry ::= SEQUENCE {
    ccasGrpStaCfgNumberRings INTEGER,
    ccasGrpStaCfgDialType INTEGER
    }

ccasGrpStaCfgNumberRings OBJECT-TYPE
    SYNTAX INTEGER(0..1000)
--  Units
--    rings
    ACCESS read-write
    STATUS mandatory
    DESCRIPTION
        "The number of rings sent before sending reorder to the
         originator and releasing resources.
         If the value of this object is 0, then sending
         reorder to the originator is disabled. 
         The default value of this object is 20 rings."
    ::= { ccasGrpStaCfgEntry 1 }

ccasGrpStaCfgDialType OBJECT-TYPE
    SYNTAX INTEGER {
        dtmf(1),
        pulse(2)
        }
    ACCESS read-write
    STATUS mandatory
    DESCRIPTION
        "Specify the addressing type of the CAS group.
         dtmf  - Dual Tone Multi-Frequency (DTMF) digit.
         pulse - dial pulse.
         The default value of this object is dtmf(1)."
    ::= { ccasGrpStaCfgEntry 2 }

ccasGrpStaTmTable OBJECT-TYPE
    SYNTAX SEQUENCE OF CcasGrpStaTmEntry
    ACCESS not-accessible
    STATUS mandatory
    DESCRIPTION
        "The FXO/SAO interface Timing Parameters table. It 
         contains the configuration of the various FXO/SAO
         signaling protocol timing parameters."
    ::= { ccasGrpStaObjects 2 }

ccasGrpStaTmEntry OBJECT-TYPE
    SYNTAX CcasGrpStaTmEntry
    ACCESS not-accessible
    STATUS mandatory
    DESCRIPTION
        "An entry in the FXO/SAO Timing Parameters Table for
         each FXO/SAO interface."
    INDEX { ifIndex, ccasGrpCfgIndex }
-- Augments ccasGrpStaCfgEntry
    ::= { ccasGrpStaTmTable 1 }

CcasGrpStaTmEntry ::= SEQUENCE {
    ccasGrpStaTmDigitDuration INTEGER,
    ccasGrpStaTmInterDigitDuration INTEGER,
    ccasGrpStaTmPulseRate INTEGER,
    ccasGrpStaTmPulseInterDigitDuration INTEGER
    }

ccasGrpStaTmDigitDuration OBJECT-TYPE
    SYNTAX INTEGER(50..500)
--  Units
--    milliseconds
    ACCESS read-write
    STATUS mandatory
    DESCRIPTION
        "Outgoing DTMF digit duration in milliseconds.
         This object is not relevant to the addressing timing of
         the interfaces in the CAS group if ccasGrpStaCfgDialType
         is dtmf.
         The default value of this object is 100 milliseconds."
    ::= { ccasGrpStaTmEntry 1 }

ccasGrpStaTmInterDigitDuration OBJECT-TYPE
    SYNTAX INTEGER(50..500)
--  Units
--    milliseconds
    ACCESS read-write
    STATUS mandatory
    DESCRIPTION
        "Outgoing DTMF inter-digit duration in milliseconds.
         This object is not relevant to the addressing timing of
         the interfaces in the CAS group if ccasGrpStaCfgDialType
         is dtmf.
         The default value of this object is 100 milliseconds."
    ::= { ccasGrpStaTmEntry 2 }

ccasGrpStaTmPulseRate OBJECT-TYPE
    SYNTAX INTEGER(10..20)
--  Units
--    pulses per second
    ACCESS read-write
    STATUS mandatory
    DESCRIPTION
        "Outgoing Pulse dialing rate in pulses per second (pps).
         This object is relevant to the addressing timing of the
         interfaces in the CAS group only if ccasGrpStaCfgDialType
         is pulse.
         The default value of this object is 10 pps."
    ::= { ccasGrpStaTmEntry 3 }

ccasGrpStaTmPulseInterDigitDuration OBJECT-TYPE
    SYNTAX INTEGER(100..1000)
--  Units
--    milliseconds
    ACCESS read-write
    STATUS mandatory
    DESCRIPTION
        "Outgoing Pulse dialing inter-digit timing in
         milliseconds. This object is relevant to the addressing
         timing of the interfaces in the CAS group only if
         ccasGrpStaCfgDialType is pulse.
         The default value of this object is 500 milliseconds."
    ::= { ccasGrpStaTmEntry 4 }

ccasGrpABCDCfgTable OBJECT-TYPE
    SYNTAX SEQUENCE OF CcasGrpABCDCfgEntry
    ACCESS not-accessible
    STATUS mandatory
    DESCRIPTION
        "The CAS group custom ABCD bits configuration table for
         E1. It contains A/B/C/D bits handling objects, one
         entry per CAS group on an E1 interface."
    ::= { ccasGrpABCDObjects 1 }

ccasGrpABCDCfgEntry OBJECT-TYPE
    SYNTAX CcasGrpABCDCfgEntry
    ACCESS not-accessible
    STATUS mandatory
    DESCRIPTION
        "An entry in the custom ABCD configuration table for
         each CAS Group on an E1 interface.
         The entry is created when a CAS group is configured
         on a E1. The entry is deleted when the CAS Group is 
         de-configured from E1."
    INDEX { ifIndex, ccasGrpCfgIndex }
    ::= { ccasGrpABCDCfgTable 1 }

CcasGrpABCDCfgEntry ::= SEQUENCE {
    ccasGrpABCDCfgInvertBits OCTET STRING,
    ccasGrpABCDCfgUnusedBits OCTET STRING
    }

ccasGrpABCDCfgInvertBits OBJECT-TYPE
    SYNTAX OCTET STRING(SIZE(1..2))
        -- BITS are:
        --   dBit(0)
        --   cBit(1)
        --   bBit(2)
        --   aBit(3)
    ACCESS read-write
    STATUS mandatory
    DESCRIPTION
        "Specify the A/B/C/D bit mask to invert the A/B/C/D bits
         value before the A/B/C/D bits are sent or
         after the A/B/C/D bits are received. 
         1-bit  - enable bit inversion.
         0-bit  - disable bit inversion.
         The default value of this object is '00'H "
    ::= { ccasGrpABCDCfgEntry 1 }

ccasGrpABCDCfgUnusedBits OBJECT-TYPE
    SYNTAX OCTET STRING(SIZE(1..2))
        -- BITS are:
        --   dBit(0)
        --   cBit(1)
        --   bBit(2)
        --   aBit(3)
    ACCESS read-write
    STATUS mandatory
    DESCRIPTION
        "Specify the Unused A/B/C/D bit values to transmit.
         If any A/B/C/D bit is unused, the bit values in this
         object will be used to transmit for the unused 
         A/B/C/D bits.
         The default value of this object is '00'H "
    ::= { ccasGrpABCDCfgEntry 2 }

ccasChannelCfgTable OBJECT-TYPE
    SYNTAX SEQUENCE OF CcasChannelCfgEntry
    ACCESS not-accessible
    STATUS mandatory
    DESCRIPTION
        "The CAS channel Standard Configuration Table.  It
         contains the standard configuration information of CAS
         channel of T1/E1."
    ::= { ccasChannelObjects 1 }

ccasChannelCfgEntry OBJECT-TYPE
    SYNTAX CcasChannelCfgEntry
    ACCESS not-accessible
    STATUS mandatory
    DESCRIPTION
        "An entry in the configuration table for each CAS
         channel. The entry is created when a CAS channel is
         configured on a T1/E1 via configuration command. The
         entry is deleted when the CAS channel is de-configured
         from T1/E1."
    INDEX { ifIndex }
    ::= { ccasChannelCfgTable 1 }

CcasChannelCfgEntry ::= SEQUENCE {
    ccasChannelCfgDS1IfIndex InterfaceIndex,
    ccasChannelCfgGroup INTEGER,
    ccasChannelCfgTimeSlot INTEGER,
    ccasChannelCfgBusyOut TruthValue
    }

ccasChannelCfgDS1IfIndex OBJECT-TYPE
    SYNTAX InterfaceIndex
--    Rsyntax INTEGER(1..2147483647)
    ACCESS read-only
    STATUS mandatory
    DESCRIPTION
        "the ifIndex of this CAS channel associated T1/E1.     "
    ::= { ccasChannelCfgEntry 1 }

ccasChannelCfgGroup OBJECT-TYPE
    SYNTAX INTEGER(0..30)
    ACCESS read-only
    STATUS mandatory
    DESCRIPTION
        "The CAS channel associated CAS group number."
    ::= { ccasChannelCfgEntry 2 }

ccasChannelCfgTimeSlot OBJECT-TYPE
    SYNTAX INTEGER(1..31)
    ACCESS read-only
    STATUS mandatory
    DESCRIPTION
        "The CAS channel associated T1/E1 timeslot."
    ::= { ccasChannelCfgEntry 3 }

ccasChannelCfgBusyOut OBJECT-TYPE
    SYNTAX TruthValue
--    Rsyntax INTEGER {
--        true(1),
--        false(2)
--        }
    ACCESS read-write
    STATUS mandatory
    DESCRIPTION
        "The CAS channel busyout configuration.
         true  - the CAS channel is busied out.     
         false - the CAS is normal.
         The default value for this object is 'false'."
    ::= { ccasChannelCfgEntry 4 }

ccasChannelStatusTable OBJECT-TYPE
    SYNTAX SEQUENCE OF CcasChannelStatusEntry
    ACCESS not-accessible
    STATUS mandatory
    DESCRIPTION
        "The CAS channel Status Table.  It contains general 
         information about the status of CAS channel."
    ::= { ccasChannelObjects 2 }

ccasChannelStatusEntry OBJECT-TYPE
    SYNTAX CcasChannelStatusEntry
    ACCESS not-accessible
    STATUS mandatory
    DESCRIPTION
        "An entry in the status table for each CAS channel. "
    INDEX { ifIndex }
-- Augments ccasChannelCfgEntry
    ::= { ccasChannelStatusTable 1 }

CcasChannelStatusEntry ::= SEQUENCE {
    ccasChannelStatusRecvSignalBits OCTET STRING,
    ccasChannelStatusBusyOut TruthValue,
    ccasChannelStatusInfoType INTEGER,
    ccasChannelStatusXmitSignalBits OCTET STRING
    }

ccasChannelStatusRecvSignalBits OBJECT-TYPE
    SYNTAX OCTET STRING(SIZE(1..2))
        -- BITS are:
        --   dBit(0)
        --   cBit(1)
        --   bBit(2)
        --   aBit(3)
    ACCESS read-only
    STATUS mandatory
    DESCRIPTION
        "The receive ABCD signaling bits for the CAS channel.
         aBit  - the signaling bit in the 6th frame
         bBit  - the signaling bit in the 12th frame
         cBit  - the signaling bit in the 18th frame
         dBit  - the signaling bit in the 24th frame
         the cBit and dBit are only valid for E1 or T1
         interface is operating in extended superframe (ESF)
         mode."
    REFERENCE
        "EIA/TIA-464B, chapter 6.2 Digital Signaling and Supervision"
    ::= { ccasChannelStatusEntry 1 }

ccasChannelStatusBusyOut OBJECT-TYPE
    SYNTAX TruthValue
--    Rsyntax INTEGER {
--        true(1),
--        false(2)
--        }
    ACCESS read-only
    STATUS mandatory
    DESCRIPTION
        "The CAS channel busyout state.
         true  - the CAS channel is busied out.     
         false - the CAS is normal."
    ::= { ccasChannelStatusEntry 2 }

ccasChannelStatusInfoType OBJECT-TYPE
    SYNTAX INTEGER {
        unknown(1),
        speech(2),
        data56(3),
        audio31(4),
        audio7(5),
        video(6),
        fax(7),
        modem(8)
        }
    ACCESS read-only
    STATUS mandatory
    DESCRIPTION
        "The Information Transfer Capability for the current
         or last call.
        
         unknown  - If since system startup there has been no call
                    on this interface, this object has a value of
                    unknown(1).
         speech   - refers to a non-data connection
         data56   - 56k data.
         audio31  - audio 3.1 kHz; refers to data mode connections
         audio7   - audio 7 kHz; refer to data mode connections;
                    'Unrestricted digital information with tones/
                    announcements'.
         video    - as defined in Q.931
         fax      - Facsimile
         modem    - V.3x modem"
    REFERENCE
        "Q.931 [8], chapter 4.5.5, octet 3 of bearer capability
         information element, combined with the User Rate
         (as defined in octets 5 and 5a to 5d), if rate adoption
         is being used."
    ::= { ccasChannelStatusEntry 3 }

ccasChannelStatusXmitSignalBits OBJECT-TYPE
    SYNTAX OCTET STRING(SIZE(1..2))
        -- BITS are:
        --   dBit(0)
        --   cBit(1)
        --   bBit(2)
        --   aBit(3)
    ACCESS read-only
    STATUS mandatory
    DESCRIPTION
        "The transmit ABCD signaling bits for the CAS channel.
         aBit  - the signaling bit in the 6th frame
         bBit  - the signaling bit in the 12th frame
         cBit  - the signaling bit in the 18th frame
         dBit  - the signaling bit in the 24th frame
         the cBit and dBit are only valid for E1 or T1 
         interface is operating in extended superframe (ESF)
         mode."
    REFERENCE
        "EIA/TIA-464B, chapter 6.2 Digital Signaling and Supervision"
    ::= { ccasChannelStatusEntry 4 }

ccasVoiceCfgTable OBJECT-TYPE
    SYNTAX SEQUENCE OF CcasVoiceCfgEntry
    ACCESS not-accessible
    STATUS mandatory
    DESCRIPTION
        "The voice specific configuration Table. It contains
         information about the voice related configuration
         parameters for a CAS group."
    ::= { ccasVoiceCfgObjects 1 }

ccasVoiceCfgEntry OBJECT-TYPE
    SYNTAX CcasVoiceCfgEntry
    ACCESS not-accessible
    STATUS mandatory
    DESCRIPTION
        "An entry in the voice specific configuration table for each 
         CAS/DS0 group of a DS1.
         The entry is created if the associated CAS/DS0 group is
         created and the voice hardware is detected to support the
         voice capability for the CAS/DS0 group in the managed
         system.
         The entry is deleted when its associated CAS/DS0 group is
         deleted."
    INDEX { ifIndex, ccasGrpCfgIndex }
    ::= { ccasVoiceCfgTable 1 }

CcasVoiceCfgEntry ::= SEQUENCE {
    ccasVoiceCfgNoiseRegEnable TruthValue,
    ccasVoiceCfgNonLinearProcEnable TruthValue,
    ccasVoiceCfgMusicOnHoldThreshold INTEGER,
    ccasVoiceCfgInGain INTEGER,
    ccasVoiceCfgOutAttn INTEGER,
    ccasVoiceCfgEchoCancelEnable TruthValue,
    ccasVoiceCfgEchoCancelCoverage INTEGER,
    ccasVoiceCfgConnectionMode INTEGER,
    ccasVoiceCfgConnectionNumber DisplayString,
    ccasVoiceCfgInitialDigitTimeOut INTEGER,
    ccasVoiceCfgInterDigitTimeOut INTEGER,
    ccasVoiceCfgRegionalTone CountryCode
    }

ccasVoiceCfgNoiseRegEnable OBJECT-TYPE
    SYNTAX TruthValue
--    Rsyntax INTEGER {
--        true(1),
--        false(2)
--        }
    ACCESS read-write
    STATUS mandatory
    DESCRIPTION
        "The object indicates whether or not the background noise
         should be played to fill silence gaps if VAD is activated.
         The default value of this object is 'true'."
    ::= { ccasVoiceCfgEntry 1 }

ccasVoiceCfgNonLinearProcEnable OBJECT-TYPE
    SYNTAX TruthValue
--    Rsyntax INTEGER {
--        true(1),
--        false(2)
--        }
    ACCESS read-write
    STATUS mandatory
    DESCRIPTION
        "The object indicates whether or not the Nonlinear Processing
         is enabled for the interface.
         The default value of this object is 'true'."
    ::= { ccasVoiceCfgEntry 2 }

ccasVoiceCfgMusicOnHoldThreshold OBJECT-TYPE
    SYNTAX INTEGER(-70..-30)
--  Units
--    dBm
    ACCESS read-write
    STATUS mandatory
    DESCRIPTION
        "The object specifies the Music On Hold Threshold for
         the interface.
         The default value of this object is -38 dBm."
    ::= { ccasVoiceCfgEntry 3 }

ccasVoiceCfgInGain OBJECT-TYPE
    SYNTAX INTEGER(-6..14)
--  Units
--    dB
    ACCESS read-write
    STATUS mandatory
    DESCRIPTION
        "This object contains the amount of gain inserted at the
         receiver side of the interface. The input gain settings
         only define a gain/loss relative to the 0 dB setting.
         The absolute loss at the 0 dB setting could be
         implementation dependent based on the desired network
         loss plan.
         The default value of this object is 0 dB (decibel)."
    ::= { ccasVoiceCfgEntry 4 }

ccasVoiceCfgOutAttn OBJECT-TYPE
    SYNTAX INTEGER(0..14)
--  Units
--    dB
    ACCESS read-write
    STATUS mandatory
    DESCRIPTION
        "This object contains the amount of attenuation inserted
         at the transmit side of the interface. 
         The output attenuation settings only define a loss 
         relative to the 0 dB setting.
         The absolute loss at the 0 dB setting could be
         implementation dependent based on the desired network
         loss plan.
         The default value of this object is 0 dB (decibel)."
    ::= { ccasVoiceCfgEntry 5 }

ccasVoiceCfgEchoCancelEnable OBJECT-TYPE
    SYNTAX TruthValue
--    Rsyntax INTEGER {
--        true(1),
--        false(2)
--        }
    ACCESS read-write
    STATUS mandatory
    DESCRIPTION
        "The object specifies whether or not the Echo Cancellation 
         is enabled for the interface.
         The default value of this object is 'true'."
    ::= { ccasVoiceCfgEntry 6 }

ccasVoiceCfgEchoCancelCoverage OBJECT-TYPE
    SYNTAX INTEGER {
        echoCanceller8ms(1),
        echoCanceller16ms(2),
        echoCanceller24ms(3),
        echoCanceller32ms(4),
        echoCanceller64ms(5),
        echoCanceller128ms(6)
        }
    ACCESS read-write
    STATUS mandatory
    DESCRIPTION
        "The object specifies the Echo Canceller coverage for
         the interface. This object is valid if the
         ccasVoiceCfgEchoCancelEnable object is 'true'.
         echoCanceller8ms  -  8 milliseconds echo canceller coverage.
         echoCanceller16ms - 16 milliseconds echo canceller coverage.
         echoCanceller24ms - 24 milliseconds echo canceller coverage.
         echoCanceller32ms - 32 milliseconds echo canceller coverage.
         echoCanceller64ms -
                           64 milliseconds echo canceller coverage.
         echoCanceller128ms-
                          128 milliseconds echo canceller coverage.
         The default value of this object is echoCanceller8ms."
    ::= { ccasVoiceCfgEntry 7 }

ccasVoiceCfgConnectionMode OBJECT-TYPE
    SYNTAX INTEGER {
        normal(1),
        trunk(2),
        plar(3)
        }
    ACCESS read-write
    STATUS mandatory
    DESCRIPTION
        "The object indicates the connection mode of the interface.
         normal - the interface acts normally to handle incoming
                  and outgoing call.
         trunk  - the interface acts in trunking mode. trunking mode
                  causes two interfaces (on either the same or
                  different routers) to be always conferenced
                  together, and for telephony signaling to be
                  passed transparently through the VoIP system
                  rather than trapped and interpreted by the session
                  application on the router(s).
         plar   - the interface acts in PLAR (private line automatic
                  ringdown) mode. PLAR is handled by associating a
                  peer directly with an interface such that when the
                  interface goes off-hook, that peer is used to setup
                  the second call leg and conference them together
                  without the caller having to dial any digits."
    ::= { ccasVoiceCfgEntry 8 }

ccasVoiceCfgConnectionNumber OBJECT-TYPE
    SYNTAX DisplayString(SIZE(0..32))
--    Rsyntax OCTET STRING(SIZE(0..32))
    ACCESS read-write
    STATUS mandatory
    DESCRIPTION
        "This is the E.164 phone number that is used to 
         establish connection with trunking mode or PLAR mode.
         If the ccasVoiceCfgConnectionMode is 'normal', then  this
         object will be a zero length string."
    ::= { ccasVoiceCfgEntry 9 }

ccasVoiceCfgInitialDigitTimeOut OBJECT-TYPE
    SYNTAX INTEGER(0..120)
--  Units
--    seconds
    ACCESS read-write
    STATUS mandatory
    DESCRIPTION
        "This is the initial digit timeout that indicates the amount
         of time the managed system waits for an initial input digit
         from the caller. The timer is activated when the call is
         accepted and is deactivated upon digit input. If the timer
         expires, the caller is signaled through the appropriate
         tone and the call is abandoned. The value of zero disables
         the timer.
         The default value of this object is 10 seconds."
    ::= { ccasVoiceCfgEntry 10 }

ccasVoiceCfgInterDigitTimeOut OBJECT-TYPE
    SYNTAX INTEGER(0..120)
--  Units
--    seconds
    ACCESS read-write
    STATUS mandatory
    DESCRIPTION
        "This is the inter-digit timeout that indicates the amount
         of time the managed system waits for a subsequent input
         digit from the caller. The timer is started upon receipt of
         an input digit and restarted as each digit is received
         until the destination address is identified. If the timer
         expires and no destination address is identified, the
         caller is signaled through the appropriate tone and the
         call is abandoned. The value of zero disables the timer.
         The default value of this object is 10 seconds."
    ::= { ccasVoiceCfgEntry 11 }

ccasVoiceCfgRegionalTone OBJECT-TYPE
    SYNTAX CountryCode
--    Rsyntax OCTET STRING(SIZE(0|2))
    ACCESS read-write
    STATUS mandatory
    DESCRIPTION
        "This object contains the current regional setting for
         the call progress tone to be used by this CAS group."
    ::= { ccasVoiceCfgEntry 12 }

ccasXgcpCfgTable OBJECT-TYPE
    SYNTAX SEQUENCE OF CcasXgcpCfgEntry
    ACCESS not-accessible
    STATUS mandatory
    DESCRIPTION
        "The XGCP configuration Table contains
         information about DS0 usage by XGCP(SGCP/MGCP).  
        
         XGCP is meant to represent both Simple Gateway Control
         Protocol (SGCP) and Media Gateway Control Protocol (MGCP)."
    ::= { ccasXgcpCfgObjects 1 }

ccasXgcpCfgEntry OBJECT-TYPE
    SYNTAX CcasXgcpCfgEntry
    ACCESS not-accessible
    STATUS mandatory
    DESCRIPTION
        "An entry in the configuration table for each 
         DS0 group of a DS1.
        
         The entry is created if the DS0 group is configured as   
         null-signaling and ccasGrpCfgServiceType is configured
         as either sgcp or mgcp.
        
         The entry is deleted when the signaling type is configured 
         as non null-signaling."
    INDEX { ifIndex, ccasGrpCfgIndex }
    ::= { ccasXgcpCfgTable 1 }

CcasXgcpCfgEntry ::= SEQUENCE {
    ccasXgcpCfgCotToneCo1 INTEGER,
    ccasXgcpCfgCotToneCo2 INTEGER
    }

ccasXgcpCfgCotToneCo1 OBJECT-TYPE
    SYNTAX INTEGER(280..3800)
--  Units
--    hertz
    ACCESS read-write
    STATUS mandatory
    DESCRIPTION
        "This object specifies the continuity test tone
         frequencies for co1. Co1 is the COT tone frequency from
         the terminating switch in transponder mode and is from
         the originating switch in loopback mode."
    REFERENCE
        "Bellcore GR-317-CORE spec, Rev 3, Nov. 1996, section
         3.1.1.3. "
    ::= { ccasXgcpCfgEntry 1 }

ccasXgcpCfgCotToneCo2 OBJECT-TYPE
    SYNTAX INTEGER(280..3800)
--  Units
--    hertz
    ACCESS read-write
    STATUS mandatory
    DESCRIPTION
        "This object specifies the continuity test tone
         frequencies for co2. Co2 is the COT tone frequency from
         the originating switch only in transponder mode.  "
    REFERENCE
        "Bellcore GR-317-CORE spec, Rev 3, Nov. 1996, section
         3.1.1.3. "
    ::= { ccasXgcpCfgEntry 2 }

ccasIfDS1Group OBJECT IDENTIFIER ::= { ccasIfMIBGroups 1 }
-- OBJECT-GROUP
--  Status
--    mandatory
--  Descr
--    The collection of objects providing CAS/DS0 related 
--     T1/E1 information.
--  objects
--    ccasDs1IfCfgDs0ChannelsConfigurable

ccasGeneralInfoGroup OBJECT IDENTIFIER ::= { ccasIfMIBGroups 2 }
-- OBJECT-GROUP
--  Status
--    obsolete
--  Descr
--    A collection of objects providing general information
--     applicable to Channel Associated Signaling interfaces.
--  objects
--    ccasGrpCfgType, ccasGrpCfgDs0Channels, ccasGrpCfgRowStatus, 
--    ccasChannelCfgDS1IfIndex, ccasChannelCfgGroup, 
--    ccasChannelCfgTimeSlot, ccasChannelCfgBusyOut, 
--    ccasChannelStatusRecvSignalBits, ccasChannelStatusBusyOut, 
--    ccasChannelStatusInfoType, ccasChannelStatusXmitSignalBits

ccasEMGroup OBJECT IDENTIFIER ::= { ccasIfMIBGroups 3 }
-- OBJECT-GROUP
--  Status
--    mandatory
--  Descr
--    A collection of objects providing information applicable
--     to the CAS E&M signal interfaces.
--  objects
--    ccasGrpEMCfgDialType, ccasGrpEMCfgDnisAni, 
--    ccasGrpEMTmClearWaitDuration, ccasGrpEMTmMaxWinkWaitDuration, 
--    ccasGrpEMTmMaxWinkDuration, ccasGrpEMTmDelayStart, 
--    ccasGrpEMTmMaxDelayDuration, ccasGrpEMTmMinDelayPulseWidth, 
--    ccasGrpEMTmDigitDuration, ccasGrpEMTmInterDigitDuration, 
--    ccasGrpEMTmPulseRate, ccasGrpEMTmPulseInterDigitDuration

ccasLineGroup OBJECT IDENTIFIER ::= { ccasIfMIBGroups 4 }
-- OBJECT-GROUP
--  Status
--    mandatory
--  Descr
--    A collection of objects providing information applicable
--     to the CAS FXS/SAS signal interfaces.
--  objects
--    ccasGrpLineCfgNumberRings, ccasGrpLineCfgSupDisconnect, 
--    ccasGrpLineCfgDialType, ccasGrpLineTmDigitDuration, 
--    ccasGrpLineTmInterDigitDuration, ccasGrpLineTmPulseRate, 
--    ccasGrpLineTmPulseInterDigitDuration

ccasStaGroup OBJECT IDENTIFIER ::= { ccasIfMIBGroups 5 }
-- OBJECT-GROUP
--  Status
--    mandatory
--  Descr
--    A collection of objects providing information applicable
--     to the CAS FXO/SAO signal interfaces.
--  objects
--    ccasGrpStaCfgNumberRings, ccasGrpStaCfgDialType, 
--    ccasGrpStaTmDigitDuration, ccasGrpStaTmInterDigitDuration, 
--    ccasGrpStaTmPulseRate, ccasGrpStaTmPulseInterDigitDuration

ccasCustomABCDGroup OBJECT IDENTIFIER ::= { ccasIfMIBGroups 6 }
-- OBJECT-GROUP
--  Status
--    mandatory
--  Descr
--    A collection of objects providing ABCD bits
--     configuration information applicable to the CAS group
--     on E1 interface.
--  objects
--    ccasGrpABCDCfgInvertBits, ccasGrpABCDCfgUnusedBits

ccasVoiceGroup OBJECT IDENTIFIER ::= { ccasIfMIBGroups 7 }
-- OBJECT-GROUP
--  Status
--    mandatory
--  Descr
--    A collection of objects providing information applicable
--     to the CAS/DS0 group that supports voice capability.
--  objects
--    ccasVoiceCfgNoiseRegEnable, ccasVoiceCfgNonLinearProcEnable, 
--    ccasVoiceCfgMusicOnHoldThreshold, ccasVoiceCfgInGain, 
--    ccasVoiceCfgOutAttn, ccasVoiceCfgEchoCancelEnable, 
--    ccasVoiceCfgEchoCancelCoverage, ccasVoiceCfgConnectionMode, 
--    ccasVoiceCfgConnectionNumber, ccasVoiceCfgInitialDigitTimeOut, 
--    ccasVoiceCfgInterDigitTimeOut, ccasVoiceCfgRegionalTone

ccasGeneralInfoGroupRev1 OBJECT IDENTIFIER ::= { ccasIfMIBGroups 8 }
-- OBJECT-GROUP
--  Status
--    mandatory
--  Descr
--    A collection of objects providing general information
--     applicable to CAS/DS0 interfaces.
--  objects
--    ccasGrpCfgType, ccasGrpCfgDs0Channels, ccasGrpCfgServiceType, 
--    ccasGrpCfgRowStatus

ccasChannelInfoGroup OBJECT IDENTIFIER ::= { ccasIfMIBGroups 9 }
-- OBJECT-GROUP
--  Status
--    mandatory
--  Descr
--    A collection of objects providing channel signaling 
--     information applicable to Channel Associated Signaling 
--     interfaces.
--  objects
--    ccasChannelCfgDS1IfIndex, ccasChannelCfgGroup, 
--    ccasChannelCfgTimeSlot, ccasChannelCfgBusyOut, 
--    ccasChannelStatusRecvSignalBits, ccasChannelStatusBusyOut, 
--    ccasChannelStatusInfoType, ccasChannelStatusXmitSignalBits

ccasXgcpCfgGroup OBJECT IDENTIFIER ::= { ccasIfMIBGroups 10 }
-- OBJECT-GROUP
--  Status
--    mandatory
--  Descr
--    A collection of objects providing XGCP specific 
--     information applicable to DS0.
--  objects
--    ccasXgcpCfgCotToneCo1, ccasXgcpCfgCotToneCo2

ccasIfMIBCompliance OBJECT IDENTIFIER ::= { ccasIfMIBCompliances 1 }
-- MODULE-COMPLIANCE
--  Status
--    obsolete
--  Descr
--    The compliance statement for entities which implement
--     the Cisco Voice Digital interface MIB
--  Module
--    >>current<<
--   MandGroup
--    ccasIfDS1Group
--   MandGroup
--    ccasGeneralInfoGroup
--   OptGroup
--    ccasEMGroup
--   OptGroup
--    ccasLineGroup
--   OptGroup
--    ccasStaGroup
--   OptGroup
--    ccasCustomABCDGroup
--   OptGroup
--    ccasVoiceGroup
--   ObjVar
--    ccasGrpCfgType
--   ObjVar
--    ccasGrpCfgDs0Channels
--   ObjVar
--    ccasGrpCfgRowStatus
--   ObjVar
--    ccasGrpEMCfgDialType
--   ObjVar
--    ccasGrpEMCfgDnisAni
--   ObjVar
--    ccasGrpABCDCfgInvertBits
--   ObjVar
--    ccasGrpABCDCfgUnusedBits
--   ObjVar
--    ccasVoiceCfgNoiseRegEnable
--   ObjVar
--    ccasVoiceCfgNonLinearProcEnable
--   ObjVar
--    ccasVoiceCfgMusicOnHoldThreshold
--   ObjVar
--    ccasVoiceCfgInGain
--   ObjVar
--    ccasVoiceCfgOutAttn
--   ObjVar
--    ccasVoiceCfgEchoCancelEnable
--   ObjVar
--    ccasVoiceCfgEchoCancelCoverage
--   ObjVar
--    ccasVoiceCfgConnectionMode
--   ObjVar
--    ccasVoiceCfgConnectionNumber
--   ObjVar
--    ccasVoiceCfgInitialDigitTimeOut
--   ObjVar
--    ccasVoiceCfgInterDigitTimeOut
--   ObjVar
--    ccasVoiceCfgRegionalTone

ccasIfMIBComplianceRev1 OBJECT IDENTIFIER ::= { ccasIfMIBCompliances 2 }
-- MODULE-COMPLIANCE
--  Status
--    mandatory
--  Descr
--    The compliance statement for entities which implement
--     the Cisco Voice Digital interface MIB
--  Module
--    >>current<<
--   MandGroup
--    ccasIfDS1Group
--   MandGroup
--    ccasGeneralInfoGroupRev1
--   OptGroup
--    ccasEMGroup
--   OptGroup
--    ccasLineGroup
--   OptGroup
--    ccasStaGroup
--   OptGroup
--    ccasCustomABCDGroup
--   OptGroup
--    ccasVoiceGroup
--   OptGroup
--    ccasChannelInfoGroup
--   OptGroup
--    ccasXgcpCfgGroup
--   ObjVar
--    ccasGrpCfgType
--   ObjVar
--    ccasGrpCfgDs0Channels
--   ObjVar
--    ccasGrpCfgRowStatus
--   ObjVar
--    ccasGrpEMCfgDialType
--   ObjVar
--    ccasGrpEMCfgDnisAni
--   ObjVar
--    ccasGrpABCDCfgInvertBits
--   ObjVar
--    ccasGrpABCDCfgUnusedBits


END
