-- MIB file created 02-May-2006 15:23:07, by
--   SMICng version 2.2.11-beta(PRO)(Solaris), January 20, 2001. Enterprise key cisco.com

CISCO-SYSLOG-EXT-MIB DEFINITIONS ::= BEGIN

-- From file: "CISCO-SYSLOG-EXT-MIB.my"
-- Compile options "4 7 F H N O W 03 06 0B 0G 0N 0T"

IMPORTS
    TruthValue, RowStatus
            FROM SNMPv2-TC-v1
    SnmpAdminString
            FROM SNMP-FRAMEWORK-MIB
    InetAddressType, InetAddress, InetPortNumber
            FROM INET-ADDRESS-MIB
    ciscoMgmt
            FROM CISCO-SMI
    SyslogSeverity
            FROM CISCO-SYSLOG-MIB
    Gauge
            FROM RFC1155-SMI
    OBJECT-TYPE
            FROM RFC-1212;

ciscoSyslogExtMIB OBJECT IDENTIFIER ::= { ciscoMgmt 301 }
-- MODULE-IDENTITY
--  LastUpdated
--    200501300000Z
--  OrgName
--    Cisco Systems Inc.
--  ContactInfo
--         Cisco Systems
--          Customer Service
--    Postal: 170 W Tasman Drive
--          San Jose, CA  95134
--          USA
--    Tel: +1 800 553 -NETS
--    E-mail: cs-san@cisco.com
--  Descr
--    MIB module for configuring and monitoring System Log 
--    related management parameters as defined by RFC 3164.
--  RevDate
--    200501300000Z
--  RevDescr
--    - Added SylogProtocol TEXTUAL CONVENTION.
--     - Added following objects in cseSyslogServerTable.
--       cseSyslogServerProtocol
--       cseSyslogServerPort
--       cseSyslogServerProtocolFallback
--  RevDate
--    200409200000Z
--  RevDescr
--    Added new enumerations isns, fccLc, cfs, dstats, ipsec, 
--    dpvm, ike, ddas, scheduler, san ExtTuner to 
--    SyslogExFacility.
--  RevDate
--    200312150000Z
--  RevDescr
--    Added new enumerations to SyslogExFacility.
--  RevDate
--    200211130000Z
--  RevDescr
--    Added cseSyslogServerFacility to cseSyslogServerTable.
--     Added two TCs SyslogFacility and SyslogExFacility.
--  RevDate
--    200210040000Z
--  RevDescr
--    Initial version of this MIB module.

ciscoSyslogExtMIBObjects OBJECT IDENTIFIER ::= { ciscoSyslogExtMIB 1 }
cseSyslogConfigurationGroup OBJECT IDENTIFIER ::= { ciscoSyslogExtMIBObjects 1 }
ciscoSyslogExtMIBConformance OBJECT IDENTIFIER ::= { ciscoSyslogExtMIB 2 }
ciscoSyslogExtMIBCompliances OBJECT IDENTIFIER ::= { ciscoSyslogExtMIBConformance 1 }
ciscoSyslogExtMIBGroups OBJECT IDENTIFIER ::= { ciscoSyslogExtMIBConformance 2 }

SyslogFacility ::= INTEGER {
        --?? enum value of zero may cause problems
        kernel(0),
        user(8),
        mail(16),
        daemon(24),
        auth(32),
        syslog(40),
        lpr(48),
        news(56),
        uucp(64),
        cron(72),
        authPriv(80),
        ftp(88),
        local0(128),
        local1(136),
        local2(144),
        local3(152),
        local4(160),
        local5(168),
        local6(176),
        local7(184)
        }
-- TEXTUAL-CONVENTION
--  Status
--    mandatory
--  Descr
--    The Syslog standard facilities.
--      kernel (0)       - Kernel
--      user (8)         - User Level     
--      mail (16)        - Mail System
--      daemon(24)       - System Daemon
--      auth  (32)       - Security/Authorization
--      syslog (40)      - Internal Syslogd 
--      lpr (48)         - Line Printer subsystem
--      news (56)        - Network New subsystem
--      uucp (64)        - UUCP subsystem
--      cron (72)        - Clock Daemon
--      authPriv (80)    - Security/Auth(private)
--      ftp (88)         - FTP Daemon
--      local0 (128)     - Reserved local use
--      local1 (136)     - Reserved local use
--      local2 (144)     - Reserved local use
--      local3 (152)     - Reserved local use
--      local4 (160)     - Reserved local use
--      local5 (168)     - Reserved local use
--      local6 (176)     - Reserved local use
--      local7 (184)     - Reserved local use.
--  Refer
--    RFC 3164 - The BSD Syslog Protocol, Section 4.

SyslogExFacility ::= INTEGER {
        --?? enum value of zero may cause problems
        kernel(0),
        user(8),
        mail(16),
        daemon(24),
        auth(32),
        syslog(40),
        lpr(48),
        news(56),
        uucp(64),
        cron(72),
        authPriv(80),
        ftp(88),
        local0(128),
        local1(136),
        local2(144),
        local3(152),
        local4(160),
        local5(168),
        local6(176),
        local7(184),
        vsanMgr(200),
        fspf(208),
        domainMgr(216),
        mtsDaemon(224),
        linecardMgr(232),
        sysMgr(240),
        sysMgrLib(248),
        zoneServer(256),
        virtualIfMgr(264),
        ipConfMgr(272),
        ipfc(280),
        xBarMgr(288),
        fcDns(296),
        fabricConfMgr(304),
        aclMgr(312),
        tlPortMgr(320),
        portMgr(328),
        fportServer(336),
        portChMgr(344),
        mpls(352),
        tftpLib(360),
        wwnMgr(368),
        fcc(376),
        qosMgr(384),
        vhba(392),
        procMgr(400),
        vedbMgr(408),
        span(416),
        vrrpMgr(424),
        fcfwd(432),
        ntp(440),
        pltmfmMgr(448),
        xbarClient(456),
        vrrpEngine(464),
        callhome(472),
        ipsMgr(480),
        fc2(488),
        debugLib(496),
        vpm(504),
        mcast(512),
        rdl(520),
        rscn(536),
        bootvar(552),
        pss(576),
        snmp(584),
        security(592),
        vhbad(608),
        dns(648),
        rib(656),
        vshd(672),
        fvpd(688),
        mplsTunnel(816),
        cdpd(848),
        ohmsd(920),
        portSec(960),
        ethPortMgr(976),
        ipaclMgr(1016),
        ficonMgr(1064),
        ficonContDev(1096),
        rlir(1128),
        fdmi(1136),
        licmgr(1152),
        fcspmgr(1160),
        confCheck(1192),
        ivr(1232),
        aaad(1240),
        tacacsd(1248),
        radiusd(1256),
        fc2d(1320),
        lcohmsd(1336),
        isns(1344),
        ficonStat(1352),
        featureMgr(1360),
        lttd(1376),
        fccLc(1392),
        cfs(1432),
        dstats(1448),
        ipsec(1456),
        dpvm(1480),
        ike(1488),
        ddas(1504),
        scheduler(1512),
        sanExtTuner(1520)
        }
-- TEXTUAL-CONVENTION
--  Status
--    mandatory
--  Descr
--    The Syslog facilities including both standard and
--    proprietary facilities.
--    
--     kernel (0)         - Kernel
--     user (8)           - User Level     
--     mail (16)          - Mail System
--     daemon(24)         - System Daemon
--     auth  (32)         - Security/Authorization
--     syslog (40)        - Internal Syslogd 
--     lpr (48)           - Line Printer subsystem
--     news (56)          - Network New subsystem
--     uucp (64)          - UUCP subsystem
--     cron (72)          - Clock Daemon
--     authPriv (80)      - Security/Auth(private)
--     ftp (88)           - FTP Daemon
--     local0 (128)       - Reserved local use
--     local1 (136)       - Reserved local use
--     local2 (144)       - Reserved local use
--     local3 (152)       - Reserved local use
--     local4 (160)       - Reserved local use
--     local5 (168)       - Reserved local use
--     local6 (176)       - Reserved local use
--     local7 (184)       - Reserved local use
--     vsanMgr (200)      - VSAN Manager
--     fspf (208)         - FSPF
--     domainMgr (216)    - Domain Manager
--     mtsDaemon (224)    - MTS Daemon
--     linecardMgr (232)  - Line Card Mgr
--     sysMgr (240)       - System Manager
--     sysMgrLib (248)    - System Mgr Library
--     zoneServer (256)   - Zone Server
--     virtualIfMgr (264) - VirtualInterface Mgr
--     ipConfMgr (272)    - IP Config Manager
--     ipfc (280)         - IP Over FC
--     xBarMgr (288)      - Xbar Manager
--     fcDns (296)        - Fibre Channel DNS
--     fabricConfMgr (304)- Fabric Config Server
--     aclMgr (312)       - AccessControlList Mgr
--     tlPortMgr (320)    - TL Port Manager
--     portMgr (328)      - Port Manager    
--     fportServer (336)  - FPort Server
--     portChMgr (344)    - Port Channel Mgr
--     mpls (352)         - MPLS
--     tftpLib (360)      - TFTP Library
--     wwnMgr (368)       - WWN Mgr  
--     fcc (376),         - FCC Process
--     qosMgr (384)       - QOS Mgr  
--     vhba (392)         - VHBA
--     procMgr (400)      - Proc Mgr  
--     vedbMgr (408)      - VEBD Mgr  
--     span (416)         - SPAN
--     vrrpMgr (424)      - VRRP Mgr   
--     fcfwd (432)        - FCFWD
--     ntp (440)          - NTP
--     pltmfmMgr (448)    - Platform Mgr  
--     xbarClient (456)   - XBAR Client  
--     vrrpEngine (464)   - VRRP Engine
--     callhome (472)     - Callhome  
--     ipsMgr (480)       - IPS Mgr  
--     fc2 (488)          - FC2
--     debugLib (496)     - Debug Library
--     vpm (504)          - VPM
--     mcast (512)        - Multicast
--     rdl (520)          - RDL
--     rscn (536)         - RSCN
--     bootvar (552)      - BootVar
--     pss (576)          - Persistent Storage System
--     snmp (584)         - SNMP
--     security (592)     - Security
--     vhbad (608)        - VHBAD
--     dns (648)          - DNS
--     rib (656)          - RIB
--     vshd (672)         - VSH Daemon
--     fvpd (688)         - Fabric Virtual Port Daemon
--     mplsTunnel (816)   - MPLS Tunnel
--     cdpd (848)         - CDP Daemon
--     ohmsd (920)        - OHMs Daemon
--     portSec (960)      - Port Security Manager
--     ethPortMgr (976)   - Ethernet Port Manager
--     ipaclMgr (1016)    - IP ACL Manager
--     ficonMgr (1064)    - FICON Manager
--     ficonContDev (1096)- Ficon Control Device
--     rlir (1128)        - RLIR Module
--     fdmi (1136)        - Fabric Device  Management Interface
--     licmgr (1152)      - License Manager
--     fcspmgr (1160)     - FCSP Manager
--     confCheck (1192)   - Configuration Check
--     ivr (1232)         - Inter-VSAN Routing
--     aaad (1240)        - AAA Daemon
--     tacacsd (1248)     - TACACS Daemon
--     radiusd (1256)     - Radius Daemon
--     fc2d (1320)        - FC2 Daemon
--     lcohmsd (1336)     - LC Ohms Daemon
--     isns (1344)        - iSNS
--     ficonStat (1352)   - FICON Statistics,
--     featureMgr (1360)  - Feature Manager
--     lttd (1376)        - LTT Daemon
--     fccLc (1392)       - linecard FCC
--     cfs (1432)         - Cisco Fabric Services 
--     dstats (1448)      - Delta Statistics
--     ipsec (1456)       - IP Sec
--     dpvm  (1480)       - Dynamic Port Vsan Mgr
--     ike (1488)         - IKE
--     ddas (1504)        - DDAS
--     scheduler (1512)   - scheduler 
--     sanExtTuner (1520) - SAN extension Tuner.
--  Refer
--    RFC 3164 - The BSD Syslog Protocol, Section 4.

SyslogProtocol ::= INTEGER {
        tcp(6),
        udp(17)
        }
-- TEXTUAL-CONVENTION
--  Status
--    mandatory
--  Descr
--    The protocol used for sending syslog
--    messages to syslog server.
--    
--      tcp (6)    - TCP
--      udp (17)   - UDP.

cseSyslogConsoleEnable OBJECT-TYPE
    SYNTAX TruthValue
--    Rsyntax INTEGER {
--        true(1),
--        false(2)
--        }
    ACCESS read-write
    STATUS mandatory
    DESCRIPTION
        "Indicate whether the Syslog messages should be 
        sent to the console."
    DEFVAL { false }
    ::= { cseSyslogConfigurationGroup 1 }

cseSyslogConsoleMsgSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Minimum severity of the message that are sent to 
         the Console."
    DEFVAL { debug }
    ::= { cseSyslogConfigurationGroup 2 }

cseSyslogLogFileName OBJECT-TYPE
    SYNTAX SnmpAdminString(SIZE(0..255))
--    Rsyntax OCTET STRING(SIZE(0..255))
    ACCESS read-write
    STATUS mandatory
    DESCRIPTION
        "Name of file to which the Syslog messages are 
        logged. Set operation with a zero length will 
        fail."
    DEFVAL { "messages" }
    ::= { cseSyslogConfigurationGroup 3 }

cseSyslogLogFileMsgSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Minimum severity of the message that are sent to 
         the log file (cseSyslogLogFileName)."
    DEFVAL { debug }
    ::= { cseSyslogConfigurationGroup 4 }

cseSyslogFileLoggingDisable OBJECT-TYPE
    SYNTAX INTEGER {
        true(1),
        noOp(2)
        }
    ACCESS read-write
    STATUS mandatory
    DESCRIPTION
        "Indicates whether the Syslog messages should be
        sent to the file indicated by cseSyslogLogFileName.
        Once this object is set to 'true', the Syslog messages 
        are no longer sent to the file. The value of 
        'cseSyslogLogFileName' is set to zero length string.
        To restart the file logging, the cseSyslogLogFileName 
        should be set to a valid file name.
        
        No action is taken if this object is set to 'noOp'.
        The value of the object when read is always 'noOp'."
    ::= { cseSyslogConfigurationGroup 5 }

cseSyslogServerTableMaxEntries OBJECT-TYPE
    SYNTAX Gauge(0..65535)
    ACCESS read-only
    STATUS mandatory
    DESCRIPTION
        "The maximum number of entries that the agent supports 
        in the cseSyslogServerTable."
    ::= { cseSyslogConfigurationGroup 6 }

cseSyslogServerTable OBJECT-TYPE
    SYNTAX SEQUENCE OF CseSyslogServerEntry
    ACCESS not-accessible
    STATUS mandatory
    DESCRIPTION
        "This table contains all the Syslog servers which are
        configured."
    ::= { cseSyslogConfigurationGroup 7 }

cseSyslogServerEntry OBJECT-TYPE
    SYNTAX CseSyslogServerEntry
    ACCESS not-accessible
    STATUS mandatory
    DESCRIPTION
        "An entry containing information about a 
        Syslog server."
    INDEX { cseSyslogServerIndex }
    ::= { cseSyslogServerTable 1 }

CseSyslogServerEntry ::= SEQUENCE {
    cseSyslogServerIndex Gauge,
    cseSyslogServerAddressType InetAddressType,
    cseSyslogServerAddress InetAddress,
    cseSyslogServerMsgSeverity SyslogSeverity,
    cseSyslogServerStatus RowStatus,
    cseSyslogServerFacility SyslogFacility,
    cseSyslogServerProtocol SyslogProtocol,
    cseSyslogServerPort InetPortNumber,
    cseSyslogServerProtocolFallback SyslogProtocol
    }

cseSyslogServerIndex OBJECT-TYPE
    SYNTAX Gauge(1..65535)
    ACCESS not-accessible
    STATUS mandatory
    DESCRIPTION
        "An arbitrary integer value, greater than zero, and 
        less than and equal to cseSyslogServerTableMaxEntries, 
        which identifies a Syslog server row in this table."
    ::= { cseSyslogServerEntry 1 }

cseSyslogServerAddressType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "The type of the address of the Syslog server which is
        given by the corresponding value of 
        cseSyslogServerAddress."
    ::= { cseSyslogServerEntry 2 }

cseSyslogServerAddress OBJECT-TYPE
    SYNTAX InetAddress
--    Rsyntax OCTET STRING(SIZE(0..255))
    ACCESS read-write
    STATUS mandatory
    DESCRIPTION
        "The address of the Syslog server."
    ::= { cseSyslogServerEntry 3 }

cseSyslogServerMsgSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Minimum severity of the message that are sent to 
        this Syslog server."
    DEFVAL { debug }
    ::= { cseSyslogServerEntry 4 }

cseSyslogServerStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this row.
        
        A row can not become 'active' until the values for
        cseSyslogServerAddressType and cseSyslogServerAddress in
        that row have both been set.
        
        A row cannot be created until corresponding instances
        of following objects are instantiated.
        - cseSyslogServerAddressType
        - cseSyslogServerAddress
        
        The following objects may not be modified while the
        value of this object is active (1):
        - cseSyslogServerAddressType
        - cseSyslogServerAddress."
    ::= { cseSyslogServerEntry 5 }

cseSyslogServerFacility OBJECT-TYPE
    SYNTAX SyslogFacility
--    Rsyntax INTEGER {
--        ?? enum value of zero may cause problems
--        kernel(0),
--        user(8),
--        mail(16),
--        daemon(24),
--        auth(32),
--        syslog(40),
--        lpr(48),
--        news(56),
--        uucp(64),
--        cron(72),
--        authPriv(80),
--        ftp(88),
--        local0(128),
--        local1(136),
--        local2(144),
--        local3(152),
--        local4(160),
--        local5(168),
--        local6(176),
--        local7(184)
--        }
    ACCESS read-write
    STATUS mandatory
    DESCRIPTION
        "The facility to be used when sending Syslog messages to
        this server."
    DEFVAL { local7 }
    ::= { cseSyslogServerEntry 6 }

cseSyslogServerProtocol OBJECT-TYPE
    SYNTAX SyslogProtocol
--    Rsyntax INTEGER {
--        tcp(6),
--        udp(17)
--        }
    ACCESS read-write
    STATUS mandatory
    DESCRIPTION
        "The transport protocol used for sending syslog messages
        to syslog server."
    DEFVAL { udp }
    ::= { cseSyslogServerEntry 7 }

cseSyslogServerPort OBJECT-TYPE
    SYNTAX InetPortNumber(1..65535)
--    Rsyntax Gauge(1..65535)
    ACCESS read-write
    STATUS mandatory
    DESCRIPTION
        "The port number of the syslog server to
        which syslog messages are sent.
        The default value in case of 'cseSyslogServerProtocol'
        value of 'udp' is 514.
        The default value in case of 'cseSyslogServerProtocol'
        value of 'tcp' is 1468."
    ::= { cseSyslogServerEntry 8 }

cseSyslogServerProtocolFallback OBJECT-TYPE
    SYNTAX SyslogProtocol
--    Rsyntax INTEGER {
--        tcp(6),
--        udp(17)
--        }
    ACCESS read-write
    STATUS mandatory
    DESCRIPTION
        "This object is used for specifying the
        protcol to fallback to if the sending of
        syslog messages using the protocol configured
        in 'cseSyslogServerProtocol' fails.
        If the value of this object is same as 
        the value specified in 'cseSyslogServerProtocol',
        then protocol fallback in case of failure is not
        supported."
    DEFVAL { udp }
    ::= { cseSyslogServerEntry 9 }

cseSyslogMessageControlTable OBJECT-TYPE
    SYNTAX SEQUENCE OF CseSyslogMessageControlEntry
    ACCESS not-accessible
    STATUS mandatory
    DESCRIPTION
        "This table contains the information about what system
        log messages should be sent to Syslog host, console, 
        log file, and/or logged into the internal buffer."
    ::= { cseSyslogConfigurationGroup 8 }

cseSyslogMessageControlEntry OBJECT-TYPE
    SYNTAX CseSyslogMessageControlEntry
    ACCESS not-accessible
    STATUS mandatory
    DESCRIPTION
        "A system log message control table entry.
        Each entry specifies a severity for a particular 
        'facility' which generates Syslog messages.  Any 
        generated message which is at least as severe as 
        the specified severity will be logged."
    INDEX { cseSyslogMessageFacility }
    ::= { cseSyslogMessageControlTable 1 }

CseSyslogMessageControlEntry ::= SEQUENCE {
    cseSyslogMessageFacility SyslogExFacility,
    cseSyslogMessageSeverity SyslogSeverity
    }

cseSyslogMessageFacility OBJECT-TYPE
    SYNTAX SyslogExFacility
--    Rsyntax INTEGER {
--        ?? enum value of zero may cause problems
--        kernel(0),
--        user(8),
--        mail(16),
--        daemon(24),
--        auth(32),
--        syslog(40),
--        lpr(48),
--        news(56),
--        uucp(64),
--        cron(72),
--        authPriv(80),
--        ftp(88),
--        local0(128),
--        local1(136),
--        local2(144),
--        local3(152),
--        local4(160),
--        local5(168),
--        local6(176),
--        local7(184),
--        vsanMgr(200),
--        fspf(208),
--        domainMgr(216),
--        mtsDaemon(224),
--        linecardMgr(232),
--        sysMgr(240),
--        sysMgrLib(248),
--        zoneServer(256),
--        virtualIfMgr(264),
--        ipConfMgr(272),
--        ipfc(280),
--        xBarMgr(288),
--        fcDns(296),
--        fabricConfMgr(304),
--        aclMgr(312),
--        tlPortMgr(320),
--        portMgr(328),
--        fportServer(336),
--        portChMgr(344),
--        mpls(352),
--        tftpLib(360),
--        wwnMgr(368),
--        fcc(376),
--        qosMgr(384),
--        vhba(392),
--        procMgr(400),
--        vedbMgr(408),
--        span(416),
--        vrrpMgr(424),
--        fcfwd(432),
--        ntp(440),
--        pltmfmMgr(448),
--        xbarClient(456),
--        vrrpEngine(464),
--        callhome(472),
--        ipsMgr(480),
--        fc2(488),
--        debugLib(496),
--        vpm(504),
--        mcast(512),
--        rdl(520),
--        rscn(536),
--        bootvar(552),
--        pss(576),
--        snmp(584),
--        security(592),
--        vhbad(608),
--        dns(648),
--        rib(656),
--        vshd(672),
--        fvpd(688),
--        mplsTunnel(816),
--        cdpd(848),
--        ohmsd(920),
--        portSec(960),
--        ethPortMgr(976),
--        ipaclMgr(1016),
--        ficonMgr(1064),
--        ficonContDev(1096),
--        rlir(1128),
--        fdmi(1136),
--        licmgr(1152),
--        fcspmgr(1160),
--        confCheck(1192),
--        ivr(1232),
--        aaad(1240),
--        tacacsd(1248),
--        radiusd(1256),
--        fc2d(1320),
--        lcohmsd(1336),
--        isns(1344),
--        ficonStat(1352),
--        featureMgr(1360),
--        lttd(1376),
--        fccLc(1392),
--        cfs(1432),
--        dstats(1448),
--        ipsec(1456),
--        dpvm(1480),
--        ike(1488),
--        ddas(1504),
--        scheduler(1512),
--        sanExtTuner(1520)
--        }
    ACCESS not-accessible
    STATUS mandatory
    DESCRIPTION
        "System log message facility."
    ::= { cseSyslogMessageControlEntry 1 }

cseSyslogMessageSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Minimum severity of the message that are generated by 
        this Syslog message facility."
    ::= { cseSyslogMessageControlEntry 2 }

cseSyslogTerminalEnable OBJECT-TYPE
    SYNTAX TruthValue
--    Rsyntax INTEGER {
--        true(1),
--        false(2)
--        }
    ACCESS read-write
    STATUS mandatory
    DESCRIPTION
        "Indicate whether the Syslog messages should be 
        sent to the terminals."
    DEFVAL { false }
    ::= { cseSyslogConfigurationGroup 9 }

cseSyslogTerminalMsgSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Minimum severity of the message that are sent to 
         the terminals."
    DEFVAL { debug }
    ::= { cseSyslogConfigurationGroup 10 }

cseSyslogLinecardEnable OBJECT-TYPE
    SYNTAX TruthValue
--    Rsyntax INTEGER {
--        true(1),
--        false(2)
--        }
    ACCESS read-write
    STATUS mandatory
    DESCRIPTION
        "Indicate whether the Syslog messages should be 
        generated at the line cards."
    DEFVAL { false }
    ::= { cseSyslogConfigurationGroup 11 }

cseSyslogLinecardMsgSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Minimum severity of the message that are sent from 
         linecards."
    DEFVAL { debug }
    ::= { cseSyslogConfigurationGroup 12 }

ciscoSyslogExtGroup OBJECT IDENTIFIER ::= { ciscoSyslogExtMIBGroups 1 }
-- OBJECT-GROUP
--  Status
--    mandatory
--  Descr
--    A collection of objects for Syslog management.
--  objects
--    cseSyslogConsoleEnable, cseSyslogLogFileName, 
--    cseSyslogFileLoggingDisable, cseSyslogConsoleMsgSeverity, 
--    cseSyslogLogFileMsgSeverity, cseSyslogServerTableMaxEntries, 
--    cseSyslogServerAddress, cseSyslogServerAddressType, 
--    cseSyslogServerMsgSeverity, cseSyslogServerStatus, 
--    cseSyslogServerFacility, cseSyslogMessageSeverity, 
--    cseSyslogTerminalEnable, cseSyslogTerminalMsgSeverity, 
--    cseSyslogLinecardEnable, cseSyslogLinecardMsgSeverity

ciscoSyslogProtocolGroup OBJECT IDENTIFIER ::= { ciscoSyslogExtMIBGroups 2 }
-- OBJECT-GROUP
--  Status
--    mandatory
--  Descr
--    A collection of objects referring to
--    protocol related objects in syslog configuration.
--  objects
--    cseSyslogServerProtocol, cseSyslogServerPort, 
--    cseSyslogServerProtocolFallback

ciscoSyslogExtMIBCompliance OBJECT IDENTIFIER ::= { ciscoSyslogExtMIBCompliances 1 }
-- MODULE-COMPLIANCE
--  Status
--    mandatory
--  Descr
--    The compliance statement for entities which
--     implement the CISCO-SYSLOG-EXT-MIB.
--  Module
--    >>current<<
--   MandGroup
--    ciscoSyslogExtGroup
--   ObjVar
--    cseSyslogServerAddressType
--   ObjVar
--    cseSyslogServerStatus
--   ObjVar
--    cseSyslogLinecardEnable
--   ObjVar
--    cseSyslogLinecardMsgSeverity

ciscoSyslogExtMIBComplianceRev2 OBJECT IDENTIFIER ::= { ciscoSyslogExtMIBCompliances 2 }
-- MODULE-COMPLIANCE
--  Status
--    mandatory
--  Descr
--    The compliance statement for entities which
--     implement the CISCO-SYSLOG-EXT-MIB.
--  Module
--    >>current<<
--   MandGroup
--    ciscoSyslogExtGroup
--   OptGroup
--    ciscoSyslogProtocolGroup
--   ObjVar
--    cseSyslogServerAddressType
--   ObjVar
--    cseSyslogServerStatus
--   ObjVar
--    cseSyslogLinecardEnable
--   ObjVar
--    cseSyslogLinecardMsgSeverity


END
