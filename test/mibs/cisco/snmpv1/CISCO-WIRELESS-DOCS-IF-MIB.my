-- MIB file created 28-Mar-2001 16:07:35, by
--   SMICng version 2.2.11-beta(PRO)(Solaris), January 20, 2001. Enterprise key cisco.com

CISCO-WIRELESS-DOCS-IF-MIB DEFINITIONS ::= BEGIN

-- From file: "CISCO-WIRELESS-DOCS-IF-MIB.my"
-- Compile options "4 7 F H N W 03 06 0B 0G 0N 0T"

IMPORTS
    MacAddress, RowStatus, TruthValue, TimeStamp, TimeInterval
            FROM SNMPv2-TC-v1
--    Unsigned32
--            FROM CISCO-TC
    ifIndex, InterfaceIndexOrZero, InterfaceIndex
            FROM IF-MIB
    CwrdBm
            FROM CISCO-WIRELESS-TC-MIB
    ciscoMgmt
            FROM CISCO-SMI
    Counter, IpAddress, Gauge
            FROM RFC1155-SMI
    OBJECT-TYPE
            FROM RFC-1212;

ciscoWirelessDocsIfMib OBJECT IDENTIFIER ::= { ciscoMgmt 167 }
-- MODULE-IDENTITY
--  LastUpdated
--    200006071003Z
--  OrgName
--    Cisco Systems - Wireless Engineering
--  ContactInfo
--        Cisco Systems
--         Customer Service
--    
--    Postal: 170 W Tasman Drive
--            San Jose, CA  95134
--            USA
--    
--            Tel: +1 800 553-NETS
--            E-mail: wireless-nms@cisco.com
--  Descr
--    This is the MIB Module for MCNS compliant Radio Frequency
--     (RF) interfaces in wireless point-to-multipoint subscriber
--     units (SU) and wireless Head-end (HE).
--  RevDate
--    200006071003Z
--  RevDescr
--    Initial version

cwdIfMibObjects OBJECT IDENTIFIER ::= { ciscoWirelessDocsIfMib 1 }
cwdIfBaseObjects OBJECT IDENTIFIER ::= { cwdIfMibObjects 1 }
cwdIfSuObjects  OBJECT IDENTIFIER ::= { cwdIfMibObjects 2 }
cwdIfHeObjects  OBJECT IDENTIFIER ::= { cwdIfMibObjects 3 }
cwdIfNotification OBJECT IDENTIFIER ::= { ciscoWirelessDocsIfMib 2 }
cwdIfConformance OBJECT IDENTIFIER ::= { ciscoWirelessDocsIfMib 3 }
cwdIfCompliances OBJECT IDENTIFIER ::= { cwdIfConformance 1 }
cwdIfGroups     OBJECT IDENTIFIER ::= { cwdIfConformance 2 }

cwdIfChannelTable OBJECT-TYPE
    SYNTAX SEQUENCE OF CwdIfChannelEntry
    ACCESS not-accessible
    STATUS mandatory
    DESCRIPTION
        "This table describes the attributes of a channel 
         group which consists of one or more downstream and
         upstream channels. "
    ::= { cwdIfBaseObjects 1 }

cwdIfChannelEntry OBJECT-TYPE
    SYNTAX CwdIfChannelEntry
    ACCESS not-accessible
    STATUS mandatory
    DESCRIPTION
        "List of attributes for a single Channel. There
         is one per Point-to-multipoint card. 
         An entry in this table exists for each ifEntry with an
         ifType of propDocsWirelessMacLayer(nnn)."
    INDEX { ifIndex }
    ::= { cwdIfChannelTable 1 }

CwdIfChannelEntry ::= SEQUENCE {
    cwdIfChannelUpFrequency INTEGER,
    cwdIfChannelUpWidth INTEGER,
    cwdIfChannelDownFrequency INTEGER,
    cwdIfChannelDownWidth INTEGER,
    cwdIfChannelMiniSlotTimeBaseTick INTEGER,
    cwdIfChannelSubChannelPlanVer Gauge
    }

cwdIfChannelUpFrequency OBJECT-TYPE
    SYNTAX INTEGER(0..60000000)
--  Units
--    kHz
    ACCESS read-write
    STATUS mandatory
    DESCRIPTION
        "The reference center frequency used by the upstream
         channels in this channel."
    ::= { cwdIfChannelEntry 1 }

cwdIfChannelUpWidth OBJECT-TYPE
    SYNTAX INTEGER(0..500000)
--  Units
--    kHz
    ACCESS read-write
    STATUS mandatory
    DESCRIPTION
        "The maximum bandwidth that can be used by any upstream
         channel. The sum of the bandwidths used by all 
         upstream channels created within this channel cannot
         exceed this value."
    ::= { cwdIfChannelEntry 2 }

cwdIfChannelDownFrequency OBJECT-TYPE
    SYNTAX INTEGER(0..60000000)
--  Units
--    kHz
    ACCESS read-write
    STATUS mandatory
    DESCRIPTION
        "The reference center frequency used by the 
         downstream channels in this channel."
    ::= { cwdIfChannelEntry 3 }

cwdIfChannelDownWidth OBJECT-TYPE
    SYNTAX INTEGER(0..500000)
--  Units
--    kHz
    ACCESS read-write
    STATUS mandatory
    DESCRIPTION
        "The maximum bandwidth that can be used by any
         downstream channel.  The sum of the bandwidths
         used by all downstream channels created
         within this channel cannot exceed this value."
    ::= { cwdIfChannelEntry 4 }

cwdIfChannelMiniSlotTimeBaseTick OBJECT-TYPE
    SYNTAX INTEGER(0..102400000)
--  Units
--    Microseconds
    ACCESS read-only
    STATUS mandatory
    DESCRIPTION
        "This object represents a unit of measurement of mini-slots. 
         Upstream mini-slots and bandwidth allocations are done 
         in multiples of this unit of time."
    ::= { cwdIfChannelEntry 5 }

cwdIfChannelSubChannelPlanVer OBJECT-TYPE
    SYNTAX Gauge
    ACCESS read-only
    STATUS mandatory
    DESCRIPTION
        "This object represents the sub-channel plan version number
         common to both upstream and downstream supported by the 
         hardware."
    REFERENCE
        "Firestorm(P2MP) Sub-Channel Plan Specification - ENG-51192"
    ::= { cwdIfChannelEntry 6 }

cwdIfDownstreamChannelTable OBJECT-TYPE
    SYNTAX SEQUENCE OF CwdIfDownstreamChannelEntry
    ACCESS not-accessible
    STATUS mandatory
    DESCRIPTION
        "This table describes the attributes of downstream
         channels (frequency bands)."
    ::= { cwdIfBaseObjects 2 }

cwdIfDownstreamChannelEntry OBJECT-TYPE
    SYNTAX CwdIfDownstreamChannelEntry
    ACCESS not-accessible
    STATUS mandatory
    DESCRIPTION
        "List of attributes for a single downstream channel.
         The index to this table is an ifIndex with an ifType
         of propDocsWirelessDownStream(nnn). "
    INDEX { ifIndex }
    ::= { cwdIfDownstreamChannelTable 1 }

CwdIfDownstreamChannelEntry ::= SEQUENCE {
    cwdIfDownChannelSubChannelNumber INTEGER,
    cwdIfDownChannelId INTEGER,
    cwdIfDownChannelFrequency INTEGER,
    cwdIfDownChannelWidth INTEGER,
    cwdIfDownChannelPower INTEGER,
    cwdIfDownChannelModProfileIndex Gauge
    }

cwdIfDownChannelSubChannelNumber OBJECT-TYPE
    SYNTAX INTEGER(1..1024)
    ACCESS read-write
    STATUS mandatory
    DESCRIPTION
        "This identifies the sub-channel used by this downstream.
         The value of this object determines the usability of the
         other downstream channels."
    ::= { cwdIfDownstreamChannelEntry 1 }

cwdIfDownChannelId OBJECT-TYPE
    SYNTAX INTEGER(0..255)
    ACCESS read-only
    STATUS mandatory
    DESCRIPTION
        "The internal (DOCSIS) identification of the downstream
         channel within this particular MAC interface. If the
         interface is down, the object returns the last assigned 
         value. If the downstream channel ID is unknown, this
         object returns a value of 0."
    ::= { cwdIfDownstreamChannelEntry 2 }

cwdIfDownChannelFrequency OBJECT-TYPE
    SYNTAX INTEGER(0..60000000)
--  Units
--    kHz
    ACCESS read-only
    STATUS mandatory
    DESCRIPTION
        "The downstream center frequency associated with
         this channel. The channel settings determine this
         value."
    ::= { cwdIfDownstreamChannelEntry 3 }

cwdIfDownChannelWidth OBJECT-TYPE
    SYNTAX INTEGER(0..500000)
--  Units
--    kHz
    ACCESS read-only
    STATUS mandatory
    DESCRIPTION
        "The bandwidth of this downstream channel. The channel
         settings determine this value."
    ::= { cwdIfDownstreamChannelEntry 4 }

cwdIfDownChannelPower OBJECT-TYPE
    SYNTAX INTEGER(-80..50)
--  Units
--    dBm - decibel milliwatts
    ACCESS read-write
    STATUS mandatory
    DESCRIPTION
        "At the HE, the operational transmit power. At the SU,
         the received power level. May be set to zero at the SU
         if power level measurement is not supported.
         If the interface is down, this object returns the
         configured value (if at HE), the most current value
         (if at SU) or zero (if not supported by the 
         implementation)."
    ::= { cwdIfDownstreamChannelEntry 5 }

cwdIfDownChannelModProfileIndex OBJECT-TYPE
    SYNTAX Gauge
    ACCESS read-write
    STATUS mandatory
    DESCRIPTION
        "An index into cwdIfModulationTable that describes 
         modulation characteristics of this channel.
         This object returns 0 if the cwdIfModulationTable
         does not exist, or there is no corresponding row
         in that table that describes modulation 
         characteristics of this channel."
    ::= { cwdIfDownstreamChannelEntry 6 }

cwdIfUpstreamChannelTable OBJECT-TYPE
    SYNTAX SEQUENCE OF CwdIfUpstreamChannelEntry
    ACCESS not-accessible
    STATUS mandatory
    DESCRIPTION
        "Describes the attributes of attached upstream channels."
    ::= { cwdIfBaseObjects 4 }

cwdIfUpstreamChannelEntry OBJECT-TYPE
    SYNTAX CwdIfUpstreamChannelEntry
    ACCESS not-accessible
    STATUS mandatory
    DESCRIPTION
        "List of attributes for a single upstream channel.
         The primary index is an ifIndex with an ifType of 
         propDocsWirelessUpstream(nnn)."
    INDEX { ifIndex }
    ::= { cwdIfUpstreamChannelTable 1 }

CwdIfUpstreamChannelEntry ::= SEQUENCE {
    cwdIfUpChannelSubChannelNumber INTEGER,
    cwdIfUpChannelId INTEGER,
    cwdIfUpChannelFrequency INTEGER,
    cwdIfUpChannelWidth INTEGER,
    cwdIfUpChannelTargetPower INTEGER,
    cwdIfUpChannelModProfileIndex Gauge,
    cwdIfUpChannelSlotSize Gauge,
    cwdIfUpChannelTxTimingOffset Gauge,
    cwdIfUpChannelRangBackoffStart INTEGER,
    cwdIfUpChannelRangBackoffEnd INTEGER,
    cwdIfUpChannelTxBackoffStart INTEGER,
    cwdIfUpChannelTxBackoffEnd INTEGER
    }

cwdIfUpChannelSubChannelNumber OBJECT-TYPE
    SYNTAX INTEGER(0..1024)
    ACCESS read-write
    STATUS mandatory
    DESCRIPTION
        "This identifies the sub-channel used by this upstream."
    ::= { cwdIfUpstreamChannelEntry 1 }

cwdIfUpChannelId OBJECT-TYPE
    SYNTAX INTEGER(0..255)
    ACCESS read-only
    STATUS mandatory
    DESCRIPTION
        "The internal (DOCSIS) identification of the upstream
         channel within this particular MAC interface. If the
         interface is down, the object returns the most current
         value. If the upstream channel ID is unknown, this
         object returns a value of 0."
    ::= { cwdIfUpstreamChannelEntry 2 }

cwdIfUpChannelFrequency OBJECT-TYPE
    SYNTAX INTEGER(0..60000000)
--  Units
--    kHz
    ACCESS read-only
    STATUS mandatory
    DESCRIPTION
        "The center of the upstream frequency associated with
         this channel. The channel settings determine this value."
    ::= { cwdIfUpstreamChannelEntry 3 }

cwdIfUpChannelWidth OBJECT-TYPE
    SYNTAX INTEGER(0..500000)
--  Units
--    kHz
    ACCESS read-only
    STATUS mandatory
    DESCRIPTION
        "The bandwidth of this upstream channel. The channel
         settings determine this value."
    ::= { cwdIfUpstreamChannelEntry 4 }

cwdIfUpChannelTargetPower OBJECT-TYPE
    SYNTAX INTEGER(-80..50)
--  Units
--    dBm - decibel milliwatts
    ACCESS read-write
    STATUS mandatory
    DESCRIPTION
        "The target receive power of this upstream channel at the
         headend and the transmit power of the channel at the
         subscriber end."
    ::= { cwdIfUpstreamChannelEntry 5 }

cwdIfUpChannelModProfileIndex OBJECT-TYPE
    SYNTAX Gauge
    ACCESS read-write
    STATUS mandatory
    DESCRIPTION
        "An index into cwdIfModulationTable that describes 
         modulation characteristics of this channel.
         This object returns 0 if the cwdIfModulationTable 
         does not exist or is empty."
    ::= { cwdIfUpstreamChannelEntry 6 }

cwdIfUpChannelSlotSize OBJECT-TYPE
    SYNTAX Gauge
    ACCESS read-write
    STATUS mandatory
    DESCRIPTION
        "The number of units of time-slot (measured by
         cwdIfChannelMiniSlotTimeBaseTick) in each upstream
         mini-slot. Returns zero if the value is undefined
         or unknown."
    ::= { cwdIfUpstreamChannelEntry 7 }

cwdIfUpChannelTxTimingOffset OBJECT-TYPE
    SYNTAX Gauge
    ACCESS read-only
    STATUS mandatory
    DESCRIPTION
        "A measure of the current round trip time at the SU, or the 
         maximum round trip time seen by the HE.  Used for timing
         of SU upstream transmissions to ensure synchronized
         arrivals at the HE. Units are in terms of
         (cwdIfChannelMiniSlotTimeBaseTick/64)."
    ::= { cwdIfUpstreamChannelEntry 8 }

cwdIfUpChannelRangBackoffStart OBJECT-TYPE
    SYNTAX INTEGER(0..16)
    ACCESS read-write
    STATUS mandatory
    DESCRIPTION
        "This value determines the initial contention resolution
         back-off window used by the SU when attempting to transmit
         an initial ranging request. The SU randomly selects a 
         number within the back-off window defined by this 
         parameter then defers this number of contention 
         transmit opportunities before actually attempting the 
         transmission. Expressed as a power of 2. A value of 16
         at the HE indicates that a proprietary adaptive retry 
         mechanism is to be used."
    ::= { cwdIfUpstreamChannelEntry 9 }

cwdIfUpChannelRangBackoffEnd OBJECT-TYPE
    SYNTAX INTEGER(0..16)
    ACCESS read-write
    STATUS mandatory
    DESCRIPTION
        "This value determines the final contention resolution
         back-off window used by the SU when attempting to transmit
         an initial ranging request. The SU randomly selects a 
         number within the back-off window defined by this 
         parameter then defers this number of contention 
         transmit opportunities before actually attempting the 
         transmission. Expressed as a power of 2. A value of 16
         at the HE indicates that a proprietary adaptive retry 
         mechanism is to be used."
    ::= { cwdIfUpstreamChannelEntry 10 }

cwdIfUpChannelTxBackoffStart OBJECT-TYPE
    SYNTAX INTEGER(0..16)
    ACCESS read-write
    STATUS mandatory
    DESCRIPTION
        "This value determines the initial contention resolution
         back-off window used by the SU when attempting to 
         transmit data packets. The SU randomly selects a 
         number within the back-off window defined by this 
         parameter then defers this number of contention 
         transmit opportunities before actually attempting the 
         transmission. Expressed as a power of 2. A value of 16
         at the HE indicates that a proprietary adaptive retry 
         mechanism is to be used."
    ::= { cwdIfUpstreamChannelEntry 11 }

cwdIfUpChannelTxBackoffEnd OBJECT-TYPE
    SYNTAX INTEGER(0..16)
    ACCESS read-write
    STATUS mandatory
    DESCRIPTION
        "This value determines the final contention resolution
         back-off window used by the SU when attempting to 
         transmit data packets. The SU randomly selects a 
         number within the back-off window defined by this 
         parameter then defers this number of contention 
         transmit opportunities before actually attempting the 
         transmission. Expressed as a power of 2. A value of 16
         at the HE indicates that a proprietary adaptive retry 
         mechanism is to be used."
    ::= { cwdIfUpstreamChannelEntry 12 }

cwdIfQosProfileTable OBJECT-TYPE
    SYNTAX SEQUENCE OF CwdIfQosProfileEntry
    ACCESS not-accessible
    STATUS mandatory
    DESCRIPTION
        "Describes the attributes for each class of service."
    ::= { cwdIfBaseObjects 5 }

cwdIfQosProfileEntry OBJECT-TYPE
    SYNTAX CwdIfQosProfileEntry
    ACCESS not-accessible
    STATUS mandatory
    DESCRIPTION
        "Describes the attributes for a single class of service.
        
         The row operation for this table is as follows:
         1. This table will be implemented as read-only at the SU. 
            SU entries are created by the agent based on 
            information in REG-REQ MAC messages received at 
            the SU from HE or based on information extracted 
            from the TFTP option file 
         2. Creation of entries in this table is controlled by
            the value of cwdIfHeQosProfilePermissions.
         3. There can be default entries created by the agent at
            the initialization time.
         3. If a table is created by agent, there should only
            be a single entry for each Class of Service. Multiple
            entries with the same Class of Service parameters are
            not recommended as it doesn't add any extra benefit
            and creates extra processing of a row in the table.
         4. You CAN modify a row when it is active provided you
            have the right cwdIfHeQosProfilePermissions. You can
            also change the row to notInService and change 
            the values. 
               An entry in this table cannot be removed while it
            is referenced by an entry in cwdIfSuServiceTable
            (Subscriber Unit) or cwdIfHeServiceTable (Head-end
            System).
               An entry in this table cannot be modified while
            it is referenced by an entry in cwdIfHeServiceTable.
         5. If the cwdIfHeQosProfilePermissions is 
            createBySubscriberUnits(2) then that row cannot be
            modified by the management system.
         6. Any arbitrary integer within the range can be used
            as index to create a row."
    INDEX { cwdIfQosProfIndex }
    ::= { cwdIfQosProfileTable 1 }

CwdIfQosProfileEntry ::= SEQUENCE {
    cwdIfQosProfIndex INTEGER,
    cwdIfQosProfPriority INTEGER,
    cwdIfQosProfMaxUpBandwidth INTEGER,
    cwdIfQosProfGuarUpBandwidth INTEGER,
    cwdIfQosProfMaxDownBandwidth INTEGER,
    cwdIfQosProfMaxTxBurst INTEGER,
    cwdIfQosProfBaselinePrivacy TruthValue,
    cwdIfQosProfStatus RowStatus
    }

cwdIfQosProfIndex OBJECT-TYPE
    SYNTAX INTEGER(1..16383)
    ACCESS not-accessible
    STATUS mandatory
    DESCRIPTION
        "The index value which uniquely identifies an entry
         in the cwdIfQosProfileTable. Any arbitrary integer
         within the range can be used as index to create a row."
    ::= { cwdIfQosProfileEntry 1 }

cwdIfQosProfPriority OBJECT-TYPE
    SYNTAX INTEGER(0..7)
    ACCESS read-write
    STATUS mandatory
    DESCRIPTION
        "A relative priority assigned to this service when
         allocating bandwidth. Zero indicates lowest priority.
         seven highest. 
         Interpretation of priority is device-specific."
    DEFVAL { 0 }
    ::= { cwdIfQosProfileEntry 2 }

cwdIfQosProfMaxUpBandwidth OBJECT-TYPE
    SYNTAX INTEGER(0..100000000)
    ACCESS read-write
    STATUS mandatory
    DESCRIPTION
        "The maximum upstream bandwidth, in bits per second,
         allowed for a service with this service class.
         Zero if there is no restriction of upstream bandwidth."
    DEFVAL { 0 }
    ::= { cwdIfQosProfileEntry 3 }

cwdIfQosProfGuarUpBandwidth OBJECT-TYPE
    SYNTAX INTEGER(0..100000000)
    ACCESS read-write
    STATUS mandatory
    DESCRIPTION
        "Minimum guaranteed upstream bandwidth, in bits per second, 
         allowed for a service with this service class."
    DEFVAL { 0 }
    ::= { cwdIfQosProfileEntry 4 }

cwdIfQosProfMaxDownBandwidth OBJECT-TYPE
    SYNTAX INTEGER(0..100000000)
    ACCESS read-write
    STATUS mandatory
    DESCRIPTION
        "The maximum downstream bandwidth, in bits per second,
         allowed for a service with this service class.
         Zero if there is no restriction of downstream bandwidth."
    DEFVAL { 0 }
    ::= { cwdIfQosProfileEntry 5 }

cwdIfQosProfMaxTxBurst OBJECT-TYPE
    SYNTAX INTEGER
    ACCESS read-write
    STATUS mandatory
    DESCRIPTION
        "The maximum number of mini-slots that may be requested
         for a single upstream transmission.
         A value of zero means there is no limit."
    DEFVAL { 0 }
    ::= { cwdIfQosProfileEntry 6 }

cwdIfQosProfBaselinePrivacy OBJECT-TYPE
    SYNTAX TruthValue
--    Rsyntax INTEGER {
--        true(1),
--        false(2)
--        }
    ACCESS read-write
    STATUS mandatory
    DESCRIPTION
        "Indicates whether Baseline Privacy is enabled for this
         service class."
    DEFVAL { false }
    ::= { cwdIfQosProfileEntry 7 }

cwdIfQosProfStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Controls and reflects the status of rows in this table."
    ::= { cwdIfQosProfileEntry 8 }

cwdIfSignalQualityTable OBJECT-TYPE
    SYNTAX SEQUENCE OF CwdIfSignalQualityEntry
    ACCESS not-accessible
    STATUS mandatory
    DESCRIPTION
        "At the SU, this table describes the PHY signal quality 
         of downstream channels. At the HE, this table describes
         the PHY signal quality of upstream channels."
    ::= { cwdIfBaseObjects 6 }

cwdIfSignalQualityEntry OBJECT-TYPE
    SYNTAX CwdIfSignalQualityEntry
    ACCESS not-accessible
    STATUS mandatory
    DESCRIPTION
        "At the SU, describes the PHY signal quality of a
         downstream channel. At the HE, describes the PHY signal
         quality of an upstream channel.
         An entry in this table exists for each ifEntry with an
         ifType of propDocsWirelessUpstream(nnn) for Head-End
         Systems and propDocsWirelessDownstream(nnn) for
         Subscriber units."
    INDEX { ifIndex }
    ::= { cwdIfSignalQualityTable 1 }

CwdIfSignalQualityEntry ::= SEQUENCE {
    cwdIfSigQIncludesContention TruthValue,
    cwdIfSigQUnerroreds Counter,
    cwdIfSigQCorrecteds Counter,
    cwdIfSigQUncorrectables Counter,
    cwdIfSigQSignalNoise CwrdBm
    }

cwdIfSigQIncludesContention OBJECT-TYPE
    SYNTAX TruthValue
--    Rsyntax INTEGER {
--        true(1),
--        false(2)
--        }
    ACCESS read-only
    STATUS mandatory
    DESCRIPTION
        "true(1) if this HE includes contention intervals in
         the counters in this table. Always false(2) for SUs."
    ::= { cwdIfSignalQualityEntry 1 }

cwdIfSigQUnerroreds OBJECT-TYPE
    SYNTAX Counter
    ACCESS read-only
    STATUS mandatory
    DESCRIPTION
        "Codewords received on this channel without error.
         This includes all codewords, whether or not they
         were part of frames destined for this device."
    ::= { cwdIfSignalQualityEntry 2 }

cwdIfSigQCorrecteds OBJECT-TYPE
    SYNTAX Counter
    ACCESS read-only
    STATUS mandatory
    DESCRIPTION
        "Codewords received on this channel with correctable
         errors. This includes all codewords, whether or not
         they were part of frames destined for this device."
    ::= { cwdIfSignalQualityEntry 3 }

cwdIfSigQUncorrectables OBJECT-TYPE
    SYNTAX Counter
    ACCESS read-only
    STATUS mandatory
    DESCRIPTION
        "Codewords received on this channel with uncorrectable
         errors. This includes all codewords, whether or not
         they were part of frames destined for this device."
    ::= { cwdIfSignalQualityEntry 4 }

cwdIfSigQSignalNoise OBJECT-TYPE
    SYNTAX CwrdBm
--    Rsyntax INTEGER(-80..33)
    ACCESS read-only
    STATUS mandatory
    DESCRIPTION
        "Signal to Interference plus Noise  ratio as perceived
         for this channel. "
    ::= { cwdIfSignalQualityEntry 5 }

cwdIfModulationTable OBJECT-TYPE
    SYNTAX SEQUENCE OF CwdIfModulationEntry
    ACCESS not-accessible
    STATUS mandatory
    DESCRIPTION
        "Describes  modulation parameters associated with one
         or more upstream and/or downstream channels."
    ::= { cwdIfBaseObjects 7 }

cwdIfModulationEntry OBJECT-TYPE
    SYNTAX CwdIfModulationEntry
    ACCESS not-accessible
    STATUS mandatory
    DESCRIPTION
        "Describes a modulation profile for one or more 
         upstream and downstream channels.
         Initial default entries may be created at system 
         initialization time by the agent.
         The row operation for this table is as follows :
         1. Any arbitrary index within the range can be
            used to create a row.
         2. No individual non-index objects have to be
            specified in order to create an entry in this table.
         3. CreateAndWait is not supported.
         4. You can update/change the values in a row when
            the row is active.
         5. The rows can be destroyed any time. "
    INDEX { cwdIfModIndex }
    ::= { cwdIfModulationTable 1 }

CwdIfModulationEntry ::= SEQUENCE {
    cwdIfModIndex INTEGER,
    cwdIfModRowStatus RowStatus,
    cwdIfModBandwidth INTEGER,
    cwdIfModThroughput INTEGER,
    cwdIfModBurstLength INTEGER,
    cwdIfModMultipathRobustness INTEGER
    }

cwdIfModIndex OBJECT-TYPE
    SYNTAX INTEGER(1..2147483647)
    ACCESS not-accessible
    STATUS mandatory
    DESCRIPTION
        "An index into the Channel Modulation table 
         (cwdIfModulationTable) representing modulation
         parameters of a channel."
    ::= { cwdIfModulationEntry 1 }

cwdIfModRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Controls and reflects the status of rows in this table."
    ::= { cwdIfModulationEntry 2 }

cwdIfModBandwidth OBJECT-TYPE
    SYNTAX INTEGER(0..500000)
--  Units
--    kHz
    ACCESS read-write
    STATUS mandatory
    DESCRIPTION
        "The maximum bandwidth that can be used by a channel 
         with using this modulation profile."
    DEFVAL { 6000 }
    ::= { cwdIfModulationEntry 3 }

cwdIfModThroughput OBJECT-TYPE
    SYNTAX INTEGER(0..50000000)
--  Units
--    bps
    ACCESS read-write
    STATUS mandatory
    DESCRIPTION
        "This represents the throughput expected of the 
         identified radio link."
    ::= { cwdIfModulationEntry 4 }

cwdIfModBurstLength OBJECT-TYPE
    SYNTAX INTEGER {
        veryShort(1),
        short(2),
        medium(3),
        long(4)
        }
    ACCESS read-write
    STATUS mandatory
    DESCRIPTION
        "The duration of the OFDM burst used by the physical layer.
         This is also the duration of the MAC minislot.  
         Not all the settings  will be supported by a particular ODU.
         Consult the capabilities of the ODU to determine the best
         burst length setting to use.
         The exact durations are hardware and implementation 
         dependent."
    DEFVAL { medium }
    ::= { cwdIfModulationEntry 5 }

cwdIfModMultipathRobustness OBJECT-TYPE
    SYNTAX INTEGER {
        standard(1),
        high(2)
        }
    ACCESS read-write
    STATUS mandatory
    DESCRIPTION
        "The quantitative level of robustness to multipath (also
         known as delay spread tolerance). The degree of 
         multipath in the environment will vary with deployment.
         Consult installation and deployment documentation to
         determine the best setting to use."
    DEFVAL { standard }
    ::= { cwdIfModulationEntry 6 }

cwdIfSuMacTable OBJECT-TYPE
    SYNTAX SEQUENCE OF CwdIfSuMacEntry
    ACCESS not-accessible
    STATUS mandatory
    DESCRIPTION
        "Describes the attributes of each SU MAC interface,
         extending the information available from ifEntry."
    ::= { cwdIfSuObjects 1 }

cwdIfSuMacEntry OBJECT-TYPE
    SYNTAX CwdIfSuMacEntry
    ACCESS not-accessible
    STATUS mandatory
    DESCRIPTION
        "An entry containing objects describing attributes of
         each MAC entry, extending the information in ifEntry.
         An entry in this table exists for each ifEntry with an
         ifType of propDocsWirelessMacLayer(nnn)."
    INDEX { ifIndex }
    ::= { cwdIfSuMacTable 1 }

CwdIfSuMacEntry ::= SEQUENCE {
    cwdIfSuHeAddress MacAddress,
    cwdIfSuCapabilities OCTET STRING,
    cwdIfSuRangingRespTimeout TimeInterval
    }

cwdIfSuHeAddress OBJECT-TYPE
    SYNTAX MacAddress
--    Rsyntax OCTET STRING(SIZE(6))
    ACCESS read-only
    STATUS mandatory
    DESCRIPTION
        "Identifies the HE that controls this MAC domain. At the
         SU, this will be the source address from SYNC, MAP, and
         other MAC-layer messages. If the HE is unknown, returns
         00-00-00-00-00-00."
    ::= { cwdIfSuMacEntry 1 }

cwdIfSuCapabilities OBJECT-TYPE
    SYNTAX OCTET STRING(SIZE(1))
    ACCESS read-only
    STATUS mandatory
    DESCRIPTION
        "Identifies the capabilities of the MAC implementation 
         at this interface. Note that packet transmission is 
         always supported. Therefore, there is no specific bit
         required to explicitly indicate this capability."
    ::= { cwdIfSuMacEntry 2 }

cwdIfSuRangingRespTimeout OBJECT-TYPE
    SYNTAX TimeInterval
--    Rsyntax INTEGER(0..2147483647)
    ACCESS read-write
    STATUS mandatory
    DESCRIPTION
        "Waiting time for a Ranging Response packet."
    REFERENCE
        "Data over Cable Radio Frequency Interface specification, 
         Section 7, timer T3"
    DEFVAL { 20 }
    ::= { cwdIfSuMacEntry 3 }

cwdIfSuStatusTable OBJECT-TYPE
    SYNTAX SEQUENCE OF CwdIfSuStatusEntry
    ACCESS not-accessible
    STATUS mandatory
    DESCRIPTION
        "This table maintains a number of status objects
         and counters for Subscriber Units."
    ::= { cwdIfSuObjects 2 }

cwdIfSuStatusEntry OBJECT-TYPE
    SYNTAX CwdIfSuStatusEntry
    ACCESS not-accessible
    STATUS mandatory
    DESCRIPTION
        "A set of status objects and counters for a single MAC
         layer instance in a Subscriber unit.
         An entry in this table exists for each ifEntry with an
         ifType of propDocsWirelessMacLayer(nnn)."
    INDEX { ifIndex }
    ::= { cwdIfSuStatusTable 1 }

CwdIfSuStatusEntry ::= SEQUENCE {
    cwdIfSuStatusValue INTEGER,
    cwdIfSuStatusCode OCTET STRING,
    cwdIfSuStatusTxPower INTEGER,
    cwdIfSuStatusResets Counter,
    cwdIfSuStatusLostSyncs Counter,
    cwdIfSuStatusInvalidMaps Counter,
    cwdIfSuStatusInvalidUcds Counter,
    cwdIfSuStatusInvalidRangingResp Counter,
    cwdIfSuStatusInvalidRegResp Counter,
    cwdIfSuStatusT1Timeouts Counter,
    cwdIfSuStatusT2Timeouts Counter,
    cwdIfSuStatusT3Timeouts Counter,
    cwdIfSuStatusT4Timeouts Counter,
    cwdIfSuStatusRangingAborteds Counter
    }

cwdIfSuStatusValue OBJECT-TYPE
    SYNTAX INTEGER {
        other(1),
        notReady(2),
        notSynchronized(3),
        phySynchronized(4),
        usParametersAcquired(5),
        rangingComplete(6),
        ipComplete(7),
        todEstablished(8),
        securityEstablished(9),
        paramTransferComplete(10),
        registrationComplete(11),
        operational(12),
        accessDenied(13)
        }
    ACCESS read-only
    STATUS mandatory
    DESCRIPTION
        "Current Subscriber unit connectivity state, as specified
         in the RF Interface Specification."
    REFERENCE
        "Data over Cable Radio Frequency Interface Specification,
         Chapter 7.2."
    ::= { cwdIfSuStatusEntry 1 }

cwdIfSuStatusCode OBJECT-TYPE
    SYNTAX OCTET STRING
    ACCESS read-only
    STATUS mandatory
    DESCRIPTION
        "Status code for this Subscriber unit as defined in the
         RF Interface Specification. The status code consists
         of a single character indicating error groups, followed
         by a two- or three-digit number indicating the status
         condition."
    REFERENCE
        "Data over Cable Radio Frequency Interface Specification,
         Subscriber unit status codes."
    ::= { cwdIfSuStatusEntry 2 }

cwdIfSuStatusTxPower OBJECT-TYPE
    SYNTAX INTEGER(-80..50)
--  Units
--    dBm - decibel milliwatts
    ACCESS read-only
    STATUS mandatory
    DESCRIPTION
        "The operational transmit power for the attached upstream
         channel."
    ::= { cwdIfSuStatusEntry 3 }

cwdIfSuStatusResets OBJECT-TYPE
    SYNTAX Counter
    ACCESS read-only
    STATUS mandatory
    DESCRIPTION
        "Number of times the SU reset or initialized
         this interface."
    ::= { cwdIfSuStatusEntry 4 }

cwdIfSuStatusLostSyncs OBJECT-TYPE
    SYNTAX Counter
    ACCESS read-only
    STATUS mandatory
    DESCRIPTION
        "Number of times the SU lost synchronization with
         the downstream channel."
    ::= { cwdIfSuStatusEntry 5 }

cwdIfSuStatusInvalidMaps OBJECT-TYPE
    SYNTAX Counter
    ACCESS read-only
    STATUS mandatory
    DESCRIPTION
        "Number of times the SU received invalid MAP messages."
    ::= { cwdIfSuStatusEntry 6 }

cwdIfSuStatusInvalidUcds OBJECT-TYPE
    SYNTAX Counter
    ACCESS read-only
    STATUS mandatory
    DESCRIPTION
        "Number of times the SU received invalid UCD messages."
    ::= { cwdIfSuStatusEntry 7 }

cwdIfSuStatusInvalidRangingResp OBJECT-TYPE
    SYNTAX Counter
    ACCESS read-only
    STATUS mandatory
    DESCRIPTION
        "Number of times the SU received invalid ranging response
         messages."
    ::= { cwdIfSuStatusEntry 8 }

cwdIfSuStatusInvalidRegResp OBJECT-TYPE
    SYNTAX Counter
    ACCESS read-only
    STATUS mandatory
    DESCRIPTION
        "Number of times the SU received invalid registration
         response messages."
    ::= { cwdIfSuStatusEntry 9 }

cwdIfSuStatusT1Timeouts OBJECT-TYPE
    SYNTAX Counter
    ACCESS read-only
    STATUS mandatory
    DESCRIPTION
        "Number of times counter T1 expired in the SU."
    ::= { cwdIfSuStatusEntry 10 }

cwdIfSuStatusT2Timeouts OBJECT-TYPE
    SYNTAX Counter
    ACCESS read-only
    STATUS mandatory
    DESCRIPTION
        "Number of times counter T2 expired in the SU."
    ::= { cwdIfSuStatusEntry 11 }

cwdIfSuStatusT3Timeouts OBJECT-TYPE
    SYNTAX Counter
    ACCESS read-only
    STATUS mandatory
    DESCRIPTION
        "Number of times counter T3 expired in the SU."
    ::= { cwdIfSuStatusEntry 12 }

cwdIfSuStatusT4Timeouts OBJECT-TYPE
    SYNTAX Counter
    ACCESS read-only
    STATUS mandatory
    DESCRIPTION
        "Number of times counter T4 expired in the SU."
    ::= { cwdIfSuStatusEntry 13 }

cwdIfSuStatusRangingAborteds OBJECT-TYPE
    SYNTAX Counter
    ACCESS read-only
    STATUS mandatory
    DESCRIPTION
        "Number of times the ranging process was aborted
         by the HE."
    ::= { cwdIfSuStatusEntry 14 }

cwdIfSuServiceTable OBJECT-TYPE
    SYNTAX SEQUENCE OF CwdIfSuServiceEntry
    ACCESS not-accessible
    STATUS mandatory
    DESCRIPTION
        "Describes the attributes of each upstream service queue
         on a SU."
    ::= { cwdIfSuObjects 3 }

cwdIfSuServiceEntry OBJECT-TYPE
    SYNTAX CwdIfSuServiceEntry
    ACCESS not-accessible
    STATUS mandatory
    DESCRIPTION
        "Describes the attributes of an upstream bandwidth service
         queue.
         An entry in this table exists for each Service ID.
         The primary index is an ifIndex with an ifType of
         propDocsWirelessMacLayer(nnn)."
    INDEX { ifIndex, cwdIfSuServiceId }
    ::= { cwdIfSuServiceTable 1 }

CwdIfSuServiceEntry ::= SEQUENCE {
    cwdIfSuServiceId INTEGER,
    cwdIfSuServiceQosProfile INTEGER,
    cwdIfSuServiceTxSlotsImmed Counter,
    cwdIfSuServiceTxSlotsDed Counter,
    cwdIfSuServiceTxRetries Counter,
    cwdIfSuServiceTxExceeded Counter,
    cwdIfSuServiceRqRetries Counter,
    cwdIfSuServiceRqExceeded Counter
    }

cwdIfSuServiceId OBJECT-TYPE
    SYNTAX INTEGER(1..16383)
    ACCESS not-accessible
    STATUS mandatory
    DESCRIPTION
        "Identifies a service queue for upstream bandwidth. The
         attributes of this service queue are shared between the
         SU and the HE. The HE allocates upstream bandwidth
         to this service queue based on requests from the SU and
         on the class of service associated with this queue."
    ::= { cwdIfSuServiceEntry 1 }

cwdIfSuServiceQosProfile OBJECT-TYPE
    SYNTAX INTEGER(0..16383)
    ACCESS read-only
    STATUS mandatory
    DESCRIPTION
        "The index in cwdIfQosProfileTable describing the quality
         of service attributes associated with this particular
         service. If cwdIfQosProfileTable is not supported or
         doesn't exist, this object returns the value of zero."
    ::= { cwdIfSuServiceEntry 2 }

cwdIfSuServiceTxSlotsImmed OBJECT-TYPE
    SYNTAX Counter
    ACCESS read-only
    STATUS mandatory
    DESCRIPTION
        "The number of upstream mini-slots which have been used to
         transmit data PDUs in immediate (contention) mode. This
         includes only those PDUs which are presumed to have
         arrived at the headend (i.e., those which were explicitly
         acknowledged.) It does not include retransmission attempts
         or mini-slots used by requests."
    ::= { cwdIfSuServiceEntry 3 }

cwdIfSuServiceTxSlotsDed OBJECT-TYPE
    SYNTAX Counter
    ACCESS read-only
    STATUS mandatory
    DESCRIPTION
        "The number of upstream mini-slots which have been used to
         transmit data PDUs in dedicated mode (i.e., as a result
         of a unicast Data Grant)."
    ::= { cwdIfSuServiceEntry 4 }

cwdIfSuServiceTxRetries OBJECT-TYPE
    SYNTAX Counter
    ACCESS read-only
    STATUS mandatory
    DESCRIPTION
        "The data PDUs transmitted directly in contention data
        slots expects explicit acknowledgement from the Headend.
        If the acknowledgement is not received the PDUs are 
        transmitted again. This object is the number of attempts
        to transmit data PDUs which didn't receive 
        acknowledgement."
    ::= { cwdIfSuServiceEntry 5 }

cwdIfSuServiceTxExceeded OBJECT-TYPE
    SYNTAX Counter
    ACCESS read-only
    STATUS mandatory
    DESCRIPTION
        "The data PDUs transmitted directly in contention data
         slots expects explicit acknowledgement from the Headend. 
         If the acknowledgement is not received the PDUs are 
         transmitted again. After excessive retries the data 
         PDUs are dropped. This object represents the number 
         of data PDU transmission failures due to excessive
         retries without acknowledgment."
    ::= { cwdIfSuServiceEntry 6 }

cwdIfSuServiceRqRetries OBJECT-TYPE
    SYNTAX Counter
    ACCESS read-only
    STATUS mandatory
    DESCRIPTION
        "The number of attempts to transmit bandwidth requests
         which did not result in acknowledgment."
    ::= { cwdIfSuServiceEntry 7 }

cwdIfSuServiceRqExceeded OBJECT-TYPE
    SYNTAX Counter
    ACCESS read-only
    STATUS mandatory
    DESCRIPTION
        "The number of requests for bandwidth which failed due to
         excessive retries without acknowledgment."
    ::= { cwdIfSuServiceEntry 8 }

cwdIfHeMacTable OBJECT-TYPE
    SYNTAX SEQUENCE OF CwdIfHeMacEntry
    ACCESS not-accessible
    STATUS mandatory
    DESCRIPTION
        "Describes the attributes of each HE MAC interface,
         extending the information available from ifEntry."
    ::= { cwdIfHeObjects 1 }

cwdIfHeMacEntry OBJECT-TYPE
    SYNTAX CwdIfHeMacEntry
    ACCESS not-accessible
    STATUS mandatory
    DESCRIPTION
        "An entry containing objects describing attributes of each
         MAC entry, extending the information in ifEntry.
         An entry in this table exists for each ifEntry with an
         ifType of propDocsWirelessMacLayer(nnn)."
    INDEX { ifIndex }
    ::= { cwdIfHeMacTable 1 }

CwdIfHeMacEntry ::= SEQUENCE {
    cwdIfHeCapabilities OCTET STRING,
    cwdIfHeSyncInterval INTEGER,
    cwdIfHeUcdInterval INTEGER,
    cwdIfHeMaxServiceIds INTEGER,
    cwdIfHeInsertionInterval TimeInterval,
    cwdIfHeInvitedRangingAttempts INTEGER
    }

cwdIfHeCapabilities OBJECT-TYPE
    SYNTAX OCTET STRING(SIZE(1))
    ACCESS read-only
    STATUS mandatory
    DESCRIPTION
        "Identifies the capabilities of the HE MAC
         implementation at this interface. Note that packet
         transmission is always supported. Therefore, there
         is no specific bit required to explicitly indicate
         this capability."
    ::= { cwdIfHeMacEntry 1 }

cwdIfHeSyncInterval OBJECT-TYPE
    SYNTAX INTEGER(1..200)
--  Units
--    Milliseconds
    ACCESS read-write
    STATUS mandatory
    DESCRIPTION
        "The interval between HE transmission of successive SYNC 
         messages at this interface."
    REFERENCE
        "Data Over Cable Radio Frequency Interface Specification, 
         Sync Interval."
    ::= { cwdIfHeMacEntry 2 }

cwdIfHeUcdInterval OBJECT-TYPE
    SYNTAX INTEGER(1..2000)
--  Units
--    Milliseconds
    ACCESS read-write
    STATUS mandatory
    DESCRIPTION
        "The interval between HE transmission of successive
         Upstream Channel Descriptor messages for each upstream
         channel at this interface."
    REFERENCE
        "Data Over Cable Radio Frequency Interface Specification, 
         UCD Interval."
    ::= { cwdIfHeMacEntry 3 }

cwdIfHeMaxServiceIds OBJECT-TYPE
    SYNTAX INTEGER(1..16383)
    ACCESS read-only
    STATUS mandatory
    DESCRIPTION
        "The maximum number of service IDs that may be 
         simultaneously active. "
    REFERENCE
        "Data Over Cable Radio Frequency Interface Specification, 
         Appendix A.  Well-Known Addresses. 
                  A.2 MAC Service IDs."
    ::= { cwdIfHeMacEntry 4 }

cwdIfHeInsertionInterval OBJECT-TYPE
    SYNTAX TimeInterval
--    Rsyntax INTEGER(0..2147483647)
    ACCESS read-write
    STATUS mandatory
    DESCRIPTION
        "The amount of time between each broadcast station 
         maintenance grant. Broadcast station maintenance
         grants are used to allow new subscriber units to join the
         network. Zero indicates that a vendor-specific algorithm
         is used instead of a fixed time. Maximum amount of time
         permitted by the DOCSIS specification is 2 seconds."
    REFERENCE
        "Data Over Cable Radio Frequency Interface Specification, 
         Ranging Interval."
    ::= { cwdIfHeMacEntry 5 }

cwdIfHeInvitedRangingAttempts OBJECT-TYPE
    SYNTAX INTEGER(0..1024)
    ACCESS read-write
    STATUS mandatory
    DESCRIPTION
        "The maximum number of attempts to make on invitations
         for ranging requests. A value of zero means the system 
         should attempt to range forever."
    ::= { cwdIfHeMacEntry 6 }

cwdIfHeStatusTable OBJECT-TYPE
    SYNTAX SEQUENCE OF CwdIfHeStatusEntry
    ACCESS not-accessible
    STATUS mandatory
    DESCRIPTION
        "For the MAC layer, this group maintains a number of 
         status objects and counters."
    ::= { cwdIfHeObjects 2 }

cwdIfHeStatusEntry OBJECT-TYPE
    SYNTAX CwdIfHeStatusEntry
    ACCESS not-accessible
    STATUS mandatory
    DESCRIPTION
        "Status entry for a single MAC layer.
         An entry in this table exists for each ifEntry with an
         ifType of propDocsWirelessMacLayer(nnn)."
    INDEX { ifIndex }
    ::= { cwdIfHeStatusTable 1 }

CwdIfHeStatusEntry ::= SEQUENCE {
    cwdIfHeStatusInvalidRangeReqs Counter,
    cwdIfHeStatusRangingAborteds Counter,
    cwdIfHeStatusInvalidRegReqs Counter,
    cwdIfHeStatusFailedRegReqs Counter,
    cwdIfHeStatusInvalidDataReqs Counter,
    cwdIfHeStatusT5Timeouts Counter
    }

cwdIfHeStatusInvalidRangeReqs OBJECT-TYPE
    SYNTAX Counter
    ACCESS read-only
    STATUS mandatory
    DESCRIPTION
        "This object counts invalid RNG-REQ messages received on
         this interface."
    ::= { cwdIfHeStatusEntry 1 }

cwdIfHeStatusRangingAborteds OBJECT-TYPE
    SYNTAX Counter
    ACCESS read-only
    STATUS mandatory
    DESCRIPTION
        "This object counts ranging attempts that were explicitly
         aborted by the HE."
    ::= { cwdIfHeStatusEntry 2 }

cwdIfHeStatusInvalidRegReqs OBJECT-TYPE
    SYNTAX Counter
    ACCESS read-only
    STATUS mandatory
    DESCRIPTION
        "This object counts invalid REG-REQ messages received on
         this interface."
    ::= { cwdIfHeStatusEntry 3 }

cwdIfHeStatusFailedRegReqs OBJECT-TYPE
    SYNTAX Counter
    ACCESS read-only
    STATUS mandatory
    DESCRIPTION
        "This object counts failed registration attempts, i.e.,
         authentication failures and class of service failures,
         on this interface."
    ::= { cwdIfHeStatusEntry 4 }

cwdIfHeStatusInvalidDataReqs OBJECT-TYPE
    SYNTAX Counter
    ACCESS read-only
    STATUS mandatory
    DESCRIPTION
        "This object counts invalid data request messages
         received on this interface."
    ::= { cwdIfHeStatusEntry 5 }

cwdIfHeStatusT5Timeouts OBJECT-TYPE
    SYNTAX Counter
    ACCESS read-only
    STATUS mandatory
    DESCRIPTION
        "This object counts the number of times counter T5
         expired on this interface.
         The T5 timer is the 'Wait for Upstream Channel Change 
         Response Timer' on the Head end."
    REFERENCE
        "Data Over Cable Radio Frequency Interface Specification, 
         Sync Interval. Appendix B"
    ::= { cwdIfHeStatusEntry 6 }

cwdIfHeSuStatusTable OBJECT-TYPE
    SYNTAX SEQUENCE OF CwdIfHeSuStatusEntry
    ACCESS not-accessible
    STATUS mandatory
    DESCRIPTION
        "A set of objects in the HE, maintained for each
         Subscriber unit connected to this HE."
    ::= { cwdIfHeObjects 3 }

cwdIfHeSuStatusEntry OBJECT-TYPE
    SYNTAX CwdIfHeSuStatusEntry
    ACCESS not-accessible
    STATUS mandatory
    DESCRIPTION
        "Status information for a single Subscriber unit.
         An entry in this table exists for each Subscriber unit 
         that is connected to the HE implementing this table."
    INDEX { cwdIfHeSuStatusIndex }
    ::= { cwdIfHeSuStatusTable 1 }

CwdIfHeSuStatusEntry ::= SEQUENCE {
    cwdIfHeSuStatusIndex INTEGER,
    cwdIfHeSuStatusMacAddress MacAddress,
    cwdIfHeSuStatusIpAddress IpAddress,
    cwdIfHeSuStatusDownChanIfIndex InterfaceIndexOrZero,
    cwdIfHeSuStatusUpChanIfIndex InterfaceIndexOrZero,
    cwdIfHeSuStatusRxPower INTEGER,
    cwdIfHeSuStatusTimingOffset Gauge,
    cwdIfHeSuStatusValue INTEGER,
    cwdIfHeSuStatusIfIndex InterfaceIndex,
    cwdIfHeSuStatusServiceId INTEGER
    }

cwdIfHeSuStatusIndex OBJECT-TYPE
    SYNTAX INTEGER(1..2147483647)
    ACCESS not-accessible
    STATUS mandatory
    DESCRIPTION
        "Index value to uniquely identify an entry in this table.
         For an individual Subscriber Unit, this index value should
         not change during HE uptime."
    ::= { cwdIfHeSuStatusEntry 1 }

cwdIfHeSuStatusMacAddress OBJECT-TYPE
    SYNTAX MacAddress
--    Rsyntax OCTET STRING(SIZE(6))
    ACCESS read-only
    STATUS mandatory
    DESCRIPTION
        "MAC address of this Subscriber Unit. If the Subscriber
         Unit has multiple MAC addresses, this is the MAC
         address associated with the Wireless interface.
         Each SU has only one wireless MAC interface."
    ::= { cwdIfHeSuStatusEntry 2 }

cwdIfHeSuStatusIpAddress OBJECT-TYPE
    SYNTAX IpAddress
    ACCESS read-only
    STATUS mandatory
    DESCRIPTION
        "IP address of this Subscriber Unit. If the Subscriber 
         Unit has no IP address assigned, or the IP address is
         unknown, this object returns a value of 0.0.0.0. If 
         the Subscriber Unit has multiple IP addresses, this 
         object returns the IP address associated with the 
         Wireless interface. Each SU has only one wireless 
         MAC interface."
    ::= { cwdIfHeSuStatusEntry 3 }

cwdIfHeSuStatusDownChanIfIndex OBJECT-TYPE
    SYNTAX InterfaceIndexOrZero
--    Rsyntax INTEGER(0..2147483647)
    ACCESS read-only
    STATUS mandatory
    DESCRIPTION
        "IfIndex of the downstream channel this Subscriber Unit
         is connected to. If the downstream channel is unknown, 
         this object returns a value of zero."
    ::= { cwdIfHeSuStatusEntry 4 }

cwdIfHeSuStatusUpChanIfIndex OBJECT-TYPE
    SYNTAX InterfaceIndexOrZero
--    Rsyntax INTEGER(0..2147483647)
    ACCESS read-only
    STATUS mandatory
    DESCRIPTION
        "IfIndex of the upstream channel this Subscriber Unit
         is connected to. If the upstream channel is unknown, 
         this object returns a value of zero."
    ::= { cwdIfHeSuStatusEntry 5 }

cwdIfHeSuStatusRxPower OBJECT-TYPE
    SYNTAX INTEGER(-80..33)
--  Units
--    dBm Decibel milliwatts
    ACCESS read-only
    STATUS mandatory
    DESCRIPTION
        "The receive power as perceived for upstream data from
         this subscriber unit.
         If the receive power is unknown, this object returns
         a value of zero."
    ::= { cwdIfHeSuStatusEntry 6 }

cwdIfHeSuStatusTimingOffset OBJECT-TYPE
    SYNTAX Gauge
    ACCESS read-only
    STATUS mandatory
    DESCRIPTION
        "A measure of the current round trip time for this SU.
         Used for timing of SU upstream transmissions to ensure
         synchronized arrivals at the HE. Units are in terms
         of (cwdIfUpstreamMiniSlotTimeBaseTick/64). Returns
         zero if the value is unknown."
    ::= { cwdIfHeSuStatusEntry 7 }

cwdIfHeSuStatusValue OBJECT-TYPE
    SYNTAX INTEGER {
        other(1),
        ranging(2),
        rangingAborted(3),
        rangingComplete(4),
        ipComplete(5),
        registrationComplete(6),
        accessDenied(7)
        }
    ACCESS read-only
    STATUS mandatory
    DESCRIPTION
        "Current subscriber unit connectivity state, as specified
         in the RF Interface Specification. Returned status
         information is the SU status as assumed by the HE,
         and indicates the following events:
         other(1)
            Any state other than below.
         ranging(2)
            The HE has received an Initial Ranging Request
            message from the SU, and the ranging process is not
            yet complete.
         rangingAborted(3)
            The HE has sent a Ranging Abort message to the SU.
         rangingComplete(4)
            The HE has sent a Ranging Complete message to the SU.
         ipComplete(5)
            The HE has received a DHCP reply message and forwarded
            it to the SU.
         registrationComplete(6)
            The HE has sent a Registration Response message to
            the SU.
         accessDenied(7)
            The HE has sent a Registration Aborted message
            to the SU.
         The HE only needs to report states it is able to detect."
    REFERENCE
        "Data over Cable Radio Frequency Interface Specification,
         Chapter 7.2."
    ::= { cwdIfHeSuStatusEntry 8 }

cwdIfHeSuStatusIfIndex OBJECT-TYPE
    SYNTAX InterfaceIndex
--    Rsyntax INTEGER(1..2147483647)
    ACCESS read-only
    STATUS mandatory
    DESCRIPTION
        "The HE MAC interface index (ifType of 
         propDocsWirelessMacLayer(nnn)) that SU connects to."
    ::= { cwdIfHeSuStatusEntry 9 }

cwdIfHeSuStatusServiceId OBJECT-TYPE
    SYNTAX INTEGER(1..16383)
    ACCESS read-only
    STATUS mandatory
    DESCRIPTION
        "The SU's primary Service ID."
    ::= { cwdIfHeSuStatusEntry 10 }

cwdIfHeServiceTable OBJECT-TYPE
    SYNTAX SEQUENCE OF CwdIfHeServiceEntry
    ACCESS not-accessible
    STATUS mandatory
    DESCRIPTION
        "Describes the attributes of upstream service queues
         in a Head-end System."
    ::= { cwdIfHeObjects 4 }

cwdIfHeServiceEntry OBJECT-TYPE
    SYNTAX CwdIfHeServiceEntry
    ACCESS not-accessible
    STATUS mandatory
    DESCRIPTION
        "Describes the attributes of a single upstream bandwidth
         service queue.
         Entries in this table exist for each ifEntry with an
         ifType of propDocsWirelessMacLayer(nnn), and for 
         each service queue (Service ID) within this MAC layer.
         Entries in this table are created with the creation of
         individual Service IDs by the MAC layer and removed
         when a Service ID is removed."
    INDEX { ifIndex, cwdIfHeServiceId }
    ::= { cwdIfHeServiceTable 1 }

CwdIfHeServiceEntry ::= SEQUENCE {
    cwdIfHeServiceId INTEGER,
    cwdIfHeServiceSuStatusIndex INTEGER,
    cwdIfHeServiceAdminStatus INTEGER,
    cwdIfHeServiceQosProfile INTEGER,
    cwdIfHeServiceCreateTime TimeStamp,
    cwdIfHeServiceInOctets Counter,
    cwdIfHeServiceInPackets Counter
    }

cwdIfHeServiceId OBJECT-TYPE
    SYNTAX INTEGER(1..16383)
    ACCESS not-accessible
    STATUS mandatory
    DESCRIPTION
        "Identifies a service queue for upstream bandwidth. The 
         attributes of this service queue are shared between the
         Subscriber unit and the Head-end System.
         The HE allocates upstream bandwidth to this service 
         queue based on requests from the SU and on the class of
         service associated with this queue."
    ::= { cwdIfHeServiceEntry 1 }

cwdIfHeServiceSuStatusIndex OBJECT-TYPE
    SYNTAX INTEGER(0..2147483647)
    ACCESS read-only
    STATUS mandatory
    DESCRIPTION
        "Pointer to an entry in cwdIfHeSuStatusTable identifying
         the Subscriber unit using this Service Queue."
    ::= { cwdIfHeServiceEntry 2 }

cwdIfHeServiceAdminStatus OBJECT-TYPE
    SYNTAX INTEGER {
        enabled(1),
        disabled(2),
        destroyed(3)
        }
    ACCESS read-write
    STATUS mandatory
    DESCRIPTION
        "Allows a service class for a particular modem to be
         suppressed, (re-)enabled, or deleted altogether."
    ::= { cwdIfHeServiceEntry 3 }

cwdIfHeServiceQosProfile OBJECT-TYPE
    SYNTAX INTEGER(0..16383)
    ACCESS read-only
    STATUS mandatory
    DESCRIPTION
        "The index in cwdIfQosProfileTable describing the quality
         of service attributes associated with this particular
         service. If cwdIfQosProfileTable is not supported, this
         object returns the value of zero."
    ::= { cwdIfHeServiceEntry 4 }

cwdIfHeServiceCreateTime OBJECT-TYPE
    SYNTAX TimeStamp
--    Rsyntax TimeTicks
    ACCESS read-only
    STATUS mandatory
    DESCRIPTION
        "The value of sysUpTime when this entry was created."
    ::= { cwdIfHeServiceEntry 5 }

cwdIfHeServiceInOctets OBJECT-TYPE
    SYNTAX Counter
    ACCESS read-only
    STATUS mandatory
    DESCRIPTION
        "The cumulative number of Packet Data octets received
         on this Service ID. The count does not include the
         size of the Wireless MAC header"
    ::= { cwdIfHeServiceEntry 6 }

cwdIfHeServiceInPackets OBJECT-TYPE
    SYNTAX Counter
    ACCESS read-only
    STATUS mandatory
    DESCRIPTION
        "The cumulative number of Packet Data packets received
         on this Service ID."
    ::= { cwdIfHeServiceEntry 7 }

cwdIfHeQosProfilePermissions OBJECT-TYPE
    SYNTAX OCTET STRING(SIZE(1..2))
        -- BITS are:
        --   createByManagement(0)
        --   updateByManagement(1)
        --   createBySubscriberUnits(2)
    ACCESS read-write
    STATUS mandatory
    DESCRIPTION
        "This object specifies permitted methods of creating
         entries in cwdIfQosProfileTable.
         CreateByManagement(0) is set if entries can be created
         using SNMP. UpdateByManagement(1) is set if updating
         entries using SNMP is permitted.
         CreateBySubscriberUnits(2) is set if entries can be
         created based on information in REG-REQ MAC messages
         received from Subscriber units.  Information in this
         object is only applicable if cwdIfQosProfileTable is
         implemented as read-create.
         Otherwise, this object is implemented as read-only
         and returns CreateBySubscriberUnits(2).
         Either CreateByManagement(0) or
         CreateBySubscriberUnits(2) must be set when writing
         to this object.  If this object has a value of
         createByManagement(2) the qos entries can be created
         and modified by the management. 
         If this object has a value of UpdateByManagement(1)
         the qos entries can be updated my management irrespective
         of who created it. But the management cannot create
         new entry in the cwdIfQosProfileTable."
    ::= { cwdIfHeObjects 6 }

cwdIfBasicGroup OBJECT IDENTIFIER ::= { cwdIfGroups 1 }
-- OBJECT-GROUP
--  Status
--    mandatory
--  Descr
--    Group of objects implemented in both Subscriber Units and
--     Head-end Systems.
--  objects
--    cwdIfChannelUpFrequency, cwdIfChannelUpWidth, 
--    cwdIfChannelDownFrequency, cwdIfChannelDownWidth, 
--    cwdIfChannelMiniSlotTimeBaseTick, 
--    cwdIfChannelSubChannelPlanVer, 
--    cwdIfDownChannelSubChannelNumber, cwdIfDownChannelId, 
--    cwdIfDownChannelFrequency, cwdIfDownChannelWidth, 
--    cwdIfDownChannelPower, cwdIfDownChannelModProfileIndex, 
--    cwdIfUpChannelSubChannelNumber, cwdIfUpChannelId, 
--    cwdIfUpChannelFrequency, cwdIfUpChannelWidth, 
--    cwdIfUpChannelTargetPower, cwdIfUpChannelModProfileIndex, 
--    cwdIfUpChannelSlotSize, cwdIfUpChannelTxTimingOffset, 
--    cwdIfUpChannelRangBackoffStart, cwdIfUpChannelRangBackoffEnd, 
--    cwdIfUpChannelTxBackoffStart, cwdIfUpChannelTxBackoffEnd, 
--    cwdIfSigQIncludesContention, cwdIfSigQUnerroreds, 
--    cwdIfSigQCorrecteds, cwdIfSigQUncorrectables, 
--    cwdIfSigQSignalNoise

cwdIfHeGroup OBJECT IDENTIFIER ::= { cwdIfGroups 7 }
-- OBJECT-GROUP
--  Status
--    mandatory
--  Descr
--    Group of objects implemented in Head-end
--     Systems.
--  objects
--    cwdIfHeCapabilities, cwdIfHeSyncInterval, cwdIfHeUcdInterval, 
--    cwdIfHeMaxServiceIds, cwdIfHeInsertionInterval, 
--    cwdIfHeInvitedRangingAttempts, cwdIfHeStatusInvalidRangeReqs, 
--    cwdIfHeStatusRangingAborteds, cwdIfHeStatusInvalidRegReqs, 
--    cwdIfHeStatusFailedRegReqs, cwdIfHeStatusInvalidDataReqs, 
--    cwdIfHeStatusT5Timeouts, cwdIfHeSuStatusMacAddress, 
--    cwdIfHeSuStatusIpAddress, cwdIfHeSuStatusDownChanIfIndex, 
--    cwdIfHeSuStatusUpChanIfIndex, cwdIfHeSuStatusRxPower, 
--    cwdIfHeSuStatusTimingOffset, cwdIfHeSuStatusValue, 
--    cwdIfHeSuStatusIfIndex, cwdIfHeSuStatusServiceId, 
--    cwdIfHeServiceSuStatusIndex, cwdIfHeServiceAdminStatus, 
--    cwdIfHeServiceQosProfile, cwdIfHeServiceCreateTime, 
--    cwdIfHeServiceInOctets, cwdIfHeServiceInPackets

cwdIfSuGroup OBJECT IDENTIFIER ::= { cwdIfGroups 2 }
-- OBJECT-GROUP
--  Status
--    mandatory
--  Descr
--    Group of objects implemented in Subscriber Units.
--  objects
--    cwdIfSuHeAddress, cwdIfSuCapabilities, 
--    cwdIfSuRangingRespTimeout, cwdIfSuStatusValue, 
--    cwdIfSuStatusCode, cwdIfSuStatusTxPower, cwdIfSuStatusResets, 
--    cwdIfSuStatusLostSyncs, cwdIfSuStatusInvalidMaps, 
--    cwdIfSuStatusInvalidUcds, cwdIfSuStatusInvalidRangingResp, 
--    cwdIfSuStatusInvalidRegResp, cwdIfSuStatusT1Timeouts, 
--    cwdIfSuStatusT2Timeouts, cwdIfSuStatusT3Timeouts, 
--    cwdIfSuStatusT4Timeouts, cwdIfSuStatusRangingAborteds, 
--    cwdIfSuServiceQosProfile, cwdIfSuServiceTxSlotsImmed, 
--    cwdIfSuServiceTxSlotsDed, cwdIfSuServiceTxRetries, 
--    cwdIfSuServiceTxExceeded, cwdIfSuServiceRqRetries, 
--    cwdIfSuServiceRqExceeded

cwdIfQosGroup OBJECT IDENTIFIER ::= { cwdIfGroups 3 }
-- OBJECT-GROUP
--  Status
--    mandatory
--  Descr
--    Quality of Service related group of objects.
--     This group is implemented in both Subscriber Units and
--     Head-end Systems.
--  objects
--    cwdIfQosProfPriority, cwdIfQosProfMaxUpBandwidth, 
--    cwdIfQosProfGuarUpBandwidth, cwdIfQosProfMaxDownBandwidth, 
--    cwdIfQosProfMaxTxBurst, cwdIfQosProfBaselinePrivacy, 
--    cwdIfQosProfStatus

cwdIfQosHeGroup OBJECT IDENTIFIER ::= { cwdIfGroups 4 }
-- OBJECT-GROUP
--  Status
--    mandatory
--  Descr
--    Quality of Service related group of objects.
--     This group is implemented in Head-end
--     Systems only.
--  objects
--    cwdIfHeQosProfilePermissions

cwdIfModGroup OBJECT IDENTIFIER ::= { cwdIfGroups 5 }
-- OBJECT-GROUP
--  Status
--    mandatory
--  Descr
--    Objects that describe modulation characteristics
--     of a channel.
--     This group is implemented in both Subscriber Units and
--     Head-end Systems.
--  objects
--    cwdIfModRowStatus, cwdIfModBandwidth, cwdIfModThroughput, 
--    cwdIfModBurstLength, cwdIfModMultipathRobustness

cwdIfBasicCompliance OBJECT IDENTIFIER ::= { cwdIfCompliances 2 }
-- MODULE-COMPLIANCE
--  Status
--    mandatory
--  Descr
--    The compliance statement for wireless devices that 
--     implement MCNS compliant Radio Frequency Interfaces.
--  Module
--    >>current<<
--   MandGroup
--    cwdIfBasicGroup
--   OptGroup
--    cwdIfSuGroup
--   OptGroup
--    cwdIfHeGroup
--   OptGroup
--    cwdIfQosGroup
--   OptGroup
--    cwdIfQosHeGroup
--   OptGroup
--    cwdIfModGroup
--   ObjVar
--    cwdIfChannelDownFrequency
--   ObjVar
--    cwdIfChannelDownWidth
--   ObjVar
--    cwdIfChannelUpFrequency
--   ObjVar
--    cwdIfChannelUpWidth
--   ObjVar
--    cwdIfUpChannelTargetPower
--   ObjVar
--    cwdIfDownChannelSubChannelNumber
--   ObjVar
--    cwdIfDownChannelPower
--   ObjVar
--    cwdIfDownChannelModProfileIndex
--   ObjVar
--    cwdIfUpChannelSubChannelNumber
--   ObjVar
--    cwdIfUpChannelModProfileIndex
--   ObjVar
--    cwdIfUpChannelSlotSize
--   ObjVar
--    cwdIfUpChannelTxBackoffStart
--   ObjVar
--    cwdIfUpChannelTxBackoffEnd
--   ObjVar
--    cwdIfQosProfPriority
--   ObjVar
--    cwdIfQosProfMaxUpBandwidth
--   ObjVar
--    cwdIfQosProfGuarUpBandwidth
--   ObjVar
--    cwdIfQosProfMaxDownBandwidth
--   ObjVar
--    cwdIfQosProfMaxTxBurst
--   ObjVar
--    cwdIfQosProfBaselinePrivacy
--   ObjVar
--    cwdIfHeUcdInterval
--   ObjVar
--    cwdIfHeInvitedRangingAttempts
--   ObjVar
--    cwdIfHeQosProfilePermissions


END
