-- MIB created 11/06/100 11:24:18, by
--   SMIC (the next generation) version 1.6.29, November 22, 1994.

CISCO-CONTENT-ENGINE-MIB DEFINITIONS ::= BEGIN

-- From file: "CISCO-CONTENT-ENGINE-MIB.my"

IMPORTS
    Counter32
            FROM SNMPv2-SMI-v1
    OBJECT-TYPE
            FROM RFC-1212
    TRAP-TYPE
            FROM RFC-1215
    Unsigned32
            FROM CISCO-TC
    ciscoMgmt
            FROM CISCO-SMI;

ciscoContentEngineMIB OBJECT IDENTIFIER ::= { ciscoMgmt 178 }
-- MODULE-IDENTITY
--  LastUpdated
--    200002100000Z
--  OrgName
--    Cisco Systems, Inc.
--  ContactInfo
--    Cisco Systems Customer Service
--     Postal: 170 W Tasman Drive
--         San Jose, CA 95134-1706
--         USA
--         Tel: +1 800 553-NETS
--         E-mail: cs-webcache@cisco.com
--  Descr
--    The MIB module for the Cisco Content Engine from
--     Cisco Systems, Inc.
--  RevDate
--    200002100000Z
--  RevDescr
--    Initial version of this MIB module.

ciscoContentEngineMIBObjects OBJECT IDENTIFIER ::= { ciscoContentEngineMIB 1 }
cceHttpGroup    OBJECT IDENTIFIER ::= { ciscoContentEngineMIBObjects 1 }
cceHttpRequests OBJECT IDENTIFIER ::= { cceHttpGroup 1 }
cceHttpPerf     OBJECT IDENTIFIER ::= { cceHttpGroup 2 }
ciscoContentEngineMIBNotificationPrefix OBJECT IDENTIFIER ::= { ciscoContentEngineMIB 2 }
ciscoContentEngineMIBNotifications OBJECT IDENTIFIER ::= { ciscoContentEngineMIBNotificationPrefix 0 }
ciscoContentEngineMIBConformance OBJECT IDENTIFIER ::= { ciscoContentEngineMIB 3 }
ciscoContentEngineMIBCompliances OBJECT IDENTIFIER ::= { ciscoContentEngineMIBConformance 1 }
ciscoContentEngineMIBGroups OBJECT IDENTIFIER ::= { ciscoContentEngineMIBConformance 2 }

cceHttpRequestsTotal OBJECT-TYPE
    SYNTAX Counter32
    ACCESS read-only
    STATUS mandatory
    DESCRIPTION
        "Total number of end-user requests the HTTP proxy
         has received."
    ::= { cceHttpRequests 1 }

cceHttpRequestsNoCacheTotal OBJECT-TYPE
    SYNTAX Counter32
    ACCESS read-only
    STATUS mandatory
    DESCRIPTION
        "Total number of end-user requests the HTTP proxy
         has received which contain a header directive
         indicating that the object cannot be cached."
    ::= { cceHttpRequests 2 }

cceHttpRequestsClientErrorTotal OBJECT-TYPE
    SYNTAX Counter32
    ACCESS read-only
    STATUS mandatory
    DESCRIPTION
        "Total number of times the HTTP proxy has failed to fulfill 
         a request due to errors caused by client connections."
    ::= { cceHttpRequests 3 }

cceHttpRequestsServerErrorTotal OBJECT-TYPE
    SYNTAX Counter32
    ACCESS read-only
    STATUS mandatory
    DESCRIPTION
        "Total number of times the HTTP proxy has failed to fulfill 
         a request due to errors while fetching objects not in cache
         from remote servers."
    ::= { cceHttpRequests 4 }

cceHttpRequestsBlocked OBJECT-TYPE
    SYNTAX Counter32
    ACCESS read-only
    STATUS mandatory
    DESCRIPTION
        "The number of times the HTTP proxy has blocked a request
         due to URL filtering or rules template blocking."
    ::= { cceHttpRequests 5 }

cceHttpRequestsHits OBJECT-TYPE
    SYNTAX Counter32
    ACCESS read-only
    STATUS mandatory
    DESCRIPTION
        "Total number of end-user requests whose response body was
         retrieved from the populated cache of the HTTP proxy."
    ::= { cceHttpRequests 6 }

cceHttpRequestsMisses OBJECT-TYPE
    SYNTAX Counter32
    ACCESS read-only
    STATUS mandatory
    DESCRIPTION
        "Total number of end-user requests whose response body is  
         retrieved from remote servers."
    ::= { cceHttpRequests 7 }

cceHttpRequestsBytesServedHits OBJECT-TYPE
    SYNTAX Counter32
    ACCESS read-only
    STATUS mandatory
    DESCRIPTION
        "Total number of bytes in the response bodies the HTTP proxy
         retrieved directly from its populated cache."
    ::= { cceHttpRequests 8 }

cceHttpRequestsBytesServedMisses OBJECT-TYPE
    SYNTAX Counter32
    ACCESS read-only
    STATUS mandatory
    DESCRIPTION
        "Total number of bytes in the response bodies the HTTP proxy  
         retrieved from remote servers."
    ::= { cceHttpRequests 9 }

cceHttpRequestsImsInmTotalCache OBJECT-TYPE
    SYNTAX Counter32
    ACCESS read-only
    STATUS mandatory
    DESCRIPTION
        "Total number of If-Modified-Since (IMS) and If-Not-Matched
         (INM) requests from the client served from the populated
         cache of the HTTP proxy without revalidation."
    ::= { cceHttpRequests 10 }

cceHttpRequestsImsInmTotalReval OBJECT-TYPE
    SYNTAX Counter32
    ACCESS read-only
    STATUS mandatory
    DESCRIPTION
        "Total number of If-Modified-Since (IMS) and If-Not-Matched
         (INM) requests from the client served from the populated
         cache of the HTTP proxy and revalidated with an IMS to the
         server."
    ::= { cceHttpRequests 11 }

cceHttpRequestsBytesClientIn OBJECT-TYPE
    SYNTAX Counter32
    ACCESS read-only
    STATUS mandatory
    DESCRIPTION
        "Total number of bytes received by the HTTP proxy from
         clients."
    ::= { cceHttpRequests 12 }

cceHttpRequestsBytesClientOut OBJECT-TYPE
    SYNTAX Counter32
    ACCESS read-only
    STATUS mandatory
    DESCRIPTION
        "Total number of bytes delivered by the HTTP proxy to
         clients."
    ::= { cceHttpRequests 13 }

cceHttpRequestsBytesServerIn OBJECT-TYPE
    SYNTAX Counter32
    ACCESS read-only
    STATUS mandatory
    DESCRIPTION
        "Total number of bytes received by the HTTP proxy from
         remote servers."
    ::= { cceHttpRequests 14 }

cceHttpRequestsBytesServerOut OBJECT-TYPE
    SYNTAX Counter32
    ACCESS read-only
    STATUS mandatory
    DESCRIPTION
        "Total number of bytes transmitted by the HTTP proxy
         to remote servers."
    ::= { cceHttpRequests 15 }

cceHttpHCRequestsTotal OBJECT-TYPE
    SYNTAX Counter32
    ACCESS read-only
    STATUS mandatory
    DESCRIPTION
        "Total number of end-user requests the HTTP proxy
         has received.  This object is a 64-bit
         version of cceHttpRequestsTotal."
    ::= { cceHttpRequests 16 }

cceHttpHCRequestsNoCacheTotal OBJECT-TYPE
    SYNTAX Counter32
    ACCESS read-only
    STATUS mandatory
    DESCRIPTION
        "Total number of end-user requests the HTTP proxy
         has received which contain a header directive
         indicating that the object cannot be cached.
         This object is a 64-bit version of
         cceHttpRequestsNoCacheTotal."
    ::= { cceHttpRequests 17 }

cceHttpHCRequestsClientErrorTotal OBJECT-TYPE
    SYNTAX Counter32
    ACCESS read-only
    STATUS mandatory
    DESCRIPTION
        "Total number of times the HTTP proxy has failed to fulfill 
         a request due to errors caused by client connections.
         This object is a 64-bit version of
         cceHttpRequestsClientErrorTotal."
    ::= { cceHttpRequests 18 }

cceHttpHCRequestsServerErrorTotal OBJECT-TYPE
    SYNTAX Counter32
    ACCESS read-only
    STATUS mandatory
    DESCRIPTION
        "Total number of times the HTTP proxy has failed to fulfill 
         a request due to errors while fetching objects not in cache
         from remote servers.  This object is a 64-bit version of
         cceHttpRequestsServerErrorTotal."
    ::= { cceHttpRequests 19 }

cceHttpHCRequestsBlocked OBJECT-TYPE
    SYNTAX Counter32
    ACCESS read-only
    STATUS mandatory
    DESCRIPTION
        "The number of times the HTTP proxy has blocked a request
         due to URL filtering or rules template blocking.
         This object is a 64-bit version of cceHttpRequestsBlocked."
    ::= { cceHttpRequests 20 }

cceHttpHCRequestsHits OBJECT-TYPE
    SYNTAX Counter32
    ACCESS read-only
    STATUS mandatory
    DESCRIPTION
        "Total number of end-user requests whose response body was
         retrieved from the populated cache of the HTTP proxy.
         This object is a 64-bit version of cceHttpRequestsHits."
    ::= { cceHttpRequests 21 }

cceHttpHCRequestsMisses OBJECT-TYPE
    SYNTAX Counter32
    ACCESS read-only
    STATUS mandatory
    DESCRIPTION
        "Total number of end-user requests whose response body is  
         retrieved from remote servers.  This object is a 64-bit
         version of cceHttpRequestsMisses."
    ::= { cceHttpRequests 22 }

cceHttpHCRequestsBytesServedHits OBJECT-TYPE
    SYNTAX Counter32
    ACCESS read-only
    STATUS mandatory
    DESCRIPTION
        "Total number of bytes in the response bodies the HTTP proxy
         retrieved directly from its populated cache.  This object
         is a 64-bit version of cceHttpRequestsBytesServedHits."
    ::= { cceHttpRequests 23 }

cceHttpHCRequestsBytesServedMisses OBJECT-TYPE
    SYNTAX Counter32
    ACCESS read-only
    STATUS mandatory
    DESCRIPTION
        "Total number of bytes in the response bodies the HTTP proxy  
         retrieved from remote servers.
         This object is a 64-bit version of
         cceHttpRequestsBytesServedMisses."
    ::= { cceHttpRequests 24 }

cceHttpHCRequestsImsInmTotalCache OBJECT-TYPE
    SYNTAX Counter32
    ACCESS read-only
    STATUS mandatory
    DESCRIPTION
        "Total number of If-Modified-Since (IMS) and If-Not-Matched
         (INM) requests from the client served from the populated
         cache of the HTTP proxy without revalidation.  This object
         is a 64-bit version of cceHttpRequestsImsInmTotalCache."
    ::= { cceHttpRequests 25 }

cceHttpHCRequestsImsInmTotalReval OBJECT-TYPE
    SYNTAX Counter32
    ACCESS read-only
    STATUS mandatory
    DESCRIPTION
        "Total number of If-Modified-Since (IMS) and If-Not-Matched
         (INM) requests from the client served from the populated
         cache of the HTTP proxy and revalidated with an IMS to the
         server.  This object is a 64-bit version of
         cceHttpRequestsImsInmTotalReval."
    ::= { cceHttpRequests 26 }

cceHttpHCRequestsBytesClientIn OBJECT-TYPE
    SYNTAX Counter32
    ACCESS read-only
    STATUS mandatory
    DESCRIPTION
        "Total number of bytes received by the HTTP proxy from
         clients.  This object is a 64-bit version of
         cceHttpRequestsBytesClientIn."
    ::= { cceHttpRequests 27 }

cceHttpHCRequestsBytesClientOut OBJECT-TYPE
    SYNTAX Counter32
    ACCESS read-only
    STATUS mandatory
    DESCRIPTION
        "Total number of bytes delivered by the HTTP proxy to
         clients.  This object is a 64-bit version of
         cceHttpRequestsBytesClientOut."
    ::= { cceHttpRequests 28 }

cceHttpHCRequestsBytesServerIn OBJECT-TYPE
    SYNTAX Counter32
    ACCESS read-only
    STATUS mandatory
    DESCRIPTION
        "Total number of bytes received by the HTTP proxy from
         remote servers.  This object is a 64-bit version of
         cceHttpRequestsBytesServerIn."
    ::= { cceHttpRequests 29 }

cceHttpHCRequestsBytesServerOut OBJECT-TYPE
    SYNTAX Counter32
    ACCESS read-only
    STATUS mandatory
    DESCRIPTION
        "Total number of bytes transmitted by the HTTP proxy
         to remote servers.  This object is a 64-bit version of
         cceHttpRequestsBytesServerOut."
    ::= { cceHttpRequests 30 }

cceHttpPerfSamplingTime OBJECT-TYPE
    SYNTAX Unsigned32(0..4294967295)
--    Rsyntax Gauge32(0..4294967295)
--  Units
--    seconds
    ACCESS read-only
    STATUS mandatory
    DESCRIPTION
        "Number of seconds in the last sampling time interval
         used to calculate the value of the cceHttpPerfReqPerSec
         and cceHttpPerfBytesPerSec objects."
    ::= { cceHttpPerf 1 }

cceHttpPerfReqPerSec OBJECT-TYPE
    SYNTAX Unsigned32(0..4294967295)
--    Rsyntax Gauge32(0..4294967295)
    ACCESS read-only
    STATUS mandatory
    DESCRIPTION
        "Number of requests per second the HTTP proxy
         has been servicing in the last sampling time."
    ::= { cceHttpPerf 2 }

cceHttpPerfBytesPerSec OBJECT-TYPE
    SYNTAX Unsigned32(0..4294967295)
--    Rsyntax Gauge32(0..4294967295)
--  Units
--    bytes-per-second
    ACCESS read-only
    STATUS mandatory
    DESCRIPTION
        "Bytes per second served in the last sampling time."
    ::= { cceHttpPerf 3 }

cceHttpPerfServiceTime OBJECT-TYPE
    SYNTAX Unsigned32(0..4294967295)
--    Rsyntax Gauge32(0..4294967295)
--  Units
--    milliseconds-per-req
    ACCESS read-only
    STATUS mandatory
    DESCRIPTION
        "Average duration of each connection serviced by the 
         HTTP proxy."
    ::= { cceHttpPerf 4 }

cceHttpPerfHitServiceTime OBJECT-TYPE
    SYNTAX Unsigned32(0..4294967295)
--    Rsyntax Gauge32(0..4294967295)
--  Units
--    milliseconds-per-req
    ACCESS read-only
    STATUS mandatory
    DESCRIPTION
        "Average duration required for the HTTP proxy to send a
         hit response.  A hit response is a response for which
         the object can be serviced from the populated cache of
         the HTTP proxy."
    ::= { cceHttpPerf 5 }

cceHttpPerfMissServiceTime OBJECT-TYPE
    SYNTAX Unsigned32(0..4294967295)
--    Rsyntax Gauge32(0..4294967295)
--  Units
--    milliseconds-per-req
    ACCESS read-only
    STATUS mandatory
    DESCRIPTION
        "Average duration required for the HTTP proxy to send a
         miss response.  A miss response is a response for which
         the object cannot be serviced from the populated cache
         of the HTTP proxy."
    ::= { cceHttpPerf 6 }

cceHttpPerfObjectSize OBJECT-TYPE
    SYNTAX Unsigned32(0..4294967295)
--    Rsyntax Gauge32(0..4294967295)
--  Units
--    bytes
    ACCESS read-only
    STATUS mandatory
    DESCRIPTION
        "Average size of the object served from the HTTP proxy."
    ::= { cceHttpPerf 7 }

cceHttpPerfCpuLoad OBJECT-TYPE
    SYNTAX Unsigned32(0..100)
--    Rsyntax Gauge32(0..100)
--  Units
--    percentage
    ACCESS read-only
    STATUS mandatory
    DESCRIPTION
        "Percentage of CPU load for the last 4 second sampling
         time interval."
    ::= { cceHttpPerf 8 }

ciscoContentEngineReadDiskError TRAP-TYPE
-- Reverse mappable trap
    ENTERPRISE ciscoContentEngineMIBNotificationPrefix
--  Status
--    mandatory
    DESCRIPTION
        "First read error occurred on the disk that is being
         accessed.  Additional information about the error
         is logged to syslog."
    ::= 1

ciscoContentEngineWriteDiskError TRAP-TYPE
-- Reverse mappable trap
    ENTERPRISE ciscoContentEngineMIBNotificationPrefix
--  Status
--    mandatory
    DESCRIPTION
        "First write error occurred on the disk that is being
         accessed.  Additional information about the error
         is logged to syslog."
    ::= 2

ciscoContentEngineWriteTransFailed TRAP-TYPE
-- Reverse mappable trap
    ENTERPRISE ciscoContentEngineMIBNotificationPrefix
--  Status
--    mandatory
    DESCRIPTION
        "Failed writing to working transaction log located in
         /local1/working.log.  Possible causes are system
         errors or the log having been removed."
    ::= 3

ciscoContentEngineDataDiskFailed TRAP-TYPE
-- Reverse mappable trap
    ENTERPRISE ciscoContentEngineMIBNotificationPrefix
--  Status
--    mandatory
    DESCRIPTION
        "A Content Engine data drive failed.  Additional
         information about the error is logged to syslog."
    ::= 4

ciscoContentEngineOverloadBypass TRAP-TYPE
-- Reverse mappable trap
    ENTERPRISE ciscoContentEngineMIBNotificationPrefix
--  Status
--    mandatory
    DESCRIPTION
        "A high watermark of percentage of capacity for transparent
         requests redirected to the Content Engine via WCCP
         (Web Cache Control Protocol) has been reached.
         Subsequent WCCP requests are rejected and forwarded
         to the Origin Server until the utilization falls
         below a low watermark."
    ::= 5

cceHttpReqGroup OBJECT IDENTIFIER ::= { ciscoContentEngineMIBGroups 1 }
-- OBJECT-GROUP
--  Status
--    mandatory
--  Descr
--    HTTP proxy request group with low capacity
--     Counter32 objects.
--  objects
--    cceHttpRequestsTotal, cceHttpRequestsNoCacheTotal, 
--    cceHttpRequestsClientErrorTotal, 
--    cceHttpRequestsServerErrorTotal, cceHttpRequestsBlocked, 
--    cceHttpRequestsHits, cceHttpRequestsMisses, 
--    cceHttpRequestsBytesServedHits, 
--    cceHttpRequestsBytesServedMisses, 
--    cceHttpRequestsImsInmTotalCache, 
--    cceHttpRequestsImsInmTotalReval, cceHttpRequestsBytesClientIn, 
--    cceHttpRequestsBytesClientOut, cceHttpRequestsBytesServerIn, 
--    cceHttpRequestsBytesServerOut

cceHttpHCReqGroup OBJECT IDENTIFIER ::= { ciscoContentEngineMIBGroups 2 }
-- OBJECT-GROUP
--  Status
--    mandatory
--  Descr
--    HTTP proxy request group with high capacity
--     Counter64 objects.
--  objects
--    cceHttpHCRequestsTotal, cceHttpHCRequestsNoCacheTotal, 
--    cceHttpHCRequestsClientErrorTotal, 
--    cceHttpHCRequestsServerErrorTotal, cceHttpHCRequestsBlocked, 
--    cceHttpHCRequestsHits, cceHttpHCRequestsMisses, 
--    cceHttpHCRequestsBytesServedHits, 
--    cceHttpHCRequestsBytesServedMisses, 
--    cceHttpHCRequestsImsInmTotalCache, 
--    cceHttpHCRequestsImsInmTotalReval, 
--    cceHttpHCRequestsBytesClientIn, 
--    cceHttpHCRequestsBytesClientOut, 
--    cceHttpHCRequestsBytesServerIn, 
--    cceHttpHCRequestsBytesServerOut

cceHttpPerfGroup OBJECT IDENTIFIER ::= { ciscoContentEngineMIBGroups 3 }
-- OBJECT-GROUP
--  Status
--    mandatory
--  Descr
--    HTTP proxy performance group.
--  objects
--    cceHttpPerfSamplingTime, cceHttpPerfReqPerSec, 
--    cceHttpPerfBytesPerSec, cceHttpPerfServiceTime, 
--    cceHttpPerfHitServiceTime, cceHttpPerfMissServiceTime, 
--    cceHttpPerfObjectSize, cceHttpPerfCpuLoad

ciscoContentEngineMIBCompliance OBJECT IDENTIFIER ::= { ciscoContentEngineMIBCompliances 1 }
-- MODULE-COMPLIANCE
--  Status
--    mandatory
--  Descr
--    The compliance statement for Cisco Systems entities which
--     implement the Content Engine applications.
--  Module
--    >>current<<
--   MandGroup
--    cceHttpReqGroup
--   MandGroup
--    cceHttpPerfGroup


END
