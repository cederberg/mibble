-- MIB created 6/25/99 12:58:11, by
--   SMIC (the next generation) version 1.6.29, November 22, 1994.

UDP-MIB DEFINITIONS ::= BEGIN

-- From file: "UDP-MIB.my"

IMPORTS
    Counter32, IpAddress, mib-2
            FROM SNMPv2-SMI-v1
    OBJECT-TYPE
            FROM RFC-1212;

udpMIB OBJECT IDENTIFIER ::= { mib-2 50 }
-- MODULE-IDENTITY
--  LastUpdated
--    9411010000Z
--  OrgName
--    IETF SNMPv2 Working Group
--  ContactInfo
--            Keith McCloghrie
--    
--     Postal: Cisco Systems, Inc.
--             170 West Tasman Drive
--             San Jose, CA  95134-1706
--             US
--    
--     Phone:  +1 408 526 5260
--     Email:  kzm@cisco.com
--  Descr
--    The MIB module for managing UDP implementations.
--  RevDate
--    9103310000Z
--  RevDescr
--    The initial revision of this MIB module was part of MIB-
--    II.

udp             OBJECT IDENTIFIER ::= { mib-2 7 }
udpMIBConformance OBJECT IDENTIFIER ::= { udpMIB 2 }
udpMIBCompliances OBJECT IDENTIFIER ::= { udpMIBConformance 1 }
udpMIBGroups    OBJECT IDENTIFIER ::= { udpMIBConformance 2 }

udpInDatagrams OBJECT-TYPE
    SYNTAX Counter32
    ACCESS read-only
    STATUS mandatory
    DESCRIPTION
        "The total number of UDP datagrams delivered to UDP users."
    ::= { udp 1 }

udpNoPorts OBJECT-TYPE
    SYNTAX Counter32
    ACCESS read-only
    STATUS mandatory
    DESCRIPTION
        "The total number of received UDP datagrams for which there
        was no application at the destination port."
    ::= { udp 2 }

udpInErrors OBJECT-TYPE
    SYNTAX Counter32
    ACCESS read-only
    STATUS mandatory
    DESCRIPTION
        "The number of received UDP datagrams that could not be
        delivered for reasons other than the lack of an application
        at the destination port."
    ::= { udp 3 }

udpOutDatagrams OBJECT-TYPE
    SYNTAX Counter32
    ACCESS read-only
    STATUS mandatory
    DESCRIPTION
        "The total number of UDP datagrams sent from this entity."
    ::= { udp 4 }

udpTable OBJECT-TYPE
    SYNTAX SEQUENCE OF UdpEntry
    ACCESS not-accessible
    STATUS mandatory
    DESCRIPTION
        "A table containing UDP listener information."
    ::= { udp 5 }

udpEntry OBJECT-TYPE
    SYNTAX UdpEntry
    ACCESS not-accessible
    STATUS mandatory
    DESCRIPTION
        "Information about a particular current UDP listener."
    INDEX { udpLocalAddress, udpLocalPort }
    ::= { udpTable 1 }

UdpEntry ::= SEQUENCE {
    udpLocalAddress IpAddress,
    udpLocalPort INTEGER
    }

udpLocalAddress OBJECT-TYPE
    SYNTAX IpAddress
    ACCESS read-only
    STATUS mandatory
    DESCRIPTION
        "The local IP address for this UDP listener.  In the case of
        a UDP listener which is willing to accept datagrams for any
        IP interface associated with the node, the value 0.0.0.0 is
        used."
    ::= { udpEntry 1 }

udpLocalPort OBJECT-TYPE
    SYNTAX INTEGER(0..65535)
    ACCESS read-only
    STATUS mandatory
    DESCRIPTION
        "The local port number for this UDP listener."
    ::= { udpEntry 2 }

udpGroup OBJECT IDENTIFIER ::= { udpMIBGroups 1 }
-- OBJECT-GROUP
--  Status
--    mandatory
--  Descr
--    The udp group of objects providing for management of UDP
--    entities.
--  objects
--    udpInDatagrams, udpNoPorts, udpInErrors, udpOutDatagrams, 
--    udpLocalAddress, udpLocalPort

udpMIBCompliance OBJECT IDENTIFIER ::= { udpMIBCompliances 1 }
-- MODULE-COMPLIANCE
--  Status
--    mandatory
--  Descr
--    The compliance statement for SNMPv2 entities which
--    implement UDP.
--  Module
--    >>current<<
--   MandGroup
--    udpGroup


END
