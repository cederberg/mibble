-- MIB file created 03-Jul-2003 10:19:01, by
--   SMICng version 2.2.11-beta(PRO)(Solaris), January 20, 2001. Enterprise key cisco.com

CISCO-RF-MIB DEFINITIONS ::= BEGIN

-- From file: "CISCO-RF-MIB.my"
-- Compile options "4 7 F H N W 03 06 0B 0G 0N 0T"

IMPORTS
    TruthValue, DateAndTime, TimeStamp, TimeInterval
            FROM SNMPv2-TC-v1
    SnmpAdminString
            FROM SNMP-FRAMEWORK-MIB
    ciscoMgmt
            FROM CISCO-SMI
    sysUpTime
            FROM RFC1213-MIB
    Counter, Gauge
            FROM RFC1155-SMI
    OBJECT-TYPE
            FROM RFC-1212
    TRAP-TYPE
            FROM RFC-1215;

ciscoRFMIB OBJECT IDENTIFIER ::= { ciscoMgmt 176 }
-- MODULE-IDENTITY
--  LastUpdated
--    200201070000Z
--  OrgName
--    Cisco Systems, Inc.
--  ContactInfo
--    Cisco Systems Customer Service
--     Postal: 170 West Tasman Drive
--             San Jose, CA 95134
--             USA
--     Tel: +1 800 553-NETS
--    
--     E-mail: cs-rf-mib@cisco.com
--  Descr
--    This MIB provides configuration control and status for the
--    Redundancy Framework (RF) subsystem.  RF provides a mechanism
--    for logical redundancy of software functionality and is
--    designed to support 1:1 redundancy on processor cards.  RF is
--    not intended to solve all redundancy schemes.  Nor is RF
--    designed to support redundant hardware, such as power
--    supplies.
--    
--    Redundancy is concerned with the duplication of data elements
--    and software functions to provide an alternative in case of
--    failure. It is a key component to meeting 99.999% availability
--    requirements for Class 5 carrier solutions.
--    
--    In the scope of this MIB definition, peer software elements
--    are redundant and redundant software elements are peers.
--  RevDate
--    200201070000Z
--  RevDescr
--    Added the following object in cRFStatus:
--        cRFStatusRFModeCapsTable
--    Added the following object in cRFCfg:
--        cRFCfgRedundancyOperMode
--    Updated description of following object in cRFCfg:
--        cRFCfgRedundancyMode
--  RevDate
--    200107200000Z
--  RevDescr
--    Added new sub-group
--        cRFHistory  
--    Added new table cRFHistorySwitchOverTable
--    which maintains the history of switchovers.
--    Also added objects: 
--        cRFStatusFailoverTime
--        cRFStatusPeerStandByEntryTime
--        cRFHistoryTableMaxLength
--        cRFHistoryColdStarts
--        cRFHistoryStandByAvailTime
--    Added textual convention:
--        RFUnitIdentifier.
--  RevDate
--    200106260000Z
--  RevDescr
--    Changed terminology:
--        'split-mode' is now 'maintenance-mode'
--    Added textual convention:
--        RFMode
--    Deprecated object:
--        cRFCfgSplitMode
--    Added objects:
--        cRFCfgMaintenanceMode
--        cRFCfgRedundancyMode
--        cRFCfgRedundancyModeDescr
--    Added enumeration values:
--        noAction(0)         to RFAction
--        activeExtraload(15) to RFState
--        activeHandback(16)  to RFState
--    Added new transition state to ciscoRFProgressionNotif:
--        activeExtraload
--    Update compliance and conformance statements
--  RevDate
--    200104030945Z
--  RevDescr
--    The initial revision of this MIB.

ciscoRFMIBObjects OBJECT IDENTIFIER ::= { ciscoRFMIB 1 }
cRFStatus       OBJECT IDENTIFIER ::= { ciscoRFMIBObjects 1 }
cRFCfg          OBJECT IDENTIFIER ::= { ciscoRFMIBObjects 2 }
cRFHistory      OBJECT IDENTIFIER ::= { ciscoRFMIBObjects 3 }
ciscoRFMIBNotificationsPrefix OBJECT IDENTIFIER ::= { ciscoRFMIB 2 }
ciscoRFMIBNotifications OBJECT IDENTIFIER ::= { ciscoRFMIBNotificationsPrefix 0 }
ciscoRFMIBConformance OBJECT IDENTIFIER ::= { ciscoRFMIB 3 }
ciscoRFMIBCompliances OBJECT IDENTIFIER ::= { ciscoRFMIBConformance 1 }
ciscoRFMIBGroups OBJECT IDENTIFIER ::= { ciscoRFMIBConformance 2 }

RFState ::= INTEGER {
        notKnown(1),
        disabled(2),
        initialization(3),
        negotiation(4),
        standbyCold(5),
        standbyColdConfig(6),
        standbyColdFileSys(7),
        standbyColdBulk(8),
        standbyHot(9),
        activeFast(10),
        activeDrain(11),
        activePreconfig(12),
        activePostconfig(13),
        active(14),
        activeExtraload(15),
        activeHandback(16)
        }
-- TEXTUAL-CONVENTION
--  Status
--    mandatory
--  Descr
--    The current state of the RF subsystem.
--    
--    notKnown
--        - state is unknown
--    disabled
--        - RF is not operational on this unit
--    initialization
--        - establish necessary system services
--    negotiation
--        - peer unit discovery and negotiation
--    standbyCold
--        - client notification on standby unit
--    *standbyColdConfig
--        - standby cfg is updated from active cfg
--    *standbyColdFileSys
--        - standby file system (FS) is updated from the active FS
--    *standbyColdBulk
--        - clients sync data from active to standby
--    standbyHot
--        - incremental client data sync continues. This unit is
--          ready to take over activity.
--    activeFast
--        - call maintenance efforts during a SWACT
--    activeDrain
--        - client clean-up phase
--    activePreconfig
--        - unit is active but has not read its configuration
--    activePostconfig
--        - unit is active and is post-processing its configuration
--    active
--        - unit is active and processing calls
--    activeExtraload
--        - unit is active and processing calls for all feature
--          boards in the system
--    activeHandback
--        - unit is active, processing calls and is in the process
--          of handing some resources to the other unit in the system
--    
--    * Sub-state of 'standbyCold'

RFMode ::= INTEGER {
        nonRedundant(1),
        staticLoadShareNonRedundant(2),
        dynamicLoadShareNonRedundant(3),
        staticLoadShareRedundant(4),
        dynamicLoadShareRedundant(5),
        coldStandbyRedundant(6),
        warmStandbyRedundant(7),
        hotStandbyRedundant(8)
        }
-- TEXTUAL-CONVENTION
--  Status
--    mandatory
--  Descr
--    The characterization of the redundancy subsystem.
--    
--    nonRedundant
--        - the system is not redundant.
--    staticLoadShareNonRedundant
--        - the system is *not* redundant but is load sharing.
--          The load sharing is *not* based on operational load
--          (i.e. number of calls, etc).
--    dynamicLoadShareNonRedundant
--        - the system is *not* redundant but is load sharing.
--          Load sharing is based on operational load.
--    staticLoadShareRedundant
--        - the system is redundant and is load sharing.  The
--          load sharing is *not* based on operational load.
--    dynamicLoadShareRedundant
--        - the system is redundant and is load sharing.  Load
--          sharing is based on operational load.
--    coldStandbyRedundant
--        - the system is redundant but the redundant peer unit is
--          not fully initialized and is not able to retain
--          established calls.
--    warmStandbyRedundant
--        - the system is redundant and the redundant peer unit is
--          immediately able to handle new calls.  The redundant
--          unit is unable to retain established calls.
--    hotStandbyRedundant
--        - the system is redundant and the redundant peer unit is
--          able to 'instantaneously' retain established calls and
--          immediately able to handle new calls.

RFAction ::= INTEGER {
        --?? enum value of zero may cause problems
        noAction(0),
        reloadPeer(1),
        reloadShelf(2),
        switchActivity(3),
        forceSwitchActivity(4)
        }
-- TEXTUAL-CONVENTION
--  Status
--    mandatory
--  Descr
--    Administrative commands to invoke in the RF subsystem.
--    
--    noAction
--        - no action (do nothing)
--    reloadPeer
--        - reset the redundant peer unit
--    reloadShelf
--        - reset the entire shelf
--    switchActivity
--        - safely SWACT to peer unit and go standby
--    forceSwitchActivity
--        - switch activity; ignoring pre-conditions, system
--          warnings and safety checks.
--    
--    When the value is set to 'noAction' no operation is performed.
--    When read, the value 'noAction' is always returned.

RFSwactReasonType ::= INTEGER {
        unsupported(1),
        none(2),
        notKnown(3),
        userInitiated(4),
        userForced(5),
        activeUnitFailed(6),
        activeUnitRemoved(7)
        }
-- TEXTUAL-CONVENTION
--  Status
--    mandatory
--  Descr
--    Reason codes for the switch of activity from an active
--    redundant unit to its standby peer unit.
--    
--    unsupported
--        - the 'reason code' is an unsupported feature
--    none
--        - no SWACT has occurred
--    notKnown
--        - reason is unknown
--    userInitiated
--        - a safe, manual SWACT was initiated by user
--    userForced
--        - a manual SWACT was forced by user; ignoring
--          pre-conditions, warnings and safety checks
--    activeUnitFailed
--        - active unit failure caused an auto SWACT
--    activeUnitRemoved
--        - active unit removal caused an auto SWACT

RFUnitIdentifier ::= INTEGER(0..2147483647)
-- TEXTUAL-CONVENTION
--  Status
--    mandatory
--  Descr
--    A unique identifier for Active/Standby unit.

cRFStatusUnitId OBJECT-TYPE
    SYNTAX RFUnitIdentifier
--    Rsyntax INTEGER(0..2147483647)
    ACCESS read-only
    STATUS mandatory
    DESCRIPTION
        "A unique identifier for this redundant unit. This identifier
        is implementation-specific but the method for selecting the id
        must remain consistent throughout the redundant system.
        
        Some example identifiers include: slot id, physical or logical
        entity id, or a unique id assigned internally by the RF
        subsystem."
    ::= { cRFStatus 1 }

cRFStatusUnitState OBJECT-TYPE
    SYNTAX RFState
--    Rsyntax INTEGER {
--        notKnown(1),
--        disabled(2),
--        initialization(3),
--        negotiation(4),
--        standbyCold(5),
--        standbyColdConfig(6),
--        standbyColdFileSys(7),
--        standbyColdBulk(8),
--        standbyHot(9),
--        activeFast(10),
--        activeDrain(11),
--        activePreconfig(12),
--        activePostconfig(13),
--        active(14),
--        activeExtraload(15),
--        activeHandback(16)
--        }
    ACCESS read-only
    STATUS mandatory
    DESCRIPTION
        "The current state of RF on this unit."
    ::= { cRFStatus 2 }

cRFStatusPeerUnitId OBJECT-TYPE
    SYNTAX RFUnitIdentifier
--    Rsyntax INTEGER(0..2147483647)
    ACCESS read-only
    STATUS mandatory
    DESCRIPTION
        "A unique identifier for the redundant peer unit. This
        identifier is implementation-specific but the method for
        selecting the id must remain consistent throughout the
        redundant system.
        
        Some example identifiers include: slot id, physical or logical
        entity id, or a unique id assigned internally by the RF
        subsystem."
    ::= { cRFStatus 3 }

cRFStatusPeerUnitState OBJECT-TYPE
    SYNTAX RFState
--    Rsyntax INTEGER {
--        notKnown(1),
--        disabled(2),
--        initialization(3),
--        negotiation(4),
--        standbyCold(5),
--        standbyColdConfig(6),
--        standbyColdFileSys(7),
--        standbyColdBulk(8),
--        standbyHot(9),
--        activeFast(10),
--        activeDrain(11),
--        activePreconfig(12),
--        activePostconfig(13),
--        active(14),
--        activeExtraload(15),
--        activeHandback(16)
--        }
    ACCESS read-only
    STATUS mandatory
    DESCRIPTION
        "The current state of RF on the peer unit."
    ::= { cRFStatus 4 }

cRFStatusPrimaryMode OBJECT-TYPE
    SYNTAX TruthValue
--    Rsyntax INTEGER {
--        true(1),
--        false(2)
--        }
    ACCESS read-only
    STATUS mandatory
    DESCRIPTION
        "Indicates whether this is the primary redundant unit or
        not. If this unit is the primary unit, this object is true. If
        this unit is the secondary unit, this object is false.
        
        Note that the terms 'primary/secondary' are not synonymous
        with the terms 'active/standby'.  At any given time, the
        primary unit may be the active unit, or the primary unit may
        be the standby unit.  Likewise, the secondary unit, at any
        given time, may be the active unit, or the secondary unit may
        be the standby unit.
        
        The primary unit is given a higher priority or precedence over
        the secondary unit. In a race condition (usually at
        initialization time) or any situation where the redundant
        units are unable to successfully negotiate activity between
        themselves, the primary unit will always become the active
        unit and the secondary unit will fall back to standby. Only
        one redundant unit can be the primary unit at any given time.
        
        The algorithm for determining the primary unit is system
        dependent, such as 'the redundant unit with the lower numeric
        unit id is always the primary unit.'"
    ::= { cRFStatus 5 }

cRFStatusDuplexMode OBJECT-TYPE
    SYNTAX TruthValue
--    Rsyntax INTEGER {
--        true(1),
--        false(2)
--        }
    ACCESS read-only
    STATUS mandatory
    DESCRIPTION
        "Indicates whether the redundant peer unit has been detected
        or not. If the redundant peer unit is detected, this object is
        true. If the redundant peer unit is not detected, this object
        is false."
    ::= { cRFStatus 6 }

cRFStatusManualSwactInhibit OBJECT-TYPE
    SYNTAX TruthValue
--    Rsyntax INTEGER {
--        true(1),
--        false(2)
--        }
    ACCESS read-only
    STATUS mandatory
    DESCRIPTION
        "Indicates whether a manual switch of activity is
        permitted. If a manual switch of activity is allowed, this
        object is false. If a manual switch of activity is not
        allowed, this object is true.  Note that the value of this
        object is the inverse of the status of manual SWACTs.
        
        This object does not indicate whether a switch of activity is
        or has occurred. This object only indicates if the
        user-controllable capability is enabled or not.
        
        A switch of activity is the event in which the standby
        redundant unit becomes active and the previously active unit
        becomes standby."
    ::= { cRFStatus 7 }

cRFStatusLastSwactReasonCode OBJECT-TYPE
    SYNTAX RFSwactReasonType
--    Rsyntax INTEGER {
--        unsupported(1),
--        none(2),
--        notKnown(3),
--        userInitiated(4),
--        userForced(5),
--        activeUnitFailed(6),
--        activeUnitRemoved(7)
--        }
    ACCESS read-only
    STATUS mandatory
    DESCRIPTION
        "The reason for the last switch of activity."
    ::= { cRFStatus 8 }

cRFStatusFailoverTime OBJECT-TYPE
    SYNTAX TimeStamp
--    Rsyntax TimeTicks
    ACCESS read-only
    STATUS mandatory
    DESCRIPTION
        "The value of sysUpTime when the primary redundant unit took over 
        as active. The value of this object will be 0 till the first 
        switchover."
    ::= { cRFStatus 9 }

cRFStatusPeerStandByEntryTime OBJECT-TYPE
    SYNTAX TimeStamp
--    Rsyntax TimeTicks
    ACCESS read-only
    STATUS mandatory
    DESCRIPTION
        "The value of sysUpTime when the peer redundant unit entered the
        standbyHot state. The value will be 0 on system initialization."
    ::= { cRFStatus 10 }

cRFStatusRFModeCapsTable OBJECT-TYPE
    SYNTAX SEQUENCE OF CRFStatusRFModeCapsEntry
    ACCESS not-accessible
    STATUS mandatory
    DESCRIPTION
        "This table containing a list of redundancy modes that can be 
        supported on the device."
    ::= { cRFStatus 11 }

cRFStatusRFModeCapsEntry OBJECT-TYPE
    SYNTAX CRFStatusRFModeCapsEntry
    ACCESS not-accessible
    STATUS mandatory
    DESCRIPTION
        "An entry containing the device implementation specific 
        terminology associated with the redundancy mode that can be
        supported on the device."
    INDEX { cRFStatusRFModeCapsMode }
    ::= { cRFStatusRFModeCapsTable 1 }

CRFStatusRFModeCapsEntry ::= SEQUENCE {
    cRFStatusRFModeCapsMode RFMode,
    cRFStatusRFModeCapsModeDescr SnmpAdminString
    }

cRFStatusRFModeCapsMode OBJECT-TYPE
    SYNTAX RFMode
--    Rsyntax INTEGER {
--        nonRedundant(1),
--        staticLoadShareNonRedundant(2),
--        dynamicLoadShareNonRedundant(3),
--        staticLoadShareRedundant(4),
--        dynamicLoadShareRedundant(5),
--        coldStandbyRedundant(6),
--        warmStandbyRedundant(7),
--        hotStandbyRedundant(8)
--        }
    ACCESS not-accessible
    STATUS mandatory
    DESCRIPTION
        "The redundancy mode that can be supported on the device."
    ::= { cRFStatusRFModeCapsEntry 1 }

cRFStatusRFModeCapsModeDescr OBJECT-TYPE
    SYNTAX SnmpAdminString
--    Rsyntax OCTET STRING(SIZE(0..255))
    ACCESS read-only
    STATUS mandatory
    DESCRIPTION
        "The description of the device implementation specific
        terminology associated with its supported redundancy mode."
    ::= { cRFStatusRFModeCapsEntry 2 }

cRFCfgSplitMode OBJECT-TYPE
    SYNTAX TruthValue
--    Rsyntax INTEGER {
--        true(1),
--        false(2)
--        }
    ACCESS read-write
    STATUS deprecated
    DESCRIPTION
        "Indicates whether redundant units may communicate
         synchronization messages with each other. If communication is
         not permitted, this object is set to true. If communication is
         permitted, this object is set to false.
        
         In split mode (true), the active unit will not communicate
         with the standby unit. The standby unit progression will not
         occur. When split mode is disabled (false), the standby unit
         is reset to recover.
        
         Split mode (true) is useful for maintenance operations."
    ::= { cRFCfg 1 }

cRFCfgKeepaliveThresh OBJECT-TYPE
    SYNTAX Gauge
    ACCESS read-write
    STATUS mandatory
    DESCRIPTION
        "On platforms that support keep-alives, the keep-alive
        threshold value designates the number of lost keep-alives
        tolerated before a failure condition is declared.  If this
        occurs, a SWACT notification is sent.
        
        On platforms that do not support keep-alives, this object has
        no purpose or effect."
    ::= { cRFCfg 2 }

cRFCfgKeepaliveThreshMin OBJECT-TYPE
    SYNTAX Gauge
    ACCESS read-only
    STATUS mandatory
    DESCRIPTION
        "The minimum acceptable value for the cRFCfgKeepaliveThresh
        object."
    ::= { cRFCfg 3 }

cRFCfgKeepaliveThreshMax OBJECT-TYPE
    SYNTAX Gauge
    ACCESS read-only
    STATUS mandatory
    DESCRIPTION
        "The maximum acceptable value for the cRFCfgKeepaliveThresh
        object."
    ::= { cRFCfg 4 }

cRFCfgKeepaliveTimer OBJECT-TYPE
    SYNTAX Gauge
--  Units
--    milliseconds
    ACCESS read-write
    STATUS mandatory
    DESCRIPTION
        "On platforms that support keep-alives, the keep-alive timer
        value is used to guard against lost keep-alives.  The RF
        subsystem expects to receive a keep-alive within this period.
        If a keep-alive is not received within this time period, a
        SWACT notification is sent.
        
        On platforms that do not support keep-alives, this object has
        no purpose or effect."
    ::= { cRFCfg 5 }

cRFCfgKeepaliveTimerMin OBJECT-TYPE
    SYNTAX Gauge
--  Units
--    milliseconds
    ACCESS read-only
    STATUS mandatory
    DESCRIPTION
        "The minimum acceptable value for the cRFCfgKeepaliveTimer
        object."
    ::= { cRFCfg 6 }

cRFCfgKeepaliveTimerMax OBJECT-TYPE
    SYNTAX Gauge
--  Units
--    milliseconds
    ACCESS read-only
    STATUS mandatory
    DESCRIPTION
        "The maximum acceptable value for the cRFCfgKeepaliveTimer
        object."
    ::= { cRFCfg 7 }

cRFCfgNotifTimer OBJECT-TYPE
    SYNTAX Gauge
--  Units
--    milliseconds
    ACCESS read-write
    STATUS mandatory
    DESCRIPTION
        "Note that the term 'notification' here refers to an RF
        notification and not an SNMP notification.
        
        As the standby unit progresses to the 'standbyHot' state,
        asynchronous messages are sent from the active unit to the
        standby unit which must then be acknowledged by the standby
        unit. If the active unit receives the acknowledgement during
        the time period specified by this object, progression proceeds
        as normal. If the timer expires and an acknowledgement was not
        received by the active unit, a switch of activity occurs."
    ::= { cRFCfg 8 }

cRFCfgNotifTimerMin OBJECT-TYPE
    SYNTAX Gauge
--  Units
--    milliseconds
    ACCESS read-only
    STATUS mandatory
    DESCRIPTION
        "The minimum acceptable value for the cRFCfgNotifTimer
        object."
    ::= { cRFCfg 9 }

cRFCfgNotifTimerMax OBJECT-TYPE
    SYNTAX Gauge
--  Units
--    milliseconds
    ACCESS read-only
    STATUS mandatory
    DESCRIPTION
        "The maximum acceptable value for the cRFCfgNotifTimer
        object."
    ::= { cRFCfg 10 }

cRFCfgAdminAction OBJECT-TYPE
    SYNTAX RFAction
--    Rsyntax INTEGER {
--        ?? enum value of zero may cause problems
--        noAction(0),
--        reloadPeer(1),
--        reloadShelf(2),
--        switchActivity(3),
--        forceSwitchActivity(4)
--        }
    ACCESS read-write
    STATUS mandatory
    DESCRIPTION
        "This variable is set to invoke RF subsystem action commands.
        The commands are useful for maintenance and software upgrade
        activities."
    ::= { cRFCfg 11 }

cRFCfgNotifsEnabled OBJECT-TYPE
    SYNTAX TruthValue
--    Rsyntax INTEGER {
--        true(1),
--        false(2)
--        }
    ACCESS read-write
    STATUS mandatory
    DESCRIPTION
        "Allows enabling/disabling of RF subsystem notifications."
    DEFVAL { false }
    ::= { cRFCfg 12 }

cRFCfgMaintenanceMode OBJECT-TYPE
    SYNTAX TruthValue
--    Rsyntax INTEGER {
--        true(1),
--        false(2)
--        }
    ACCESS read-write
    STATUS mandatory
    DESCRIPTION
        "Indicates whether redundant units may communicate
        synchronization messages with each other. If communication is
        not permitted, this object is set to 'true'. If communication
        is permitted, this object is set to 'false'.
        
        If the value of this object is 'true', the redundant system is
        considered to be in a maintenance mode of operation.  If the
        value of this object is 'false', the redundant system is
        considered to be in a normal (non-maintenance) mode of
        operation.
        
        In maintenance mode (true), the active unit will not
        communicate with the standby unit. The standby unit
        progression will not occur. When maintenance mode is disabled
        (false), the standby unit is reset to recover.
        
        Maintenance mode (true) is useful for maintenance-type
        operations."
    ::= { cRFCfg 13 }

cRFCfgRedundancyMode OBJECT-TYPE
    SYNTAX RFMode
--    Rsyntax INTEGER {
--        nonRedundant(1),
--        staticLoadShareNonRedundant(2),
--        dynamicLoadShareNonRedundant(3),
--        staticLoadShareRedundant(4),
--        dynamicLoadShareRedundant(5),
--        coldStandbyRedundant(6),
--        warmStandbyRedundant(7),
--        hotStandbyRedundant(8)
--        }
    ACCESS read-write
    STATUS mandatory
    DESCRIPTION
        "Indicates the redundancy mode configured on the device."
    ::= { cRFCfg 14 }

cRFCfgRedundancyModeDescr OBJECT-TYPE
    SYNTAX SnmpAdminString
--    Rsyntax OCTET STRING(SIZE(0..255))
    ACCESS read-only
    STATUS mandatory
    DESCRIPTION
        "Further clarifies or describes the redundancy mode indicated
        by cRFCfgRedundancyMode.  Implementation-specific terminology
        associated with the current redundancy mode may be presented
        here."
    ::= { cRFCfg 15 }

cRFCfgRedundancyOperMode OBJECT-TYPE
    SYNTAX RFMode
--    Rsyntax INTEGER {
--        nonRedundant(1),
--        staticLoadShareNonRedundant(2),
--        dynamicLoadShareNonRedundant(3),
--        staticLoadShareRedundant(4),
--        dynamicLoadShareRedundant(5),
--        coldStandbyRedundant(6),
--        warmStandbyRedundant(7),
--        hotStandbyRedundant(8)
--        }
    ACCESS read-only
    STATUS mandatory
    DESCRIPTION
        "Indicate the operational redundancy mode of the device."
    ::= { cRFCfg 16 }

cRFHistoryTableMaxLength OBJECT-TYPE
    SYNTAX Gauge(0..50)
    ACCESS read-write
    STATUS mandatory
    DESCRIPTION
        "Maximum number of entries permissible in the history 
        table. A value of 0 will result in no history being
        maintained."
    DEFVAL { 10 }
    ::= { cRFHistory 1 }

cRFHistorySwitchOverTable OBJECT-TYPE
    SYNTAX SEQUENCE OF CRFHistorySwitchOverEntry
    ACCESS not-accessible
    STATUS mandatory
    DESCRIPTION
        "A table that tracks the history of all switchovers that 
        have occurred since system initialization. The maximum
        number of entries permissible in this table is defined by
        cRFHistoryTableMaxLength. When the number of entries in
        the table reaches the maximum limit, the next entry
        would replace the oldest existing entry in the table."
    ::= { cRFHistory 2 }

cRFHistorySwitchOverEntry OBJECT-TYPE
    SYNTAX CRFHistorySwitchOverEntry
    ACCESS not-accessible
    STATUS mandatory
    DESCRIPTION
        "The entries in this table contain the switchover 
        information. Each entry in the table is indexed by 
        cRFHistorySwitchOverIndex. The index wraps around to 1 
        after reaching the maximum value."
    INDEX { cRFHistorySwitchOverIndex }
    ::= { cRFHistorySwitchOverTable 1 }

CRFHistorySwitchOverEntry ::= SEQUENCE {
    cRFHistorySwitchOverIndex Gauge,
    cRFHistoryPrevActiveUnitId RFUnitIdentifier,
    cRFHistoryCurrActiveUnitId RFUnitIdentifier,
    cRFHistorySwitchOverReason RFSwactReasonType,
    cRFHistorySwactTime DateAndTime
    }

cRFHistorySwitchOverIndex OBJECT-TYPE
    SYNTAX Gauge(1..4294967295)
    ACCESS not-accessible
    STATUS mandatory
    DESCRIPTION
        "A monotonically increasing integer for the purpose of
        indexing history table. After reaching maximum value,
        it wraps around to 1."
    ::= { cRFHistorySwitchOverEntry 1 }

cRFHistoryPrevActiveUnitId OBJECT-TYPE
    SYNTAX RFUnitIdentifier
--    Rsyntax INTEGER(0..2147483647)
    ACCESS read-only
    STATUS mandatory
    DESCRIPTION
        "Indicates the primary redundant unit that went down."
    ::= { cRFHistorySwitchOverEntry 2 }

cRFHistoryCurrActiveUnitId OBJECT-TYPE
    SYNTAX RFUnitIdentifier
--    Rsyntax INTEGER(0..2147483647)
    ACCESS read-only
    STATUS mandatory
    DESCRIPTION
        "Indicates the secondary redundant unit that took 
        over as active."
    ::= { cRFHistorySwitchOverEntry 3 }

cRFHistorySwitchOverReason OBJECT-TYPE
    SYNTAX RFSwactReasonType
--    Rsyntax INTEGER {
--        unsupported(1),
--        none(2),
--        notKnown(3),
--        userInitiated(4),
--        userForced(5),
--        activeUnitFailed(6),
--        activeUnitRemoved(7)
--        }
    ACCESS read-only
    STATUS mandatory
    DESCRIPTION
        "Indicates the reason for the switchover."
    ::= { cRFHistorySwitchOverEntry 4 }

cRFHistorySwactTime OBJECT-TYPE
    SYNTAX DateAndTime
--    Rsyntax OCTET STRING(SIZE(8|11))
    ACCESS read-only
    STATUS mandatory
    DESCRIPTION
        "Indicates the Date & Time when switchover occured."
    ::= { cRFHistorySwitchOverEntry 5 }

cRFHistoryColdStarts OBJECT-TYPE
    SYNTAX Counter
    ACCESS read-only
    STATUS mandatory
    DESCRIPTION
        "Indicates the number of system cold starts. This includes
        the number of system cold starts due to switchover failure
        and the number of manual restarts."
    ::= { cRFHistory 3 }

cRFHistoryStandByAvailTime OBJECT-TYPE
    SYNTAX TimeInterval
--    Rsyntax INTEGER(0..2147483647)
    ACCESS read-only
    STATUS mandatory
    DESCRIPTION
        "Indicates the cumulative time that a standby redundant  
        unit has been available since last system initialization."
    ::= { cRFHistory 4 }

ciscoRFSwactNotif TRAP-TYPE
-- Reverse mappable trap
    ENTERPRISE ciscoRFMIBNotificationsPrefix
    VARIABLES {
        cRFStatusUnitId, sysUpTime, cRFStatusLastSwactReasonCode }
--  Status
--    mandatory
    DESCRIPTION
        "A SWACT notification is sent by the newly active redundant
        unit whenever a switch of activity occurs. In the case where a
        SWACT event may be indistinguishable from a reset event, a
        network management station should use this notification to
        differentiate the activity.
        
        sysUpTime is the same sysUpTime defined in the RFC-1213 MIB."
    ::= 1

ciscoRFProgressionNotif TRAP-TYPE
-- Reverse mappable trap
    ENTERPRISE ciscoRFMIBNotificationsPrefix
    VARIABLES {
        cRFStatusUnitId, cRFStatusUnitState, cRFStatusPeerUnitId, 
        cRFStatusPeerUnitState }
--  Status
--    mandatory
    DESCRIPTION
        "A progression notification is sent by the active redundant
        unit whenever its RF state changes or the RF state of the peer
        unit changes.
        
        To avoid a flurry of notifications for all state transitions,
        notifications will only be sent for transitions to the
        following RF states:
            standbyCold
            standbyHot
            active
            activeExtraload"
    ::= 2

ciscoRFStatusGroup OBJECT IDENTIFIER ::= { ciscoRFMIBGroups 1 }
-- OBJECT-GROUP
--  Status
--    deprecated
--  Descr
--    The collection of global RF status objects.
--  objects
--    cRFStatusUnitId, cRFStatusUnitState, cRFStatusPeerUnitId, 
--    cRFStatusPeerUnitState, cRFStatusPrimaryMode, 
--    cRFStatusDuplexMode, cRFStatusManualSwactInhibit, 
--    cRFStatusLastSwactReasonCode

ciscoRFConfigGroup OBJECT IDENTIFIER ::= { ciscoRFMIBGroups 2 }
-- OBJECT-GROUP
--  Status
--    deprecated
--  Descr
--    The collection of RF configuration objects.
--  objects
--    cRFCfgSplitMode, cRFCfgKeepaliveThresh, 
--    cRFCfgKeepaliveThreshMin, cRFCfgKeepaliveThreshMax, 
--    cRFCfgKeepaliveTimer, cRFCfgKeepaliveTimerMin, 
--    cRFCfgKeepaliveTimerMax, cRFCfgNotifTimer, 
--    cRFCfgNotifTimerMin, cRFCfgNotifTimerMax, cRFCfgAdminAction, 
--    cRFCfgNotifsEnabled, cRFCfgRedundancyMode, 
--    cRFCfgRedundancyModeDescr

ciscoRFConfigGroupRev1 OBJECT IDENTIFIER ::= { ciscoRFMIBGroups 4 }
-- OBJECT-GROUP
--  Status
--    mandatory
--  Descr
--    The collection of RF configuration objects.
--  objects
--    cRFCfgKeepaliveThresh, cRFCfgKeepaliveThreshMin, 
--    cRFCfgKeepaliveThreshMax, cRFCfgKeepaliveTimer, 
--    cRFCfgKeepaliveTimerMin, cRFCfgKeepaliveTimerMax, 
--    cRFCfgNotifTimer, cRFCfgNotifTimerMin, cRFCfgNotifTimerMax, 
--    cRFCfgAdminAction, cRFCfgNotifsEnabled, cRFCfgMaintenanceMode, 
--    cRFCfgRedundancyMode, cRFCfgRedundancyModeDescr

ciscoRFStatusGroupRev1 OBJECT IDENTIFIER ::= { ciscoRFMIBGroups 5 }
-- OBJECT-GROUP
--  Status
--    mandatory
--  Descr
--    The collection of global RF status objects.
--  objects
--    cRFStatusUnitId, cRFStatusUnitState, cRFStatusPeerUnitId, 
--    cRFStatusPeerUnitState, cRFStatusPrimaryMode, 
--    cRFStatusDuplexMode, cRFStatusManualSwactInhibit, 
--    cRFStatusLastSwactReasonCode, cRFStatusFailoverTime, 
--    cRFStatusPeerStandByEntryTime

ciscoRFHistoryGroup OBJECT IDENTIFIER ::= { ciscoRFMIBGroups 6 }
-- OBJECT-GROUP
--  Status
--    mandatory
--  Descr
--    The collection of RF History objects.
--  objects
--    cRFHistoryPrevActiveUnitId, cRFHistoryCurrActiveUnitId, 
--    cRFHistorySwitchOverReason, cRFHistorySwactTime, 
--    cRFHistoryColdStarts, cRFHistoryStandByAvailTime, 
--    cRFHistoryTableMaxLength

ciscoRFConfigRFOperModeGroup OBJECT IDENTIFIER ::= { ciscoRFMIBGroups 7 }
-- OBJECT-GROUP
--  Status
--    mandatory
--  Descr
--    An optional group with a collection of objects providing 
--    the information of the operational redundancy mode on the
--    device.
--  objects
--    cRFCfgRedundancyOperMode

ciscoRFStatusRFModeCapsGroup OBJECT IDENTIFIER ::= { ciscoRFMIBGroups 8 }
-- OBJECT-GROUP
--  Status
--    mandatory
--  Descr
--    An optional group with a collection of objects 
--    providing the information of redundancy mode capability 
--    on the device.
--  objects
--    cRFStatusRFModeCapsModeDescr

ciscoRFNotifGroup OBJECT IDENTIFIER ::= { ciscoRFMIBGroups 3 }
-- NOTIFICATION-GROUP
--  Status
--    mandatory
--  Descr
--    The collection of notifications used to indicate RF state
--    information.
--  notifications
--    ciscoRFSwactNotif, ciscoRFProgressionNotif

ciscoRFMIBCompliance OBJECT IDENTIFIER ::= { ciscoRFMIBCompliances 1 }
-- MODULE-COMPLIANCE
--  Status
--    deprecated
--  Descr
--    The compliance statement for entities which implement the
--    Cisco RF MIB.
--  Module
--    >>current<<
--   MandGroup
--    ciscoRFStatusGroup
--   MandGroup
--    ciscoRFConfigGroup
--   MandGroup
--    ciscoRFNotifGroup

ciscoRFMIBComplianceRev1 OBJECT IDENTIFIER ::= { ciscoRFMIBCompliances 2 }
-- MODULE-COMPLIANCE
--  Status
--    deprecated
--  Descr
--    The compliance statement for entities which implement the
--    Cisco RF MIB
--  Module
--    >>current<<
--   MandGroup
--    ciscoRFStatusGroup
--   MandGroup
--    ciscoRFConfigGroupRev1
--   MandGroup
--    ciscoRFNotifGroup

ciscoRFMIBComplianceRev2 OBJECT IDENTIFIER ::= { ciscoRFMIBCompliances 3 }
-- MODULE-COMPLIANCE
--  Status
--    mandatory
--  Descr
--    The compliance statement for entities which implement the
--    Cisco RF MIB.
--  Module
--    >>current<<
--   MandGroup
--    ciscoRFStatusGroupRev1
--   MandGroup
--    ciscoRFConfigGroupRev1
--   MandGroup
--    ciscoRFNotifGroup
--   MandGroup
--    ciscoRFHistoryGroup


END
