-- MIB file created 11-Aug-2004 19:42:03, by
--   SMICng version 2.2.11-beta(PRO)(Solaris), January 20, 2001. Enterprise key cisco.com

CISCO-ITP-XUA-MIB DEFINITIONS ::= BEGIN

-- From file: "CISCO-ITP-XUA-MIB.my"
-- Compile options "4 7 F H N W 03 06 0B 0G 0N 0T"

IMPORTS
    InetAddressType, InetAddress, InetPortNumber
            FROM INET-ADDRESS-MIB
    CItpTcNetworkName, CItpTcPointCode, CItpTcSubSystemNumber, 
    CItpTcServiceIndicator, CItpTcXuaName, CItpTcQos
            FROM CISCO-ITP-TC-MIB
    cItpSpCLLICode
            FROM CISCO-ITP-SP-MIB
    RowStatus, TruthValue
            FROM SNMPv2-TC-v1
    ciscoMgmt
            FROM CISCO-SMI
    Counter, Gauge, TimeTicks
            FROM RFC1155-SMI
    OBJECT-TYPE
            FROM RFC-1212
    TRAP-TYPE
            FROM RFC-1215;

ciscoItpXuaMIB OBJECT IDENTIFIER ::= { ciscoMgmt 253 }
-- MODULE-IDENTITY
--  LastUpdated
--    200406140000Z
--  OrgName
--    Cisco Systems, Inc.
--  ContactInfo
--           Cisco Systems, Inc
--            Customer Service
--    
--    Postal: 170 W. Tasman Drive
--            San Jose, CA  95134
--            USA
--    
--       Tel: +1 800 553-NETS
--    
--    E-mail: cs-ss7@cisco.com
--  Descr
--    The MIB for MTP3 User Adaptation (M3UA) and SCCP User
--     Adaptation (SUA) for Cisco's IP Transfer Point (ITP)
--     implementation.
--    
--     The Cisco IP Transfer Point (ITP) is a hardware and
--     software solution that transports SS7 traffic using
--     IP. Each ITP node provides function similar to SS7
--     signaling point.   
--    
--     The relevant ITU documents describing this technology
--     is the ITU Q series, including ITU Q.700: Introduction
--     to CCITT Signaling System No. 7 and ITU Q.701
--     Functional description of the message transfer part
--     (MTP) of Signaling System No. 7.
--    
--     The relevent information about M3UA and SUA is
--     available at the IETF:
--     http://www.ietf.org/html.charters/sigtran-charter.html
--    
--     This MIB consists of the following tables:
--       M3UA/SUA (XUA) Instance Table
--       M3UA/SUA (XUA) Instance Local IP Table
--       Signaling Gateway Mate Table
--       Signaling Gateway Mate Remote IP Table
--       Application Server Process (ASP) Table
--       Application Server Process (ASP) Remote IP Table
--       Application Server Process (ASP) Statistics Table
--       Application Server (AS) Table
--       ASP-AS Table
--       ASRoute Table
--       ASRouteAs Table
--    
--     Abbreviations:
--     AS    - Application Server
--     ASP   - Application Server Process
--     ASPAC - ASP ACtive message
--     ASPDN - ASP Down message
--     ASPIA - ASP InActive message
--     ASPUP - ASP UP message
--     CIC   - Circuit Identifier Code for ISUP
--     CLLI  - Common Language Location Codes
--     DPC   - Destination Point Code
--     DAUD  - Destination AUDit
--     DAVA  - Destination AVAilable
--     DUNA  - Destination UNAvailable
--     DUPU  - Destination User Part Unavailable
--     ERR   - Error message
--     GTT   - Global Title Translation
--     HLR   - Home Location Registry
--     ISDN  - Integrated Services Digital Network
--     ISUP  - ISDN User Part
--     M3UA  - MTP3 User Adaptation
--     MGC   - Media Gateway Controller used in VoIP
--     MTP   - Message Transport Protocol
--     MTP2  - Layer 2 of Message Transport Protocol
--     MTP3  - Layer 3 of Message Transport Protocol
--     NMS   - Network Management System
--     OPC   - Originating Point Code
--     PC    - Point Code
--     QOS   - Quality Of Service
--     SCCP  - Signaling Connection Control Part
--     SCP   - Service Control Point (SS7)
--     SCON  - Signaling link CONgestion
--     SCON0 - Signaling link CONgestion level 0 (no congestion)
--     SCON1 - Signaling link CONgestion level 1
--     SCON2 - Signaling link CONgestion level 2
--     SCON3 - Signaling link CONgestion level 3
--     SG    - Signaling Gateway
--     SGM   - Signaling Gateway Mate
--     SGMP  - Signaling Gateway Mated Protocol
--     SCTP  - Stream Transmission Protocol(RFC 2960)
--     SI    - Signaling Indicator
--     SIO   - Service Indicator Octet (SS7)
--     SNMM  - Signaling Network Management Message
--     SSN   - Subsystem Number for SCCP
--     SUA   - SCCP User Adaptation
--     TUP   - Telephone User Part
--     TT    - Title Translation
--     VIP   - Versatile Interface Processor
--     XUA   - M3UA, SUA or SGMP
--    
--     Brief description:
--    
--     The Signaling Gateway (SG) on the ITP receives the SS7
--     packets, converts them to M3UA/SUA packets and routes
--     them to the ASPs over SCTP/IP association. The routing
--     of the packet depends on the routing information
--     present in the packet and the routing keys configured
--     as part of the ASes. 
--    
--     There can be one or more instances of M3UA/SUA at the
--     SG. These instances are identified by a unique port
--     number. Each of these instances can have one or more
--     IP addresses which form 'local' end of the multi-homing
--     SCTP association.
--    
--     The Application Server Process (ASP) is a remote entity
--     which has its own port number and one or more IP
--     addresses to form the 'remote' end of the multi-homing
--     SCTP association. Examples of ASPs are MGCs, IP SCPs or
--     IP HLRs.
--    
--     Application Server (AS), as described in section
--     '1.2 Terminology' of M3UA/SUA draft, is a logical
--     entity serving a specific Routing Key. An example of
--     an AS is a virtual switch element handling all call
--     processing for a unique range of PSTN trunks,
--     identified by an SS7 SIO/DPC/OPC/CIC_range. Another
--     example is a virtual database element, handling all
--     HLR transactions for a particular SS7 DPC/OPC/SCCP_SSN
--     combination. The AS contains a set of one or more
--     unique ASPs of which one or more is normally actively
--     processing traffic. Note that there is a 1:1
--     relationship between an AS and a Routing Key.
--    
--     An ASP can serve one or more ASes and an AS can have
--     one or more ASPs. An ASP while serving an AS can be
--     active, inactive or down. When one or more ASPs for
--     an AS is active, the AS is active. When all ASPs for
--     an AS are inactive, the AS is inactive. The state of
--     the AS is maintained in one object, whereas, the state
--     of an ASP is maintained for each AS that it serves in
--     ASP-AS table.
--    
--     The SGs are always deployed in mated pairs to provide
--     high availability and redundancy. The SG mates exchange
--     the state of ASes. When an AS is down on one SG, it can
--     route the SS7 message to its mate which can properly
--     route that SS7 message.
--  RevDate
--    200406140000Z
--  RevDescr
--    Added the following textual convention:
--        CItpXuaRouteState
--     Added the following table:
--        cItpXuaASRouteTable
--        cItpXuaASRouteAsTable
--     Added the following objects:
--        cItpXuaAspAsWeight,
--        cItpXuaAsNetworkAppear,
--        cItpXuaAsCongLevel.
--  RevDate
--    200308270000Z
--  RevDescr
--    Deprecated the following object(s):
--        cItpXuaAspAssocId
--     Added the following objects:
--        cItpXuaInstOffload
--        cItpXuaInstOffloadSlot
--        cItpXuaAsNetworkName
--        cItpXuaAspAssocIdU32
--     Modified the description of cItpXuaAsRkParameters
--     to include TUP Service Indicator.
--  RevDate
--    200302190000Z
--  RevDescr
--    Added the following sub-table:
--        cItpXuaSgmRemoteIpTable
--     Added the following objects:
--        cItpXuaSgmCongLevel
--        cItpXuaAspCongLevel
--     Added the following notifications:
--        ciscoItpXuaAspCongChange
--        ciscoItpXuaSgmCongChange.
--     Modified the following Textual Conventions:
--        CItpXuaAsState
--        CItpXuaAspState.
--     Added 'undefined(5)' to CItpXuaTrafMode textual
--     convention.
--  RevDate
--    200204150000Z
--  RevDescr
--    Initial version of this MIB module.

ciscoItpXuaMIBNotifs OBJECT IDENTIFIER ::= { ciscoItpXuaMIB 0 }
ciscoItpXuaMIBObjects OBJECT IDENTIFIER ::= { ciscoItpXuaMIB 1 }
ciscoItpXuaConformance OBJECT IDENTIFIER ::= { ciscoItpXuaMIB 2 }
cItpXuaScalars  OBJECT IDENTIFIER ::= { ciscoItpXuaMIBObjects 1 }
cItpXuaInst     OBJECT IDENTIFIER ::= { ciscoItpXuaMIBObjects 2 }
cItpXuaInstLocalIp OBJECT IDENTIFIER ::= { ciscoItpXuaMIBObjects 3 }
cItpXuaSgm      OBJECT IDENTIFIER ::= { ciscoItpXuaMIBObjects 4 }
cItpXuaAsp      OBJECT IDENTIFIER ::= { ciscoItpXuaMIBObjects 5 }
cItpXuaAspRemoteIp OBJECT IDENTIFIER ::= { ciscoItpXuaMIBObjects 6 }
cItpXuaAspStats OBJECT IDENTIFIER ::= { ciscoItpXuaMIBObjects 7 }
cItpXuaAs       OBJECT IDENTIFIER ::= { ciscoItpXuaMIBObjects 8 }
cItpXuaAspAs    OBJECT IDENTIFIER ::= { ciscoItpXuaMIBObjects 9 }
cItpXuaMIBNotifObjects OBJECT IDENTIFIER ::= { ciscoItpXuaMIBObjects 10 }
cItpXuaSgmRemoteIp OBJECT IDENTIFIER ::= { ciscoItpXuaMIBObjects 11 }
cItpXuaASRoute  OBJECT IDENTIFIER ::= { ciscoItpXuaMIBObjects 12 }
cItpXuaASRouteAs OBJECT IDENTIFIER ::= { ciscoItpXuaMIBObjects 13 }
ciscoItpXuaMIBCompliances OBJECT IDENTIFIER ::= { ciscoItpXuaConformance 1 }
ciscoItpXuaMIBGroups OBJECT IDENTIFIER ::= { ciscoItpXuaConformance 2 }

CItpXuaProtocol ::= INTEGER {
        m3ua(1),
        sua(2),
        sgmp(3)
        }
-- TEXTUAL-CONVENTION
--  Status
--    mandatory
--  Descr
--    The possible protocol types supported by AS or ASP
--    'm3ua'  : The protocol is M3UA.
--    'sua'   : The protocol is SUA.
--    'sgmp'  : The protocol is Signaling Gateway Mated
--              Protocol (SGMP).

CItpXuaTrafMode ::= INTEGER {
        overRide(1),
        loadBind(2),
        loadRndRobin(3),
        broadcast(4),
        undefined(5)
        }
-- TEXTUAL-CONVENTION
--  Status
--    mandatory
--  Descr
--    The possible traffic modes supported by AS
--    'overRide'  : In override mode, one ASP takes over
--       all traffic for the AS, possibly overriding any
--       currently active ASP in the AS.
--    
--    'broadcast' : In broadcast mode, every active ASP
--       receives the same message.
--    
--    'loadBind'  : In loadshare bindings mode, an ASP
--       shares in the traffic distribution with any other
--       currently active ASPs based on ASP bindings.
--    
--    'loadRndRobin' : In loadshare round-robin mode, an
--       ASP shares in the traffic distribution with any
--       other currently active ASPs using a roundrobin
--       algorithm.
--    
--    'undefined' : The traffic mode is not defined.
--       The first ASP that becomes active will define
--       the traffic mode.
--  Refer
--    3.7.1 ASP Active in RFC 3332 and 3.9.11 Traffic Mode
--     Type in SUA draft.

CItpXuaAsState ::= INTEGER {
        down(1),
        inactive(2),
        active(3),
        pending(4),
        undefined(5)
        }
-- TEXTUAL-CONVENTION
--  Status
--    mandatory
--  Descr
--    The possible AS states
--    'down' : The AS is unavailable. This state implies 
--             that all ASPs that are serving this AS are
--             in the 'down' state. Initially the AS will
--             be in this state.
--    
--    'inactive' : The AS is available but no application 
--                 traffic is active (i.e., one or more
--                 ASPs are in the inactive state, but none
--                 in the active state).
--    
--    'active' : The AS is available and application traffic 
--               is active.  This state implies that at least
--               one ASP is in the active state.
--    
--    'pending' : An active ASP has transitioned to inactive
--                or down and it was the last remaining
--                active ASP serving the AS. Depending on
--                the recovery timer and an ASP becoming
--                active this AS moves to active, inactive,
--                or down state.
--    
--    'undefined' : The AS state is not known or undefined.
--  Refer
--    4.3.2 AS States in M3UA/SUA draft.

CItpXuaAspState ::= INTEGER {
        down(1),
        inactive(2),
        active(3),
        undefined(4)
        }
-- TEXTUAL-CONVENTION
--  Status
--    mandatory
--  Descr
--    The possible ASP states
--    'down' : The remote peer at the ASP is unavailable
--             and/or the related SCTP association is down.
--             Initially all ASPs will be in this state.
--    
--    'inactive' : The remote peer at the ASP is available
--                 (and the related SCTP association is up)
--                 but application traffic is stopped. In 
--                 this state the ASP should not be sent any
--                 DATA or SNMM messages for the AS for
--                 which the ASP is inactive.
--    
--    'active' : The remote peer at the ASP is available and 
--               application traffic is active.
--    
--    'undefined' : The state of the remote peer at the ASP
--                  is not known or undefined.
--  Refer
--    4.3.1 ASP States in M3UA/SUA draft.

CItpXuaRouteState ::= INTEGER {
        unknown(1),
        avail(2),
        restr(3),
        unavail(4),
        deleted(5)
        }
-- TEXTUAL-CONVENTION
--  Status
--    mandatory
--  Descr
--    The possible ASRoute states
--    'unknown' : The state of the ASRoute is unknown.
--    
--    'avail' : The ASRoute is available for routing data.
--    
--    'restr' : The ASRoute is restricted due to congestion.
--    
--    'unavail' : The ASRoute is not available for data.
--    
--    'deleted' : The ASRoute is deleted.

cItpXuaInstConfigLastChanged OBJECT-TYPE
    SYNTAX TimeTicks
    ACCESS read-only
    STATUS mandatory
    DESCRIPTION
        "The value of system timestamp at the time of the last
         creation or deletion of an entry in the
         cItpXuaInstTable. This value can be used to prevent
         unnecessary walks of the XUA Instance Table."
    ::= { cItpXuaScalars 1 }

cItpXuaSgmConfigLastChanged OBJECT-TYPE
    SYNTAX TimeTicks
    ACCESS read-only
    STATUS mandatory
    DESCRIPTION
        "The value of system timestamp at the time of the last
         creation or deletion of an entry in the
         cItpXuaSgmTable. This value can be used to prevent
         unnecessary walks of the XUA SG Mate Table."
    ::= { cItpXuaScalars 2 }

cItpXuaAspConfigLastChanged OBJECT-TYPE
    SYNTAX TimeTicks
    ACCESS read-only
    STATUS mandatory
    DESCRIPTION
        "The value of system timestamp at the time of the last
         creation or deletion of an entry in the
         cItpXuaAspTable. This value can be used to prevent
         unnecessary walks of the XUA ASP Table."
    ::= { cItpXuaScalars 3 }

cItpXuaAsConfigLastChanged OBJECT-TYPE
    SYNTAX TimeTicks
    ACCESS read-only
    STATUS mandatory
    DESCRIPTION
        "The value of system timestamp at the time of the last
         creation or deletion of an entry in the
         cItpXuaAsTable. This value can be used to prevent
         unnecessary walks of the XUA AS Table."
    ::= { cItpXuaScalars 4 }

cItpXuaStateChangeNotifEnabled OBJECT-TYPE
    SYNTAX TruthValue
--    Rsyntax INTEGER {
--        true(1),
--        false(2)
--        }
    ACCESS read-write
    STATUS mandatory
    DESCRIPTION
        "The State notification truth value.
        'true'  Indicates that the notification generation
                is enabled for ASP state changes, AS state
                changes, SG Mate state changes, ASP Congestion
                Level change and SG Mate Congestion Level
                change.
        'false' Indicates that the notification generation
                is disabled for ASP state change, AS state,
                SG Mate state change, ASP Congestion
                Level change and SG Mate Congestion Level
                change."
    DEFVAL { false }
    ::= { cItpXuaScalars 5 }

cItpXuaInstTable OBJECT-TYPE
    SYNTAX SEQUENCE OF CItpXuaInstTableEntry
    ACCESS not-accessible
    STATUS mandatory
    DESCRIPTION
        "A table of M3UA/SUA/SGMP instances.
        
         There can be multiple M3UA or SUA instances on a
         given Signaling Gateway. Each instance is uniquely
         identified by the port number. The local port number
         of the ASP (cItpXuaAspLocalPort) matches with the
         port number of the instance (cItpXuaInstPort).
        
         Also for a given instance, there can be multiple
         local IP addresses which are used for the
         multi-homing feature of the SCTP associations.
        
         There can only be one instance of SGMP.
        
         M3UA or SUA instances can be offloaded to a VIP
         on a 7500 platform. When an instance is offloaded,
         all ASPs that belong to that instance are also
         offloaded.
        
         Entries are added to this table via 
         cItpXuaInstRowStatus in accordance with the 
         RowStatus convention."
    ::= { cItpXuaInst 1 }

cItpXuaInstTableEntry OBJECT-TYPE
    SYNTAX CItpXuaInstTableEntry
    ACCESS not-accessible
    STATUS mandatory
    DESCRIPTION
        "A list of XUA instance attributes."
    INDEX { cItpXuaInstPort }
    ::= { cItpXuaInstTable 1 }

CItpXuaInstTableEntry ::= SEQUENCE {
    cItpXuaInstPort InetPortNumber,
    cItpXuaInstProtocol CItpXuaProtocol,
    cItpXuaInstShut TruthValue,
    cItpXuaInstActiveASPs Gauge,
    cItpXuaInstRowStatus RowStatus,
    cItpXuaInstOffload TruthValue,
    cItpXuaInstOffloadSlot Gauge
    }

cItpXuaInstPort OBJECT-TYPE
    SYNTAX InetPortNumber
--    Rsyntax Gauge(0..65535)
    ACCESS not-accessible
    STATUS mandatory
    DESCRIPTION
        "The local SCTP port for the XUA instance. The value
         zero is not allowed."
    ::= { cItpXuaInstTableEntry 1 }

cItpXuaInstProtocol OBJECT-TYPE
    SYNTAX CItpXuaProtocol
--    Rsyntax INTEGER {
--        m3ua(1),
--        sua(2),
--        sgmp(3)
--        }
    ACCESS read-write
    STATUS mandatory
    DESCRIPTION
        "The protocol of the XUA instance."
    ::= { cItpXuaInstTableEntry 2 }

cItpXuaInstShut OBJECT-TYPE
    SYNTAX TruthValue
--    Rsyntax INTEGER {
--        true(1),
--        false(2)
--        }
    ACCESS read-write
    STATUS mandatory
    DESCRIPTION
        "The XUA Instance Shut truth value.
        'true'  Indicates that the XUA Instance has
                been shutdown by an administrative action.
        'false' Indicates that the XUA Instance is
                not shutdown."
    DEFVAL { false }
    ::= { cItpXuaInstTableEntry 3 }

cItpXuaInstActiveASPs OBJECT-TYPE
    SYNTAX Gauge(0..65535)
    ACCESS read-only
    STATUS mandatory
    DESCRIPTION
        "The number of ASPs connected to this instance."
    ::= { cItpXuaInstTableEntry 4 }

cItpXuaInstRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpXuaInstTable  
         following the RowStatus textual convention."
    ::= { cItpXuaInstTableEntry 5 }

cItpXuaInstOffload OBJECT-TYPE
    SYNTAX TruthValue
--    Rsyntax INTEGER {
--        true(1),
--        false(2)
--        }
    ACCESS read-write
    STATUS mandatory
    DESCRIPTION
        "The XUA Instance Offload truth value.
        'true'  Indicates that the XUA Instance has been
                offloaded to a VIP in the slot specified by
                cItpXuaInstOffloadSlot object.
        'false' Indicates that the XUA Instance is
                not offloaded."
    DEFVAL { false }
    ::= { cItpXuaInstTableEntry 6 }

cItpXuaInstOffloadSlot OBJECT-TYPE
    SYNTAX Gauge(0..16)
    ACCESS read-write
    STATUS mandatory
    DESCRIPTION
        "When the XUA instance is offloaded to a VIP (i.e.
         cItpXuaInstOffload is true), this object specifies
         the slot number for the VIP. Otherwise, this object
         is not defined."
    DEFVAL { 0 }
    ::= { cItpXuaInstTableEntry 7 }

cItpXuaInstLocalIpTable OBJECT-TYPE
    SYNTAX SEQUENCE OF CItpXuaInstLocalIpTableEntry
    ACCESS not-accessible
    STATUS mandatory
    DESCRIPTION
        "A table of Local IP addresses for the XUA
         instances.
        
         For a given instance, there can be multiple local
         IP addresses which are used for the multi-homing
         feature of the SCTP associations. This table lists
         out the configured local IP addresses.
        
         Entries are added to this table via 
         cItpXuaInstLocalIpRowStatus in accordance with 
         the RowStatus convention."
    ::= { cItpXuaInstLocalIp 1 }

cItpXuaInstLocalIpTableEntry OBJECT-TYPE
    SYNTAX CItpXuaInstLocalIpTableEntry
    ACCESS not-accessible
    STATUS mandatory
    DESCRIPTION
        "A list of attributes of the Local IP addresses for
         the XUA instances."
    INDEX { cItpXuaInstPort, cItpXuaInstAddrNum }
    ::= { cItpXuaInstLocalIpTable 1 }

CItpXuaInstLocalIpTableEntry ::= SEQUENCE {
    cItpXuaInstAddrNum Gauge,
    cItpXuaInstLocalIpType InetAddressType,
    cItpXuaInstLocalIpAddr InetAddress,
    cItpXuaInstLocalIpRowStatus RowStatus
    }

cItpXuaInstAddrNum OBJECT-TYPE
    SYNTAX Gauge(1..65535)
    ACCESS not-accessible
    STATUS mandatory
    DESCRIPTION
        "This object specifies the index for one of local
         IP addresses for the XUA instance which is identified
         by cItpXuaInstPort."
    ::= { cItpXuaInstLocalIpTableEntry 1 }

cItpXuaInstLocalIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object contains the type of the local
         IP address used to create the association
         for ASPs connecting to the XUA instance
         specified by the cItpXuaInstPort."
    ::= { cItpXuaInstLocalIpTableEntry 2 }

cItpXuaInstLocalIpAddr OBJECT-TYPE
    SYNTAX InetAddress
--    Rsyntax OCTET STRING(SIZE(0..255))
    ACCESS read-write
    STATUS mandatory
    DESCRIPTION
        "This object contains the local IP address
         used to create the association for ASPs
         connecting to the XUA instance specified
         by the cItpXuaInstPort."
    ::= { cItpXuaInstLocalIpTableEntry 3 }

cItpXuaInstLocalIpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in
         cItpXuaInstLocalIpTable following the RowStatus
         textual convention."
    ::= { cItpXuaInstLocalIpTableEntry 4 }

cItpXuaSgmTable OBJECT-TYPE
    SYNTAX SEQUENCE OF CItpXuaSgmTableEntry
    ACCESS not-accessible
    STATUS mandatory
    DESCRIPTION
        "A table of SG Mate attributes.
        
         Entries are added to this table via 
         cItpXuaSgmRowStatus in accordance with 
         the RowStatus convention."
    ::= { cItpXuaSgm 1 }

cItpXuaSgmTableEntry OBJECT-TYPE
    SYNTAX CItpXuaSgmTableEntry
    ACCESS not-accessible
    STATUS mandatory
    DESCRIPTION
        "A list of SG Mate attributes."
    INDEX { cItpXuaSgmName }
    ::= { cItpXuaSgmTable 1 }

CItpXuaSgmTableEntry ::= SEQUENCE {
    cItpXuaSgmName CItpTcXuaName,
    cItpXuaSgmAssocId Gauge,
    cItpXuaSgmLocalPort InetPortNumber,
    cItpXuaSgmRemotePort InetPortNumber,
    cItpXuaSgmShut TruthValue,
    cItpXuaSgmActiveTS TimeTicks,
    cItpXuaSgmQosClass CItpTcQos,
    cItpXuaSgmPassive TruthValue,
    cItpXuaSgmState CItpXuaAspState,
    cItpXuaSgmRowStatus RowStatus,
    cItpXuaSgmCongLevel Gauge
    }

cItpXuaSgmName OBJECT-TYPE
    SYNTAX CItpTcXuaName
--    Rsyntax OCTET STRING(SIZE(0..12))
    ACCESS not-accessible
    STATUS mandatory
    DESCRIPTION
        "The name of the SG Mate."
    ::= { cItpXuaSgmTableEntry 1 }

cItpXuaSgmAssocId OBJECT-TYPE
    SYNTAX Gauge
    ACCESS read-only
    STATUS mandatory
    DESCRIPTION
        "This is the association identifier defined in
         the Stream Control Transmission Protocol(SCTP)
         MIB. A value greater than zero indicates a valid
         association and zero indicates no association."
    ::= { cItpXuaSgmTableEntry 2 }

cItpXuaSgmLocalPort OBJECT-TYPE
    SYNTAX InetPortNumber
--    Rsyntax Gauge(0..65535)
    ACCESS read-write
    STATUS mandatory
    DESCRIPTION
        "This object contains the local SCTP port number
         used to create the association supporting this link.
         This local port determines the XUA instance that
         this SG Mate is connected with. The value zero is not
         allowed."
    ::= { cItpXuaSgmTableEntry 3 }

cItpXuaSgmRemotePort OBJECT-TYPE
    SYNTAX InetPortNumber
--    Rsyntax Gauge(0..65535)
    ACCESS read-write
    STATUS mandatory
    DESCRIPTION
        "This object contains the remote SCTP port number
         used to create the association supporting this link.
         The value zero is not allowed."
    ::= { cItpXuaSgmTableEntry 4 }

cItpXuaSgmShut OBJECT-TYPE
    SYNTAX TruthValue
--    Rsyntax INTEGER {
--        true(1),
--        false(2)
--        }
    ACCESS read-write
    STATUS mandatory
    DESCRIPTION
        "The SG Mate shut truth value.
        'true'  Indicates that the SG Mate has been
                shutdown by an administrative action.
        'false' Indicates that the SG Mate is not
                shutdown."
    DEFVAL { false }
    ::= { cItpXuaSgmTableEntry 6 }

cItpXuaSgmActiveTS OBJECT-TYPE
    SYNTAX TimeTicks
    ACCESS read-only
    STATUS mandatory
    DESCRIPTION
        "The value of system timestamp at the time when this
         SG Mate became active. A value of zero (0) indicates
         that the SG Mate is not active."
    ::= { cItpXuaSgmTableEntry 7 }

cItpXuaSgmQosClass OBJECT-TYPE
    SYNTAX CItpTcQos
--    Rsyntax Gauge(0..7|255)
    ACCESS read-write
    STATUS mandatory
    DESCRIPTION
        "This object specifies the QOS class for the SG
         Mate. The value of 255 is not applicable. A value
         of zero (0) indicates that QOS class is not
         defined."
    DEFVAL { 0 }
    ::= { cItpXuaSgmTableEntry 8 }

cItpXuaSgmPassive OBJECT-TYPE
    SYNTAX TruthValue
--    Rsyntax INTEGER {
--        true(1),
--        false(2)
--        }
    ACCESS read-write
    STATUS mandatory
    DESCRIPTION
        "The SG Mate Passive truth value.
        'true'  Indicates that the SG Mate is passive, i.e.
                it waits for the SG Mate to initiate the
                SCTP association.
        'false' Indicates that the SG Mate is not passive,
                i.e., it initiates the SCTP association with
                its SG Mate."
    DEFVAL { true }
    ::= { cItpXuaSgmTableEntry 10 }

cItpXuaSgmState OBJECT-TYPE
    SYNTAX CItpXuaAspState
--    Rsyntax INTEGER {
--        down(1),
--        inactive(2),
--        active(3),
--        undefined(4)
--        }
    ACCESS read-only
    STATUS mandatory
    DESCRIPTION
        "The state of the SG Mate. Only active and inactive
         states are applicable."
    ::= { cItpXuaSgmTableEntry 11 }

cItpXuaSgmRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpXuaSgmTable
         following the RowStatus textual convention."
    ::= { cItpXuaSgmTableEntry 12 }

cItpXuaSgmCongLevel OBJECT-TYPE
    SYNTAX Gauge(0..7)
    ACCESS read-only
    STATUS mandatory
    DESCRIPTION
        "The current congestion level for the SG Mate. A zero
         value indicates that the SG Mate is not congested.
         The higher numbers indicate the higher levels of
         congestion. The congestion level is determined from
         the SCTP congestion indication and the SCON level
         received from the SG Mate."
    ::= { cItpXuaSgmTableEntry 13 }

cItpXuaSgmRemoteIpTable OBJECT-TYPE
    SYNTAX SEQUENCE OF CItpXuaSgmRemoteIpTableEntry
    ACCESS not-accessible
    STATUS mandatory
    DESCRIPTION
        "A table of Remote IP addresses for the Signaling  
         Gateway Mate (SGM).
        
         For a given SGM, there can be multiple remote
         IP addresses which are used for the multi-homing
         feature of the SCTP associations.
         
         Entries are added to this table via 
         cItpXuaSgmRemoteIpRowStatus in accordance with 
         the RowStatus convention."
    ::= { cItpXuaSgmRemoteIp 1 }

cItpXuaSgmRemoteIpTableEntry OBJECT-TYPE
    SYNTAX CItpXuaSgmRemoteIpTableEntry
    ACCESS not-accessible
    STATUS mandatory
    DESCRIPTION
        "A list of Remote IP addresses for the Signaling  
         Gateway Mate."
    INDEX { cItpXuaSgmName, cItpXuaSgmAddrNum }
    ::= { cItpXuaSgmRemoteIpTable 1 }

CItpXuaSgmRemoteIpTableEntry ::= SEQUENCE {
    cItpXuaSgmAddrNum Gauge,
    cItpXuaSgmRemoteIpType InetAddressType,
    cItpXuaSgmRemoteIpAddr InetAddress,
    cItpXuaSgmRemoteIpRowStatus RowStatus
    }

cItpXuaSgmAddrNum OBJECT-TYPE
    SYNTAX Gauge(1..65535)
    ACCESS not-accessible
    STATUS mandatory
    DESCRIPTION
        "This object specifies the index for the SGM's
         remote IP address. The SGM Name in cItpXuaSgmName
         specifies the SGM."
    ::= { cItpXuaSgmRemoteIpTableEntry 1 }

cItpXuaSgmRemoteIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object contains the type of the remote IP address
         used to create the association supporting this SGM."
    ::= { cItpXuaSgmRemoteIpTableEntry 2 }

cItpXuaSgmRemoteIpAddr OBJECT-TYPE
    SYNTAX InetAddress
--    Rsyntax OCTET STRING(SIZE(0..255))
    ACCESS read-write
    STATUS mandatory
    DESCRIPTION
        "This object contains the remote IP address used to
         create the association supporting this SGM."
    ::= { cItpXuaSgmRemoteIpTableEntry 3 }

cItpXuaSgmRemoteIpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in
         cItpXuaSgmRemoteIpTable following the RowStatus
         textual convention."
    ::= { cItpXuaSgmRemoteIpTableEntry 4 }

cItpXuaAspTable OBJECT-TYPE
    SYNTAX SEQUENCE OF CItpXuaAspTableEntry
    ACCESS not-accessible
    STATUS mandatory
    DESCRIPTION
        "A table of Application Server Processes (ASP).
        
         Entries are added to this table via 
         cItpXuaAspRowStatus in accordance with 
         the RowStatus convention."
    ::= { cItpXuaAsp 1 }

cItpXuaAspTableEntry OBJECT-TYPE
    SYNTAX CItpXuaAspTableEntry
    ACCESS not-accessible
    STATUS mandatory
    DESCRIPTION
        "A list of Application Server Processes."
    INDEX { cItpXuaAspName }
    ::= { cItpXuaAspTable 1 }

CItpXuaAspTableEntry ::= SEQUENCE {
    cItpXuaAspName CItpTcXuaName,
    cItpXuaAspAssocId Gauge,
    cItpXuaAspLocalPort InetPortNumber,
    cItpXuaAspRemotePort InetPortNumber,
    cItpXuaAspProtocol CItpXuaProtocol,
    cItpXuaAspShut TruthValue,
    cItpXuaAspBlocked TruthValue,
    cItpXuaAspQosClass CItpTcQos,
    cItpXuaAspIdentifier Gauge,
    cItpXuaAspRowStatus RowStatus,
    cItpXuaAspCongLevel Gauge,
    cItpXuaAspAssocIdU32 Gauge
    }

cItpXuaAspName OBJECT-TYPE
    SYNTAX CItpTcXuaName
--    Rsyntax OCTET STRING(SIZE(0..12))
    ACCESS not-accessible
    STATUS mandatory
    DESCRIPTION
        "The name of the Applicaton Server Process."
    ::= { cItpXuaAspTableEntry 1 }

cItpXuaAspAssocId OBJECT-TYPE
    SYNTAX Gauge(0..65535)
    ACCESS read-only
    STATUS deprecated
    DESCRIPTION
        "Association Identifiers can be greater than 
         65,535.  This object has been replaced by 
         cItpXuaAspAssocIdU32."
    ::= { cItpXuaAspTableEntry 2 }

cItpXuaAspLocalPort OBJECT-TYPE
    SYNTAX InetPortNumber
--    Rsyntax Gauge(0..65535)
    ACCESS read-write
    STATUS mandatory
    DESCRIPTION
        "This object contains the local SCTP port number
         used to create the association supporting this link.
         This local port determines the XUA instance that
         this ASP is connected with. The value zero is not
         allowed."
    ::= { cItpXuaAspTableEntry 3 }

cItpXuaAspRemotePort OBJECT-TYPE
    SYNTAX InetPortNumber
--    Rsyntax Gauge(0..65535)
    ACCESS read-write
    STATUS mandatory
    DESCRIPTION
        "This object contains the configured remote SCTP port
         number used to create the association supporting this
         link. The value zero means any non-zero remote port is
         acceptable. The actual remote port can be determined
         from SCTP association in cItpXuaAspAssocIdU32."
    ::= { cItpXuaAspTableEntry 4 }

cItpXuaAspProtocol OBJECT-TYPE
    SYNTAX CItpXuaProtocol
--    Rsyntax INTEGER {
--        m3ua(1),
--        sua(2),
--        sgmp(3)
--        }
    ACCESS read-write
    STATUS mandatory
    DESCRIPTION
        "The protocol used by this ASP. Only M3UA or SUA are
         allowed."
    ::= { cItpXuaAspTableEntry 5 }

cItpXuaAspShut OBJECT-TYPE
    SYNTAX TruthValue
--    Rsyntax INTEGER {
--        true(1),
--        false(2)
--        }
    ACCESS read-write
    STATUS mandatory
    DESCRIPTION
        "The ASP Shut truth value.
        'true'  Indicates that the ASP has been shutdown 
                by an administrative action.
        'false' Indicates that the ASP is not shutdown."
    DEFVAL { false }
    ::= { cItpXuaAspTableEntry 6 }

cItpXuaAspBlocked OBJECT-TYPE
    SYNTAX TruthValue
--    Rsyntax INTEGER {
--        true(1),
--        false(2)
--        }
    ACCESS read-write
    STATUS mandatory
    DESCRIPTION
        "When an ASP is blocked, it cannot receive normal
         data traffic, but it can send or receive control
         messages.
        
         The ASP Blocked  truth value.
        'true'  Indicates that the ASP has been blocked 
                by an administrative action.
        'false' Indicates that the ASP is not blocked."
    DEFVAL { false }
    ::= { cItpXuaAspTableEntry 7 }

cItpXuaAspQosClass OBJECT-TYPE
    SYNTAX CItpTcQos
--    Rsyntax Gauge(0..7|255)
    ACCESS read-write
    STATUS mandatory
    DESCRIPTION
        "This object specifies the QOS class for the ASP.
         The value of 255 is not applicable. A value of
         zero (0) indicates that QOS class is not defined.
         When QOS class is defined, it overrides the QOS
         class specified by cItpXuaAsQosClass."
    DEFVAL { 0 }
    ::= { cItpXuaAspTableEntry 9 }

cItpXuaAspIdentifier OBJECT-TYPE
    SYNTAX Gauge(0..4294967295)
    ACCESS read-only
    STATUS mandatory
    DESCRIPTION
        "A unique value received by the Signaling Gateway
         from the ASP as part of ASP UP message."
    REFERENCE
        "3.5.1 ASP Up in M3UA/SUA draft."
    ::= { cItpXuaAspTableEntry 10 }

cItpXuaAspRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpXuaAspTable
         following the RowStatus textual convention."
    ::= { cItpXuaAspTableEntry 11 }

cItpXuaAspCongLevel OBJECT-TYPE
    SYNTAX Gauge(0..7)
    ACCESS read-only
    STATUS mandatory
    DESCRIPTION
        "The current congestion level for this ASP. A zero
         value indicates that the ASP is not congested. The
         higher numbers indicate the higher levels of
         congestion. The congestion level is determined from
         the SCTP congestion indication and the SCON level
         received from the ASP."
    REFERENCE
        "3.4.4 Signalling Congestion (SCON) in M3UA
         RFC 3332 and 3.10.24 Congestion Level SUA draft."
    ::= { cItpXuaAspTableEntry 12 }

cItpXuaAspAssocIdU32 OBJECT-TYPE
    SYNTAX Gauge
    ACCESS read-only
    STATUS mandatory
    DESCRIPTION
        "This is the association identifier defined in
         the Stream Control Transmission Protocol(SCTP)
         MIB. A value greater than zero indicates a valid
         association and zero indicates no association."
    ::= { cItpXuaAspTableEntry 13 }

cItpXuaAspRemoteIpTable OBJECT-TYPE
    SYNTAX SEQUENCE OF CItpXuaAspRemoteIpTableEntry
    ACCESS not-accessible
    STATUS mandatory
    DESCRIPTION
        "A table of Remote IP addresses for the Application
         Server Processes (ASP).
        
         For a given ASP, there can be multiple remote
         IP addresses which are used for the multi-homing
         feature of the SCTP associations.
         
         Entries are added to this table via 
         cItpXuaAspRemoteIpRowStatus in accordance with 
         the RowStatus convention."
    ::= { cItpXuaAspRemoteIp 1 }

cItpXuaAspRemoteIpTableEntry OBJECT-TYPE
    SYNTAX CItpXuaAspRemoteIpTableEntry
    ACCESS not-accessible
    STATUS mandatory
    DESCRIPTION
        "A list of Remote IP addresses for the Application
         Server Processes."
    INDEX { cItpXuaAspName, cItpXuaAspAddrNum }
    ::= { cItpXuaAspRemoteIpTable 1 }

CItpXuaAspRemoteIpTableEntry ::= SEQUENCE {
    cItpXuaAspAddrNum Gauge,
    cItpXuaAspRemoteIpType InetAddressType,
    cItpXuaAspRemoteIpAddr InetAddress,
    cItpXuaAspRemoteIpRowStatus RowStatus
    }

cItpXuaAspAddrNum OBJECT-TYPE
    SYNTAX Gauge(1..65535)
    ACCESS not-accessible
    STATUS mandatory
    DESCRIPTION
        "This object specifies the index for the ASP's
         remote IP address. The ASP Name in cItpXuaAspName
         specifies the ASP."
    ::= { cItpXuaAspRemoteIpTableEntry 1 }

cItpXuaAspRemoteIpType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "This object contains the type of the remote IP address
         used to create the association supporting this ASP."
    ::= { cItpXuaAspRemoteIpTableEntry 2 }

cItpXuaAspRemoteIpAddr OBJECT-TYPE
    SYNTAX InetAddress
--    Rsyntax OCTET STRING(SIZE(0..255))
    ACCESS read-write
    STATUS mandatory
    DESCRIPTION
        "This object contains the remote IP address used to
         create the association supporting this ASP."
    ::= { cItpXuaAspRemoteIpTableEntry 3 }

cItpXuaAspRemoteIpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in
         cItpXuaAspRemoteIpTable following the RowStatus
         textual convention."
    ::= { cItpXuaAspRemoteIpTableEntry 4 }

cItpXuaAspStatsTable OBJECT-TYPE
    SYNTAX SEQUENCE OF CItpXuaAspStatsTableEntry
    ACCESS not-accessible
    STATUS mandatory
    DESCRIPTION
        "A table of Application Server Processes (ASP)
         statistics."
    ::= { cItpXuaAspStats 1 }

cItpXuaAspStatsTableEntry OBJECT-TYPE
    SYNTAX CItpXuaAspStatsTableEntry
    ACCESS not-accessible
    STATUS mandatory
    DESCRIPTION
        "A list of ASP statistics."
    INDEX { cItpXuaAspName }
    ::= { cItpXuaAspStatsTable 1 }

CItpXuaAspStatsTableEntry ::= SEQUENCE {
    cItpXuaAspPktsFromAsp Counter,
    cItpXuaAspPktsToAsp Counter,
    cItpXuaAspPktsFromMtp3 Counter,
    cItpXuaAspPktsToMtp3 Counter,
    cItpXuaAspASPUPsRcvd Counter,
    cItpXuaAspASPUPACKsSent Counter,
    cItpXuaAspASPDNsRcvd Counter,
    cItpXuaAspASPDNACKsSent Counter,
    cItpXuaAspASPACsRcvd Counter,
    cItpXuaAspASPACACKsSent Counter,
    cItpXuaAspASPIAsRcvd Counter,
    cItpXuaAspASPIAACKsSent Counter,
    cItpXuaAspErrorsRcvd Counter,
    cItpXuaAspErrorsSent Counter,
    cItpXuaAspNotifysSent Counter,
    cItpXuaAspDUNAsRcvd Counter,
    cItpXuaAspDUNAsSent Counter,
    cItpXuaAspDAVAsRcvd Counter,
    cItpXuaAspDAVAsSent Counter,
    cItpXuaAspDUPUsRcvd Counter,
    cItpXuaAspDUPUsSent Counter,
    cItpXuaAspDAUDsRcvd Counter,
    cItpXuaAspDAUDsSent Counter,
    cItpXuaAspSCON0sRcvd Counter,
    cItpXuaAspSCON1sRcvd Counter,
    cItpXuaAspSCON2sRcvd Counter,
    cItpXuaAspSCON3sRcvd Counter,
    cItpXuaAspSCON0sSent Counter,
    cItpXuaAspSCON1sSent Counter,
    cItpXuaAspSCON2sSent Counter,
    cItpXuaAspSCON3sSent Counter
    }

cItpXuaAspPktsFromAsp OBJECT-TYPE
    SYNTAX Counter
--  Units
--    packets
    ACCESS read-only
    STATUS mandatory
    DESCRIPTION
        "The number of data packets received from this ASP."
    ::= { cItpXuaAspStatsTableEntry 1 }

cItpXuaAspPktsToAsp OBJECT-TYPE
    SYNTAX Counter
--  Units
--    packets
    ACCESS read-only
    STATUS mandatory
    DESCRIPTION
        "The number of data packets sent to this ASP."
    ::= { cItpXuaAspStatsTableEntry 2 }

cItpXuaAspPktsFromMtp3 OBJECT-TYPE
    SYNTAX Counter
--  Units
--    packets
    ACCESS read-only
    STATUS mandatory
    DESCRIPTION
        "The number of data packets received from MTP3."
    ::= { cItpXuaAspStatsTableEntry 3 }

cItpXuaAspPktsToMtp3 OBJECT-TYPE
    SYNTAX Counter
--  Units
--    packets
    ACCESS read-only
    STATUS mandatory
    DESCRIPTION
        "The number of data packets sent to MTP3."
    ::= { cItpXuaAspStatsTableEntry 4 }

cItpXuaAspASPUPsRcvd OBJECT-TYPE
    SYNTAX Counter
--  Units
--    messages
    ACCESS read-only
    STATUS mandatory
    DESCRIPTION
        "The number of ASP Up messages received."
    REFERENCE
        "Section 3.5.1 ASP Up (UP) of M3UA/SUA draft."
    ::= { cItpXuaAspStatsTableEntry 5 }

cItpXuaAspASPUPACKsSent OBJECT-TYPE
    SYNTAX Counter
--  Units
--    messages
    ACCESS read-only
    STATUS mandatory
    DESCRIPTION
        "The number of ASP Up ACK messages sent."
    REFERENCE
        "Section 3.5.2 ASP Up Acknowledgement (ASP Up Ack)
         of M3UA/SUA draft."
    ::= { cItpXuaAspStatsTableEntry 6 }

cItpXuaAspASPDNsRcvd OBJECT-TYPE
    SYNTAX Counter
--  Units
--    messages
    ACCESS read-only
    STATUS mandatory
    DESCRIPTION
        "The number of ASP Down messages received."
    REFERENCE
        "Section 3.5.3 ASP Down of M3UA/SUA draft."
    ::= { cItpXuaAspStatsTableEntry 7 }

cItpXuaAspASPDNACKsSent OBJECT-TYPE
    SYNTAX Counter
--  Units
--    messages
    ACCESS read-only
    STATUS mandatory
    DESCRIPTION
        "The number of ASP Down ACK messages sent."
    REFERENCE
        "Section 3.5.4 ASP Down Acknowledgement
         (ASP Down Ack) of M3UA/SUA draft."
    ::= { cItpXuaAspStatsTableEntry 8 }

cItpXuaAspASPACsRcvd OBJECT-TYPE
    SYNTAX Counter
--  Units
--    messages
    ACCESS read-only
    STATUS mandatory
    DESCRIPTION
        "The number of ASP Active messages received."
    REFERENCE
        "Sections 3.7.1 ASP Active of M3UA draft and
         3.6.1 of SUA draft."
    ::= { cItpXuaAspStatsTableEntry 9 }

cItpXuaAspASPACACKsSent OBJECT-TYPE
    SYNTAX Counter
--  Units
--    messages
    ACCESS read-only
    STATUS mandatory
    DESCRIPTION
        "The number of ASP Active ACK messages sent."
    REFERENCE
        "Sections 3.7.2 ASP Active Acknowledgement
         (ASP Active Ack) of M3UA draft and 3.6.2 ASP
         Active (ACTIVE) of SUA draft."
    ::= { cItpXuaAspStatsTableEntry 10 }

cItpXuaAspASPIAsRcvd OBJECT-TYPE
    SYNTAX Counter
--  Units
--    messages
    ACCESS read-only
    STATUS mandatory
    DESCRIPTION
        "The number of ASP Inactive messages received."
    REFERENCE
        "Sections 3.7.3 ASP Inactive of M3UA draft and
         3.6.3 of SUA draft."
    ::= { cItpXuaAspStatsTableEntry 11 }

cItpXuaAspASPIAACKsSent OBJECT-TYPE
    SYNTAX Counter
--  Units
--    messages
    ACCESS read-only
    STATUS mandatory
    DESCRIPTION
        "The number of ASP Inactive ACK messages sent."
    REFERENCE
        "Sections 3.7.4 ASP Inactive Acknowledgement
         (ASP Inactive Ack) of M3UA draft and 3.6.4 ASP
         Inactive (INACTIVE) of SUA draft."
    ::= { cItpXuaAspStatsTableEntry 12 }

cItpXuaAspErrorsRcvd OBJECT-TYPE
    SYNTAX Counter
--  Units
--    messages
    ACCESS read-only
    STATUS mandatory
    DESCRIPTION
        "The number of ASP Error messages received."
    REFERENCE
        "Sections 3.8.1  Error of M3UA draft and
         3.7.1 Error (ERR) of SUA draft."
    ::= { cItpXuaAspStatsTableEntry 13 }

cItpXuaAspErrorsSent OBJECT-TYPE
    SYNTAX Counter
--  Units
--    messages
    ACCESS read-only
    STATUS mandatory
    DESCRIPTION
        "The number of ASP Error messages sent."
    REFERENCE
        "Sections 3.8.1  Error of M3UA draft and
         3.7.1 Error (ERR) of SUA draft."
    ::= { cItpXuaAspStatsTableEntry 14 }

cItpXuaAspNotifysSent OBJECT-TYPE
    SYNTAX Counter
--  Units
--    messages
    ACCESS read-only
    STATUS mandatory
    DESCRIPTION
        "The number of ASP Notify messages sent."
    REFERENCE
        "Sections 3.8.2 Notify of M3UA draft and
         3.7.2 Notify (NTFY) of SUA draft."
    ::= { cItpXuaAspStatsTableEntry 15 }

cItpXuaAspDUNAsRcvd OBJECT-TYPE
    SYNTAX Counter
--  Units
--    messages
    ACCESS read-only
    STATUS mandatory
    DESCRIPTION
        "The number of Destination Unavailable messages
         received."
    REFERENCE
        "Section 3.4.1 Destination Unavailable (DUNA) of
         M3UA/SUA draft."
    ::= { cItpXuaAspStatsTableEntry 16 }

cItpXuaAspDUNAsSent OBJECT-TYPE
    SYNTAX Counter
--  Units
--    messages
    ACCESS read-only
    STATUS mandatory
    DESCRIPTION
        "The number of Destination Unavailable messages
         sent."
    REFERENCE
        "Section 3.4.1 Destination Unavailable (DUNA) of
         M3UA/SUA draft."
    ::= { cItpXuaAspStatsTableEntry 17 }

cItpXuaAspDAVAsRcvd OBJECT-TYPE
    SYNTAX Counter
--  Units
--    messages
    ACCESS read-only
    STATUS mandatory
    DESCRIPTION
        "The number of Destination Available messages
         received."
    REFERENCE
        "Section 3.4.2 Destination Available (DAVA) of
         M3UA/SUA draft."
    ::= { cItpXuaAspStatsTableEntry 18 }

cItpXuaAspDAVAsSent OBJECT-TYPE
    SYNTAX Counter
--  Units
--    messages
    ACCESS read-only
    STATUS mandatory
    DESCRIPTION
        "The number of Destination Available messages
         sent."
    REFERENCE
        "Section 3.4.2 Destination Available (DAVA) of
         M3UA/SUA draft."
    ::= { cItpXuaAspStatsTableEntry 19 }

cItpXuaAspDUPUsRcvd OBJECT-TYPE
    SYNTAX Counter
--  Units
--    messages
    ACCESS read-only
    STATUS mandatory
    DESCRIPTION
        "The number of Destination User Part Unavailable
         messages received."
    REFERENCE
        "Section 3.4.5 Destination User Part Unavailable
         (DUPU) of M3UA/SUA draft."
    ::= { cItpXuaAspStatsTableEntry 20 }

cItpXuaAspDUPUsSent OBJECT-TYPE
    SYNTAX Counter
--  Units
--    messages
    ACCESS read-only
    STATUS mandatory
    DESCRIPTION
        "The number of Destination User Part Unavailable
         messages sent."
    REFERENCE
        "Section 3.4.5 Destination User Part Unavailable
         (DUPU) of M3UA/SUA draft."
    ::= { cItpXuaAspStatsTableEntry 21 }

cItpXuaAspDAUDsRcvd OBJECT-TYPE
    SYNTAX Counter
--  Units
--    messages
    ACCESS read-only
    STATUS mandatory
    DESCRIPTION
        "The number of Destination State Audit
         messages received."
    REFERENCE
        "Section 3.4.3 Destination State Audit (DAUD)
         of M3UA/SUA draft."
    ::= { cItpXuaAspStatsTableEntry 22 }

cItpXuaAspDAUDsSent OBJECT-TYPE
    SYNTAX Counter
--  Units
--    messages
    ACCESS read-only
    STATUS mandatory
    DESCRIPTION
        "The number of Destination State Audit
         messages sent."
    REFERENCE
        "Section 3.4.3 Destination State Audit (DAUD)
         of M3UA/SUA draft."
    ::= { cItpXuaAspStatsTableEntry 23 }

cItpXuaAspSCON0sRcvd OBJECT-TYPE
    SYNTAX Counter
--  Units
--    messages
    ACCESS read-only
    STATUS mandatory
    DESCRIPTION
        "The number of Signaling Congestion messages with
         congestion level 0 (or no congestion) received."
    REFERENCE
        "Section 3.4.4 Signalling Congestion (SCON)
         of M3UA/SUA draft."
    ::= { cItpXuaAspStatsTableEntry 24 }

cItpXuaAspSCON1sRcvd OBJECT-TYPE
    SYNTAX Counter
--  Units
--    messages
    ACCESS read-only
    STATUS mandatory
    DESCRIPTION
        "The number of Signaling Congestion messages with
         congestion level 1 received."
    REFERENCE
        "Section 3.4.4 Signalling Congestion (SCON)
         of M3UA/SUA draft."
    ::= { cItpXuaAspStatsTableEntry 25 }

cItpXuaAspSCON2sRcvd OBJECT-TYPE
    SYNTAX Counter
--  Units
--    messages
    ACCESS read-only
    STATUS mandatory
    DESCRIPTION
        "The number of Signaling Congestion messages with
         congestion level 2 received."
    REFERENCE
        "Section 3.4.4 Signalling Congestion (SCON)
         of M3UA/SUA draft."
    ::= { cItpXuaAspStatsTableEntry 26 }

cItpXuaAspSCON3sRcvd OBJECT-TYPE
    SYNTAX Counter
--  Units
--    messages
    ACCESS read-only
    STATUS mandatory
    DESCRIPTION
        "The number of Signaling Congestion messages with
         congestion level 3 received."
    REFERENCE
        "Section 3.4.4 Signalling Congestion (SCON)
         of M3UA/SUA draft."
    ::= { cItpXuaAspStatsTableEntry 27 }

cItpXuaAspSCON0sSent OBJECT-TYPE
    SYNTAX Counter
--  Units
--    messages
    ACCESS read-only
    STATUS mandatory
    DESCRIPTION
        "The number of Signaling Congestion messages with
         congestion level 0 (or no congestion) sent."
    REFERENCE
        "Section 3.4.4 Signalling Congestion (SCON)
         of M3UA/SUA draft."
    ::= { cItpXuaAspStatsTableEntry 28 }

cItpXuaAspSCON1sSent OBJECT-TYPE
    SYNTAX Counter
--  Units
--    messages
    ACCESS read-only
    STATUS mandatory
    DESCRIPTION
        "The number of Signaling Congestion messages with
         congestion level 1 sent."
    REFERENCE
        "Section 3.4.4 Signalling Congestion (SCON)
         of M3UA/SUA draft."
    ::= { cItpXuaAspStatsTableEntry 29 }

cItpXuaAspSCON2sSent OBJECT-TYPE
    SYNTAX Counter
--  Units
--    messages
    ACCESS read-only
    STATUS mandatory
    DESCRIPTION
        "The number of Signaling Congestion messages with
         congestion level 2 sent."
    REFERENCE
        "Section 3.4.4 Signalling Congestion (SCON)
         of M3UA/SUA draft."
    ::= { cItpXuaAspStatsTableEntry 30 }

cItpXuaAspSCON3sSent OBJECT-TYPE
    SYNTAX Counter
--  Units
--    messages
    ACCESS read-only
    STATUS mandatory
    DESCRIPTION
        "The number of Signaling Congestion messages with
         congestion level 3 sent."
    REFERENCE
        "Section 3.4.4 Signalling Congestion (SCON)
         of M3UA/SUA draft."
    ::= { cItpXuaAspStatsTableEntry 31 }

cItpXuaAsTable OBJECT-TYPE
    SYNTAX SEQUENCE OF CItpXuaAsTableEntry
    ACCESS not-accessible
    STATUS mandatory
    DESCRIPTION
        "A table of M3UA/SUA Application Server (AS) entries.
        
         Entries are added to this table via 
         cItpXuaAsRowStatus in accordance with 
         the RowStatus convention."
    ::= { cItpXuaAs 1 }

cItpXuaAsTableEntry OBJECT-TYPE
    SYNTAX CItpXuaAsTableEntry
    ACCESS not-accessible
    STATUS mandatory
    DESCRIPTION
        "A list of M3UA/SUA AS attributes."
    INDEX { cItpXuaAsName }
    ::= { cItpXuaAsTable 1 }

CItpXuaAsTableEntry ::= SEQUENCE {
    cItpXuaAsName CItpTcXuaName,
    cItpXuaAsProtocol CItpXuaProtocol,
    cItpXuaAsShut TruthValue,
    cItpXuaAsState CItpXuaAsState,
    cItpXuaAsStateOnSgMate CItpXuaAsState,
    cItpXuaAsActiveTS TimeTicks,
    cItpXuaAsQosClass CItpTcQos,
    cItpXuaAsTrafMode CItpXuaTrafMode,
    cItpXuaAsRerouting TruthValue,
    cItpXuaAsRoutingContext Gauge,
    cItpXuaAsRkParameters OCTET STRING,
    cItpXuaAsRkDpc CItpTcPointCode,
    cItpXuaAsRkOpc CItpTcPointCode,
    cItpXuaAsRkOpcMask Gauge,
    cItpXuaAsRkSi CItpTcServiceIndicator,
    cItpXuaAsRkSsn CItpTcSubSystemNumber,
    cItpXuaAsRkGtt TruthValue,
    cItpXuaAsRkCicMin Gauge,
    cItpXuaAsRkCicMax Gauge,
    cItpXuaAsPktsFromMtp3 Counter,
    cItpXuaAsPktsToASPsOfAs Counter,
    cItpXuaAsRowStatus RowStatus,
    cItpXuaAsNetworkName CItpTcNetworkName,
    cItpXuaAsNetworkAppear Gauge,
    cItpXuaAsCongLevel Gauge
    }

cItpXuaAsName OBJECT-TYPE
    SYNTAX CItpTcXuaName
--    Rsyntax OCTET STRING(SIZE(0..12))
    ACCESS not-accessible
    STATUS mandatory
    DESCRIPTION
        "The Application Server name. This name has only 
         local significance."
    ::= { cItpXuaAsTableEntry 1 }

cItpXuaAsProtocol OBJECT-TYPE
    SYNTAX CItpXuaProtocol
--    Rsyntax INTEGER {
--        m3ua(1),
--        sua(2),
--        sgmp(3)
--        }
    ACCESS read-write
    STATUS mandatory
    DESCRIPTION
        "The protocol used by this AS."
    ::= { cItpXuaAsTableEntry 2 }

cItpXuaAsShut OBJECT-TYPE
    SYNTAX TruthValue
--    Rsyntax INTEGER {
--        true(1),
--        false(2)
--        }
    ACCESS read-write
    STATUS mandatory
    DESCRIPTION
        "The AS Shut truth value.
        'true'  Indicates that the AS has been shutdown 
                by an administrative action.
        'false' Indicates that the AS is not shutdown."
    DEFVAL { false }
    ::= { cItpXuaAsTableEntry 3 }

cItpXuaAsState OBJECT-TYPE
    SYNTAX CItpXuaAsState
--    Rsyntax INTEGER {
--        down(1),
--        inactive(2),
--        active(3),
--        pending(4),
--        undefined(5)
--        }
    ACCESS read-only
    STATUS mandatory
    DESCRIPTION
        "The Application Server (AS) state."
    REFERENCE
        "4.3.2 AS States in M3UA/SUA draft."
    ::= { cItpXuaAsTableEntry 4 }

cItpXuaAsStateOnSgMate OBJECT-TYPE
    SYNTAX CItpXuaAsState
--    Rsyntax INTEGER {
--        down(1),
--        inactive(2),
--        active(3),
--        pending(4),
--        undefined(5)
--        }
    ACCESS read-only
    STATUS mandatory
    DESCRIPTION
        "The Application Server (AS) state on the mated
         Signaling Gateway.  This object provides the status
         of an Application Service as provided by the 
         Signaling Gateway Mated  Protocol.  This object 
         can be used by the NMS to assist in problem 
         determination.  
         
         Each Signaling Gateway Mated pair should have 
         same definitions.  This allows the NMS
         examine the status Application Service from 
         perspective of each Signalling Gateway.  If the
         definitions are different on the mated pairs the
         NMS will be unable to determine the relationships
         between the ASes and mated pairs."
    REFERENCE
        "4.3.2 AS States in M3UA/SUA draft."
    ::= { cItpXuaAsTableEntry 5 }

cItpXuaAsActiveTS OBJECT-TYPE
    SYNTAX TimeTicks
    ACCESS read-only
    STATUS mandatory
    DESCRIPTION
        "The value of system uptime at the time 
         when this AS became active. A value of zero (0) 
         indicates that the AS is not active."
    ::= { cItpXuaAsTableEntry 6 }

cItpXuaAsQosClass OBJECT-TYPE
    SYNTAX CItpTcQos
--    Rsyntax Gauge(0..7|255)
    ACCESS read-write
    STATUS mandatory
    DESCRIPTION
        "The AS specifies the QOS class for all its ASPs.
         The value of 255 is not applicable. A value of
         zero (0) indicates that QOS class is not defined.
         This value can be overridden by cItpXuaAspQosClass."
    DEFVAL { 0 }
    ::= { cItpXuaAsTableEntry 7 }

cItpXuaAsTrafMode OBJECT-TYPE
    SYNTAX CItpXuaTrafMode
--    Rsyntax INTEGER {
--        overRide(1),
--        loadBind(2),
--        loadRndRobin(3),
--        broadcast(4),
--        undefined(5)
--        }
    ACCESS read-write
    STATUS mandatory
    DESCRIPTION
        "The traffic mode for the data packets
         received for this AS."
    ::= { cItpXuaAsTableEntry 8 }

cItpXuaAsRerouting OBJECT-TYPE
    SYNTAX TruthValue
--    Rsyntax INTEGER {
--        true(1),
--        false(2)
--        }
    ACCESS read-only
    STATUS mandatory
    DESCRIPTION
        "The AS Rerouting truth value.
        'true'  Indicates that this SG is rerouting the
                traffic to the mated SG.
        'false' Indicates that this SG is not rerouting
                the traffic to the mated SG."
    ::= { cItpXuaAsTableEntry 9 }

cItpXuaAsRoutingContext OBJECT-TYPE
    SYNTAX Gauge(0..4294967295)
    ACCESS read-only
    STATUS mandatory
    DESCRIPTION
        "An ASP may be configured to serve more than one AS. In
         this case, the Routing Context parameter is exchanged
         between the SG and the ASP, identifying the relevant
         AS. The Routing Context uniquely identifies the range
         of traffic associated with a particular AS, which the
         ASP is configured to receive. There is a 1:1
         relationship between a Routing Context value and a
         Routing Key within an AS."
    REFERENCE
        "1.4.2 Routing Contexts and Routing Keys in M3UA draft
         and 3.9.6 Routing Context in SUA draft."
    ::= { cItpXuaAsTableEntry 10 }

cItpXuaAsRkParameters OBJECT-TYPE
    SYNTAX OCTET STRING(SIZE(1..2))
        -- BITS are:
        --   dpc(0)
        --   opc(1)
        --   opcMask(2)
        --   si(3)
        --   ssn(4)
        --   gtt(5)
        --   cic(6)
    ACCESS read-write
    STATUS mandatory
    DESCRIPTION
        "The cItpXuaAsRkParameters object indicates
         which Routing Key parameters are valid for
         this AS.
        
        'dpc'     : The cItpXuaAsRkDpc is the relevant column.
           
        'opc'     : cItpXuaAsRkOpc and cItpXuaAsRkOpcMask are
                    the relevant columns.
           
        'opcMask' : Indicates that a mask is to be applied when
                    the opc is specified in the routing key. If
                    the mask is not specified then the mask is
                    assumed to be all zeros.
        
        'si'      : The cItpXuaAsRkSi is the relevant column.
           
        'ssn'     : Indicates that a SSN is to be checked as
                    part of the routing key.
        
        'gtt'     : The cItpXuaAsRkGtt is the relevant column.
                    It indicates that routing key for this AS
                    can be the result of Global Title
                    Translation.
        
        'cic'     : The cItpXuaAsRkCicMin and cItpXuaAsRkCicMax
                    are the relevant columns.
        
         The following combination is allowed for all si's:
           gtt
           dpc
           dpc + opc
           dpc + opc + opcMask
        
         When si equals 3 (SCCP), the following is allowed:
           dpc + si
           dpc + si + opc
           dpc + si + ssn
           dpc + si + ssn + opc
        
         When si equals 4 (TUP) or 5 (ISUP), the following
         is allowed:
           dpc + si
           dpc + si + opc
           dpc + si + cic
           dpc + si + cic + opc"
    ::= { cItpXuaAsTableEntry 11 }

cItpXuaAsRkDpc OBJECT-TYPE
    SYNTAX CItpTcPointCode
--    Rsyntax Gauge(0..16777216)
    ACCESS read-write
    STATUS mandatory
    DESCRIPTION
        "The Destination Point Code (DPC) in the routing
         key for the AS. The 'dpc' bit in the
         cItpXuaAsRkParameters object is used to indicate
         whether this object's value has any current
         relevance."
    ::= { cItpXuaAsTableEntry 12 }

cItpXuaAsRkOpc OBJECT-TYPE
    SYNTAX CItpTcPointCode
--    Rsyntax Gauge(0..16777216)
    ACCESS read-write
    STATUS mandatory
    DESCRIPTION
        "The Origin Point Code (OPC) in the routing
         key for the AS. The 'opc' bit in the
         cItpXuaAsRkParameters object is used to indicate
         whether this object's value has any current
         relevance."
    ::= { cItpXuaAsTableEntry 13 }

cItpXuaAsRkOpcMask OBJECT-TYPE
    SYNTAX Gauge
    ACCESS read-write
    STATUS mandatory
    DESCRIPTION
        "The Origin Point Code (OPC) mask in the routing
         key for the AS. The 'opcMask' bit in the
         cItpXuaAsRkParameters object is used to indicate
         whether this object's value has any current
         relevance."
    ::= { cItpXuaAsTableEntry 14 }

cItpXuaAsRkSi OBJECT-TYPE
    SYNTAX CItpTcServiceIndicator
--    Rsyntax INTEGER {
--        ?? enum value of zero may cause problems
--        snmm(0),
--        sntm(1),
--        spare2(2),
--        sccp(3),
--        tup(4),
--        isup(5),
--        dupc(6),
--        dupf(7),
--        mtup(8),
--        bisup(9),
--        sisup(10),
--        spare11(11),
--        spare12(12),
--        spare13(13),
--        spare14(14),
--        spare15(15)
--        }
    ACCESS read-write
    STATUS mandatory
    DESCRIPTION
        "The Service Indicator in the routing key for
         the AS. The 'si' bit in the cItpXuaAsRkParameters
         object is used to indicate whether this object's
         value has any current relevance."
    ::= { cItpXuaAsTableEntry 15 }

cItpXuaAsRkSsn OBJECT-TYPE
    SYNTAX CItpTcSubSystemNumber
--    Rsyntax Gauge(0|2..255)
    ACCESS read-write
    STATUS mandatory
    DESCRIPTION
        "The SubSystem Number (SSN) in routing key for
         the AS. The 'ssn' bit in the cItpXuaAsRkParameters
         object is used to indicate whether this object's
         value has any current relevance."
    ::= { cItpXuaAsTableEntry 16 }

cItpXuaAsRkGtt OBJECT-TYPE
    SYNTAX TruthValue
--    Rsyntax INTEGER {
--        true(1),
--        false(2)
--        }
    ACCESS read-write
    STATUS mandatory
    DESCRIPTION
        "The Routing key Global Title Translation (GTT)
         truth value.
        'true'  Indicates that the GTT is enabled.
        'false' Indicates that the GTT is not enabled.
        
         The 'gtt' bit in the cItpXuaAsRkParameters object
         is used to indicate whether this object's value
         has any current relevance."
    ::= { cItpXuaAsTableEntry 17 }

cItpXuaAsRkCicMin OBJECT-TYPE
    SYNTAX Gauge(0..65535)
    ACCESS read-write
    STATUS mandatory
    DESCRIPTION
        "The Routing key minimum CIC value. The 'cic'
         bit in the cItpXuaAsRkParameters object is used
         to indicate whether this object's value has any
         current relevance."
    ::= { cItpXuaAsTableEntry 18 }

cItpXuaAsRkCicMax OBJECT-TYPE
    SYNTAX Gauge(0..65535)
    ACCESS read-write
    STATUS mandatory
    DESCRIPTION
        "The Routing key maximum CIC value. The 'cic'
         bit in the cItpXuaAsRkParameters object is used
         to indicate whether this object's value has any
         current relevance."
    ::= { cItpXuaAsTableEntry 19 }

cItpXuaAsPktsFromMtp3 OBJECT-TYPE
    SYNTAX Counter
--  Units
--    packets
    ACCESS read-only
    STATUS mandatory
    DESCRIPTION
        "The number of data packets received from MTP3."
    ::= { cItpXuaAsTableEntry 20 }

cItpXuaAsPktsToASPsOfAs OBJECT-TYPE
    SYNTAX Counter
--  Units
--    packets
    ACCESS read-only
    STATUS mandatory
    DESCRIPTION
        "The number of data packets sent to all ASPs that
         are serving this AS."
    ::= { cItpXuaAsTableEntry 21 }

cItpXuaAsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpXuaAsTable 
         following the RowStatus textual convention."
    ::= { cItpXuaAsTableEntry 22 }

cItpXuaAsNetworkName OBJECT-TYPE
    SYNTAX CItpTcNetworkName
--    Rsyntax OCTET STRING(SIZE(0..19))
    ACCESS read-only
    STATUS mandatory
    DESCRIPTION
        "The network name is used to indicate the network
         in which this signalling point is participating.
         One or more instances of signalling points can 
         exist in the same physical device.  This identifier
         will be used to correlate instances of signalling 
         points by network.
         When multiple instance support is not enabled the 
         network name will default to the null string.
         
         An octet string specified by an administrator that
         must be in human-readable form.  The names must conform
         to the allowed characters that can be specified via 
         Command Line Interface(CLI).  The names cannot contain
         control character and should not contain leading or 
         trailing white space."
    ::= { cItpXuaAsTableEntry 23 }

cItpXuaAsNetworkAppear OBJECT-TYPE
    SYNTAX Gauge
    ACCESS read-write
    STATUS mandatory
    DESCRIPTION
        "The Network Appearance is a local reference shared by
         SG and AS that together with a point code uniquely
         identifies an SS7 node by indicating the specific SS7
         network it belongs to. It can be used to distinguish
         between signaling traffic associated with different
         networks being sent between the SG and the ASP over
         a common SCTP association. An example scenario is
         where an SG appears as an element in multiple
         separate national SS7 networks and the same point
         code value may be reused in different networks."
    REFERENCE
        "1.2 Terminology section in RFC 3332 and SUA draft 16"
    ::= { cItpXuaAsTableEntry 24 }

cItpXuaAsCongLevel OBJECT-TYPE
    SYNTAX Gauge(0..7)
    ACCESS read-only
    STATUS mandatory
    DESCRIPTION
        "The current congestion level for the AS. A zero
         value indicates that the AS is not congested.
         The higher numbers indicate the higher levels of
         congestion. The congestion level is determined from
         the congestion levels of the ASPs that belong to
         this AS."
    ::= { cItpXuaAsTableEntry 25 }

cItpXuaAspAsTable OBJECT-TYPE
    SYNTAX SEQUENCE OF CItpXuaAspAsTableEntry
    ACCESS not-accessible
    STATUS mandatory
    DESCRIPTION
        "A table of M3UA/SUA ASP-AS entries.
        
         An ASP can serve one or more ASes. For each AS
         that it serves, the ASP maintains the state
         information.
         
         Entries are added to this table via 
         cItpXuaAspAsRowStatus in accordance with 
         the RowStatus convention."
    ::= { cItpXuaAspAs 1 }

cItpXuaAspAsTableEntry OBJECT-TYPE
    SYNTAX CItpXuaAspAsTableEntry
    ACCESS not-accessible
    STATUS mandatory
    DESCRIPTION
        "A list of M3UA/SUA ASP-AS attributes."
    INDEX { cItpXuaAspName, cItpXuaAspAsName }
    ::= { cItpXuaAspAsTable 1 }

CItpXuaAspAsTableEntry ::= SEQUENCE {
    cItpXuaAspAsName CItpTcXuaName,
    cItpXuaAspAsState CItpXuaAspState,
    cItpXuaAspAsActiveTS TimeTicks,
    cItpXuaAspAsRowStatus RowStatus,
    cItpXuaAspAsWeight Gauge
    }

cItpXuaAspAsName OBJECT-TYPE
    SYNTAX CItpTcXuaName
--    Rsyntax OCTET STRING(SIZE(0..12))
    ACCESS not-accessible
    STATUS mandatory
    DESCRIPTION
        "The Application Server name."
    ::= { cItpXuaAspAsTableEntry 1 }

cItpXuaAspAsState OBJECT-TYPE
    SYNTAX CItpXuaAspState
--    Rsyntax INTEGER {
--        down(1),
--        inactive(2),
--        active(3),
--        undefined(4)
--        }
    ACCESS read-only
    STATUS mandatory
    DESCRIPTION
        "The state of the ASP that serves this AS."
    REFERENCE
        "4.3.1 ASP States in M3UA/SUA draft."
    ::= { cItpXuaAspAsTableEntry 2 }

cItpXuaAspAsActiveTS OBJECT-TYPE
    SYNTAX TimeTicks
    ACCESS read-only
    STATUS mandatory
    DESCRIPTION
        "The value of system timestamp at the time when this
         ASP became active with respect to the specified AS.
         If the ASP is not active with respect to the 
         specified AS this object will contain a value of 
         zero."
    ::= { cItpXuaAspAsTableEntry 3 }

cItpXuaAspAsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpXuaAspAsTable
         following the RowStatus textual convention."
    ::= { cItpXuaAspAsTableEntry 4 }

cItpXuaAspAsWeight OBJECT-TYPE
    SYNTAX Gauge(0..10)
    ACCESS read-write
    STATUS mandatory
    DESCRIPTION
        "When cItpXuaAsTrafMode specifies 'loadRndRobind',
         this object specifies the weight which is used in
         Weighted Round Robin algorithm. The default is 1.
         When the weight is 0, this particular ASP is 
         selected only when there are no other active ASPs
         with a non-zero weight."
    DEFVAL { 1 }
    ::= { cItpXuaAspAsTableEntry 5 }

cItpXuaASRouteTable OBJECT-TYPE
    SYNTAX SEQUENCE OF CItpXuaASRouteTableEntry
    ACCESS not-accessible
    STATUS mandatory
    DESCRIPTION
        "A table of routes for remote point-codes using
         ASs defined on this ITP node.
        
         Entries are added to this table via 
         cItpXuaASRouteRowStatus in accordance with 
         the RowStatus convention."
    ::= { cItpXuaASRoute 1 }

cItpXuaASRouteTableEntry OBJECT-TYPE
    SYNTAX CItpXuaASRouteTableEntry
    ACCESS not-accessible
    STATUS mandatory
    DESCRIPTION
        "A list of routes for remote point-codes using    
         ASs."
    INDEX { cItpXuaAsrName }
    ::= { cItpXuaASRouteTable 1 }

CItpXuaASRouteTableEntry ::= SEQUENCE {
    cItpXuaAsrName CItpTcXuaName,
    cItpXuaAsrNetwork CItpTcNetworkName,
    cItpXuaAsrProtocol CItpXuaProtocol,
    cItpXuaAsrRoutingContext Gauge,
    cItpXuaAsrDpc CItpTcPointCode,
    cItpXuaAsrShut TruthValue,
    cItpXuaAsrSgmateState CItpXuaRouteState,
    cItpXuaAsrSgmatePriority Gauge,
    cItpXuaAsrOutbPktsRcvd Counter,
    cItpXuaAsrOutbByteRcvd Counter,
    cItpXuaAsrOutbPktsSent Counter,
    cItpXuaAsrOutbByteSent Counter,
    cItpXuaAsrSgmateDunaRcvd Counter,
    cItpXuaAsrSgmateDavaRcvd Counter,
    cItpXuaAsrSgmateDrstRcvd Counter,
    cItpXuaAsrRowStatus RowStatus
    }

cItpXuaAsrName OBJECT-TYPE
    SYNTAX CItpTcXuaName
--    Rsyntax OCTET STRING(SIZE(0..12))
    ACCESS not-accessible
    STATUS mandatory
    DESCRIPTION
        "The ASRoute name. This name has only local 
         significance."
    ::= { cItpXuaASRouteTableEntry 1 }

cItpXuaAsrNetwork OBJECT-TYPE
    SYNTAX CItpTcNetworkName
--    Rsyntax OCTET STRING(SIZE(0..19))
    ACCESS read-only
    STATUS mandatory
    DESCRIPTION
        "The network name is used to indicate the network
         in which this signalling point is participating.
         One or more instances of signalling points can 
         exist in the same physical device.  This identifier
         will be used to correlate instances of signalling 
         points by network.
         When multiple instance support is not enabled the 
         network name will default to the null string.
        
         An octet string specified by an administrator that
         must be in human-readable form.  The names must conform
         to the allowed characters that can be specified via 
         Command Line Interface(CLI).  The names cannot contain
         control character and should not contain leading or 
         trailing white space."
    ::= { cItpXuaASRouteTableEntry 2 }

cItpXuaAsrProtocol OBJECT-TYPE
    SYNTAX CItpXuaProtocol
--    Rsyntax INTEGER {
--        m3ua(1),
--        sua(2),
--        sgmp(3)
--        }
    ACCESS read-write
    STATUS mandatory
    DESCRIPTION
        "The protocol used by this ASRoute."
    ::= { cItpXuaASRouteTableEntry 3 }

cItpXuaAsrRoutingContext OBJECT-TYPE
    SYNTAX Gauge(0..4294967295)
    ACCESS read-only
    STATUS mandatory
    DESCRIPTION
        "An AS may be configured to serve more than one
         ASRoute. In this case, the Routing Context parameter
         is exchanged between the SG and the ASP, identifying
         the relevant AS. The Routing Context uniquely
         identifies the range of traffic associated with a
         particular AS, which the ASP is configured to
         receive."
    ::= { cItpXuaASRouteTableEntry 4 }

cItpXuaAsrDpc OBJECT-TYPE
    SYNTAX CItpTcPointCode
--    Rsyntax Gauge(0..16777216)
    ACCESS read-write
    STATUS mandatory
    DESCRIPTION
        "The Destination Point Code (DPC) in the routing
         key for the ASRoute."
    ::= { cItpXuaASRouteTableEntry 5 }

cItpXuaAsrShut OBJECT-TYPE
    SYNTAX TruthValue
--    Rsyntax INTEGER {
--        true(1),
--        false(2)
--        }
    ACCESS read-write
    STATUS mandatory
    DESCRIPTION
        "The ASRoute Shut truth value.
        'true'  Indicates that the ASRoute has been shutdown
                by an administrative action.
        'false' Indicates that the ASRoute is not shutdown."
    DEFVAL { false }
    ::= { cItpXuaASRouteTableEntry 6 }

cItpXuaAsrSgmateState OBJECT-TYPE
    SYNTAX CItpXuaRouteState
--    Rsyntax INTEGER {
--        unknown(1),
--        avail(2),
--        restr(3),
--        unavail(4),
--        deleted(5)
--        }
    ACCESS read-only
    STATUS mandatory
    DESCRIPTION
        "The ASRoute state on the mated Signalling Gateway.
         This object provides the status of an ASRoute as
         provided by the Signalling Gateway Mated  Protocol.
         This object can be used by the NMS to assist in
         problem determination.  
         
         Each Signaling Gateway Mated pair should have 
         same definitions.  This allows the NMS
         examine the status ASRoute from the perspective of
         each Signalling Gateway.  If the definitions are
         different on the mated pairs the NMS will be unable
         to determine the relationships between the ASRoutes
         and mated pairs."
    ::= { cItpXuaASRouteTableEntry 7 }

cItpXuaAsrSgmatePriority OBJECT-TYPE
    SYNTAX Gauge(0..9)
    ACCESS read-only
    STATUS mandatory
    DESCRIPTION
        "The ASRoute priority on the mated Signalling
         Gateway."
    ::= { cItpXuaASRouteTableEntry 8 }

cItpXuaAsrOutbPktsRcvd OBJECT-TYPE
    SYNTAX Counter
--  Units
--    packets
    ACCESS read-only
    STATUS mandatory
    DESCRIPTION
        "The number of outbound data packets received from
         MTP3."
    ::= { cItpXuaASRouteTableEntry 9 }

cItpXuaAsrOutbByteRcvd OBJECT-TYPE
    SYNTAX --?? syntax is not convertable to SMIv1
           Counter
--  Units
--    Octets
    ACCESS read-only
    STATUS mandatory
    DESCRIPTION
        "The number of outbound data byte received from
         MTP3."
    ::= { cItpXuaASRouteTableEntry 10 }

cItpXuaAsrOutbPktsSent OBJECT-TYPE
    SYNTAX Counter
--  Units
--    packets
    ACCESS read-only
    STATUS mandatory
    DESCRIPTION
        "The number of outbound data packets sent to this 
         ASroute."
    ::= { cItpXuaASRouteTableEntry 11 }

cItpXuaAsrOutbByteSent OBJECT-TYPE
    SYNTAX --?? syntax is not convertable to SMIv1
           Counter
--  Units
--    Octets
    ACCESS read-only
    STATUS mandatory
    DESCRIPTION
        "The number of outbound data byte sent to this 
         ASRoute."
    ::= { cItpXuaASRouteTableEntry 12 }

cItpXuaAsrSgmateDunaRcvd OBJECT-TYPE
    SYNTAX Counter
--  Units
--    packets
    ACCESS read-only
    STATUS mandatory
    DESCRIPTION
        "The number of Destination Unavailable (DUNA)
         messages received by the SG Mate."
    ::= { cItpXuaASRouteTableEntry 13 }

cItpXuaAsrSgmateDavaRcvd OBJECT-TYPE
    SYNTAX Counter
--  Units
--    packets
    ACCESS read-only
    STATUS mandatory
    DESCRIPTION
        "The number of Destination Available (DAVA)
         messages received by the SG Mate."
    ::= { cItpXuaASRouteTableEntry 14 }

cItpXuaAsrSgmateDrstRcvd OBJECT-TYPE
    SYNTAX Counter
--  Units
--    packets
    ACCESS read-only
    STATUS mandatory
    DESCRIPTION
        "The number of Destination Restricted (DRST)
         messages received by the SG Mate."
    ::= { cItpXuaASRouteTableEntry 15 }

cItpXuaAsrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpXuaASRouteTable
         following the RowStatus textual convention."
    ::= { cItpXuaASRouteTableEntry 16 }

cItpXuaASRouteAsTable OBJECT-TYPE
    SYNTAX SEQUENCE OF CItpXuaASRouteAsTableEntry
    ACCESS not-accessible
    STATUS mandatory
    DESCRIPTION
        "A table of routes for remote point-codes using
         ASs defined on this ITP node.
        
         Entries are added to this table via 
         cItpXuaASRouteRowStatus in accordance with 
         the RowStatus convention."
    ::= { cItpXuaASRouteAs 1 }

cItpXuaASRouteAsTableEntry OBJECT-TYPE
    SYNTAX CItpXuaASRouteAsTableEntry
    ACCESS not-accessible
    STATUS mandatory
    DESCRIPTION
        "A list of ASs for ASRoute."
    INDEX { cItpXuaAsrName, cItpXuaAsrAsName }
    ::= { cItpXuaASRouteAsTable 1 }

CItpXuaASRouteAsTableEntry ::= SEQUENCE {
    cItpXuaAsrAsName CItpTcXuaName,
    cItpXuaAsrAsPriority Gauge,
    cItpXuaAsrAsState CItpXuaRouteState,
    cItpXuaAsrAsOutbPktsRcvd Counter,
    cItpXuaAsrAsOutbByteRcvd Counter,
    cItpXuaAsrAsOutbPktsSent Counter,
    cItpXuaAsrAsOutbByteSent Counter,
    cItpXuaAsrAsDunaRcvd Counter,
    cItpXuaAsrAsDavaRcvd Counter,
    cItpXuaAsrAsDrstRcvd Counter,
    cItpXuaAsrAsRowStatus RowStatus
    }

cItpXuaAsrAsName OBJECT-TYPE
    SYNTAX CItpTcXuaName
--    Rsyntax OCTET STRING(SIZE(0..12))
    ACCESS not-accessible
    STATUS mandatory
    DESCRIPTION
        "The Application Server name."
    ::= { cItpXuaASRouteAsTableEntry 1 }

cItpXuaAsrAsPriority OBJECT-TYPE
    SYNTAX Gauge(0..9)
    ACCESS read-only
    STATUS mandatory
    DESCRIPTION
        "The priority of this AS in the ASRoute."
    ::= { cItpXuaASRouteAsTableEntry 2 }

cItpXuaAsrAsState OBJECT-TYPE
    SYNTAX CItpXuaRouteState
--    Rsyntax INTEGER {
--        unknown(1),
--        avail(2),
--        restr(3),
--        unavail(4),
--        deleted(5)
--        }
    ACCESS read-only
    STATUS mandatory
    DESCRIPTION
        "The AS state in the ASRoute."
    ::= { cItpXuaASRouteAsTableEntry 3 }

cItpXuaAsrAsOutbPktsRcvd OBJECT-TYPE
    SYNTAX Counter
--  Units
--    packets
    ACCESS read-only
    STATUS mandatory
    DESCRIPTION
        "The number of outbound data packets received from
         MTP3 for this AS."
    ::= { cItpXuaASRouteAsTableEntry 4 }

cItpXuaAsrAsOutbByteRcvd OBJECT-TYPE
    SYNTAX --?? syntax is not convertable to SMIv1
           Counter
--  Units
--    Octets
    ACCESS read-only
    STATUS mandatory
    DESCRIPTION
        "The number of outbound data byte received from
         MTP3 for this AS."
    ::= { cItpXuaASRouteAsTableEntry 5 }

cItpXuaAsrAsOutbPktsSent OBJECT-TYPE
    SYNTAX Counter
--  Units
--    packets
    ACCESS read-only
    STATUS mandatory
    DESCRIPTION
        "The number of outbound data packets sent to this 
         AS in the ASroute."
    ::= { cItpXuaASRouteAsTableEntry 6 }

cItpXuaAsrAsOutbByteSent OBJECT-TYPE
    SYNTAX --?? syntax is not convertable to SMIv1
           Counter
--  Units
--    Octets
    ACCESS read-only
    STATUS mandatory
    DESCRIPTION
        "The number of outbound data byte sent to this 
         AS in the ASRoute."
    ::= { cItpXuaASRouteAsTableEntry 7 }

cItpXuaAsrAsDunaRcvd OBJECT-TYPE
    SYNTAX Counter
--  Units
--    packets
    ACCESS read-only
    STATUS mandatory
    DESCRIPTION
        "The number of Destination Unavailable (DUNA)
         messages received by this AS in the ASRoute."
    ::= { cItpXuaASRouteAsTableEntry 8 }

cItpXuaAsrAsDavaRcvd OBJECT-TYPE
    SYNTAX Counter
--  Units
--    packets
    ACCESS read-only
    STATUS mandatory
    DESCRIPTION
        "The number of Destination Available (DAVA)
         messages received by this AS in the ASRoute."
    ::= { cItpXuaASRouteAsTableEntry 9 }

cItpXuaAsrAsDrstRcvd OBJECT-TYPE
    SYNTAX Counter
--  Units
--    packets
    ACCESS read-only
    STATUS mandatory
    DESCRIPTION
        "The number of Destination Restricted (DRST)
         messages received by this AS in the ASRoute."
    ::= { cItpXuaASRouteAsTableEntry 10 }

cItpXuaAsrAsRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in
         cItpXuaASRouteAsTable following the RowStatus
         textual convention."
    ::= { cItpXuaASRouteAsTableEntry 11 }

cItpXuaSgmDisplayName OBJECT-TYPE
    SYNTAX CItpTcXuaName
--    Rsyntax OCTET STRING(SIZE(0..12))
    ACCESS not-accessible
    STATUS mandatory
    DESCRIPTION
        "This object identifies the SG Mate name associated with
         the ciscoItpXuaSgmStateChange notification."
    ::= { cItpXuaMIBNotifObjects 1 }

cItpXuaAspDisplayName OBJECT-TYPE
    SYNTAX CItpTcXuaName
--    Rsyntax OCTET STRING(SIZE(0..12))
    ACCESS not-accessible
    STATUS mandatory
    DESCRIPTION
        "This object identifies the ASP name associated with
         the ciscoItpXuaAspStateChange notification."
    ::= { cItpXuaMIBNotifObjects 2 }

cItpXuaAsDisplayName OBJECT-TYPE
    SYNTAX CItpTcXuaName
--    Rsyntax OCTET STRING(SIZE(0..12))
    ACCESS not-accessible
    STATUS mandatory
    DESCRIPTION
        "This object identifies the AS name associated with
         the ciscoItpXuaAspStateChange and
         ciscoItpXuaAsStateChange notifications."
    ::= { cItpXuaMIBNotifObjects 3 }

ciscoItpXuaAspStateChange TRAP-TYPE
-- Reverse mappable trap
    ENTERPRISE ciscoItpXuaMIB
    VARIABLES {
        cItpSpCLLICode, cItpXuaAspDisplayName, cItpXuaAsDisplayName, 
        cItpXuaAspAsState }
--  Status
--    mandatory
    DESCRIPTION
        "The notification generated when an ASP changes
         to a new state. The value of cItpXuaAspAsState
         indicates the new state for the ASP that is 
         serving the AS specified by cItpXuaAsDisplayName."
    ::= 1

ciscoItpXuaSgmStateChange TRAP-TYPE
-- Reverse mappable trap
    ENTERPRISE ciscoItpXuaMIB
    VARIABLES {
        cItpSpCLLICode, cItpXuaSgmDisplayName, cItpXuaSgmState }
--  Status
--    mandatory
    DESCRIPTION
        "The notification generated when an SG Mate
         changes to a new state. The value of
         cItpXuaSgmState indicates the new state for
         the SG Mate."
    ::= 2

ciscoItpXuaAsStateChange TRAP-TYPE
-- Reverse mappable trap
    ENTERPRISE ciscoItpXuaMIB
    VARIABLES {
        cItpSpCLLICode, cItpXuaAsDisplayName, cItpXuaAsState }
--  Status
--    mandatory
    DESCRIPTION
        "The notification generated when an AS changes
         to a new state. The value of cItpXuaAsState
         indicates the new state for the AS."
    ::= 3

ciscoItpXuaAspCongChange TRAP-TYPE
-- Reverse mappable trap
    ENTERPRISE ciscoItpXuaMIB
    VARIABLES {
        cItpSpCLLICode, cItpXuaAspDisplayName, cItpXuaAspCongLevel }
--  Status
--    mandatory
    DESCRIPTION
        "The notification generated when an ASP changes
         to a new congestion level. The value of
         cItpXuaAspCongLevel indicates the new congetion
         level for the ASP."
    ::= 4

ciscoItpXuaSgmCongChange TRAP-TYPE
-- Reverse mappable trap
    ENTERPRISE ciscoItpXuaMIB
    VARIABLES {
        cItpSpCLLICode, cItpXuaSgmDisplayName, cItpXuaSgmCongLevel }
--  Status
--    mandatory
    DESCRIPTION
        "The notification generated when an SG Mate changes
         to a new congestion level. The value of
         cItpXuaSgmCongLevel indicates the new congetion
         level for the SG Mate."
    ::= 5

ciscoItpXuaScalarsGroup OBJECT IDENTIFIER ::= { ciscoItpXuaMIBGroups 1 }
-- OBJECT-GROUP
--  Status
--    mandatory
--  Descr
--    M3UA/SUA main objects.
--  objects
--    cItpXuaInstConfigLastChanged, cItpXuaSgmConfigLastChanged, 
--    cItpXuaAspConfigLastChanged, cItpXuaAsConfigLastChanged, 
--    cItpXuaStateChangeNotifEnabled

ciscoItpXuaInstGroup OBJECT IDENTIFIER ::= { ciscoItpXuaMIBGroups 2 }
-- OBJECT-GROUP
--  Status
--    deprecated
--  Descr
--    M3UA/SUA Instance objects.
--  objects
--    cItpXuaInstProtocol, cItpXuaInstShut, cItpXuaInstActiveASPs, 
--    cItpXuaInstRowStatus

ciscoItpXuaInstLocalIpGroup OBJECT IDENTIFIER ::= { ciscoItpXuaMIBGroups 3 }
-- OBJECT-GROUP
--  Status
--    mandatory
--  Descr
--    The Local IP address for M3UA/SUA Instance
--     objects.
--  objects
--    cItpXuaInstLocalIpType, cItpXuaInstLocalIpAddr, 
--    cItpXuaInstLocalIpRowStatus

ciscoItpXuaSgmGroup OBJECT IDENTIFIER ::= { ciscoItpXuaMIBGroups 4 }
-- OBJECT-GROUP
--  Status
--    deprecated
--  Descr
--    SG Mate objects.
--  objects
--    cItpXuaSgmAssocId, cItpXuaSgmLocalPort, cItpXuaSgmRemotePort, 
--    cItpXuaSgmShut, cItpXuaSgmActiveTS, cItpXuaSgmQosClass, 
--    cItpXuaSgmPassive, cItpXuaSgmState, cItpXuaSgmRowStatus

ciscoItpXuaAspGroup OBJECT IDENTIFIER ::= { ciscoItpXuaMIBGroups 5 }
-- OBJECT-GROUP
--  Status
--    deprecated
--  Descr
--    M3UA/SUA ASP objects.
--  objects
--    cItpXuaAspAssocId, cItpXuaAspLocalPort, cItpXuaAspRemotePort, 
--    cItpXuaAspProtocol, cItpXuaAspShut, cItpXuaAspBlocked, 
--    cItpXuaAspQosClass, cItpXuaAspIdentifier, cItpXuaAspRowStatus

ciscoItpXuaAspRemoteIpGroup OBJECT IDENTIFIER ::= { ciscoItpXuaMIBGroups 6 }
-- OBJECT-GROUP
--  Status
--    mandatory
--  Descr
--    Remote IP address for M3UA/SUA ASP objects.
--  objects
--    cItpXuaAspRemoteIpType, cItpXuaAspRemoteIpAddr, 
--    cItpXuaAspRemoteIpRowStatus

ciscoItpXuaAspStatsGroup OBJECT IDENTIFIER ::= { ciscoItpXuaMIBGroups 7 }
-- OBJECT-GROUP
--  Status
--    mandatory
--  Descr
--    M3UA/SUA ASP Statistics objects.
--  objects
--    cItpXuaAspPktsFromAsp, cItpXuaAspPktsToAsp, 
--    cItpXuaAspPktsFromMtp3, cItpXuaAspPktsToMtp3, 
--    cItpXuaAspASPUPsRcvd, cItpXuaAspASPUPACKsSent, 
--    cItpXuaAspASPDNsRcvd, cItpXuaAspASPDNACKsSent, 
--    cItpXuaAspASPACsRcvd, cItpXuaAspASPACACKsSent, 
--    cItpXuaAspASPIAsRcvd, cItpXuaAspASPIAACKsSent, 
--    cItpXuaAspErrorsRcvd, cItpXuaAspErrorsSent, 
--    cItpXuaAspNotifysSent, cItpXuaAspDUNAsRcvd, 
--    cItpXuaAspDUNAsSent, cItpXuaAspDAVAsRcvd, cItpXuaAspDAVAsSent, 
--    cItpXuaAspDUPUsRcvd, cItpXuaAspDUPUsSent, cItpXuaAspDAUDsRcvd, 
--    cItpXuaAspDAUDsSent, cItpXuaAspSCON0sRcvd, 
--    cItpXuaAspSCON1sRcvd, cItpXuaAspSCON2sRcvd, 
--    cItpXuaAspSCON3sRcvd, cItpXuaAspSCON0sSent, 
--    cItpXuaAspSCON1sSent, cItpXuaAspSCON2sSent, 
--    cItpXuaAspSCON3sSent

ciscoItpXuaAsGroup OBJECT IDENTIFIER ::= { ciscoItpXuaMIBGroups 8 }
-- OBJECT-GROUP
--  Status
--    deprecated
--  Descr
--    M3UA/SUA AS objects.
--  objects
--    cItpXuaAsProtocol, cItpXuaAsShut, cItpXuaAsState, 
--    cItpXuaAsStateOnSgMate, cItpXuaAsActiveTS, cItpXuaAsQosClass, 
--    cItpXuaAsTrafMode, cItpXuaAsRerouting, 
--    cItpXuaAsRoutingContext, cItpXuaAsRkParameters, 
--    cItpXuaAsRkDpc, cItpXuaAsRkOpc, cItpXuaAsRkOpcMask, 
--    cItpXuaAsRkSi, cItpXuaAsRkSsn, cItpXuaAsRkGtt, 
--    cItpXuaAsRkCicMin, cItpXuaAsRkCicMax, cItpXuaAsPktsFromMtp3, 
--    cItpXuaAsPktsToASPsOfAs, cItpXuaAsRowStatus

ciscoItpXuaAspAsGroup OBJECT IDENTIFIER ::= { ciscoItpXuaMIBGroups 9 }
-- OBJECT-GROUP
--  Status
--    deprecated
--  Descr
--    M3UA/SUA ASP-AS objects.
--  objects
--    cItpXuaAspAsState, cItpXuaAspAsActiveTS, 
--    cItpXuaAspAsRowStatus

ciscoItpXuaNotifObjectsGroup OBJECT IDENTIFIER ::= { ciscoItpXuaMIBGroups 10 }
-- OBJECT-GROUP
--  Status
--    mandatory
--  Descr
--    M3UA/SUA notification objects.
--  objects
--    cItpXuaSgmDisplayName, cItpXuaAspDisplayName, 
--    cItpXuaAsDisplayName

ciscoItpXuaSgmGroupRev1 OBJECT IDENTIFIER ::= { ciscoItpXuaMIBGroups 12 }
-- OBJECT-GROUP
--  Status
--    mandatory
--  Descr
--    SG Mate objects.
--  objects
--    cItpXuaSgmAssocId, cItpXuaSgmLocalPort, cItpXuaSgmRemotePort, 
--    cItpXuaSgmShut, cItpXuaSgmActiveTS, cItpXuaSgmQosClass, 
--    cItpXuaSgmPassive, cItpXuaSgmState, cItpXuaSgmRowStatus, 
--    cItpXuaSgmCongLevel

ciscoItpXuaAspGroupRev1 OBJECT IDENTIFIER ::= { ciscoItpXuaMIBGroups 13 }
-- OBJECT-GROUP
--  Status
--    deprecated
--  Descr
--    M3UA/SUA ASP objects.
--  objects
--    cItpXuaAspAssocId, cItpXuaAspLocalPort, cItpXuaAspRemotePort, 
--    cItpXuaAspProtocol, cItpXuaAspShut, cItpXuaAspBlocked, 
--    cItpXuaAspQosClass, cItpXuaAspIdentifier, cItpXuaAspRowStatus, 
--    cItpXuaAspCongLevel

ciscoItpXuaSgmRemoteIpGroup OBJECT IDENTIFIER ::= { ciscoItpXuaMIBGroups 15 }
-- OBJECT-GROUP
--  Status
--    mandatory
--  Descr
--    Remote IP address for the Signaling Gateway Mate.
--  objects
--    cItpXuaSgmRemoteIpType, cItpXuaSgmRemoteIpAddr, 
--    cItpXuaSgmRemoteIpRowStatus

ciscoItpXuaInstGroupRev2 OBJECT IDENTIFIER ::= { ciscoItpXuaMIBGroups 16 }
-- OBJECT-GROUP
--  Status
--    mandatory
--  Descr
--    M3UA/SUA Instance objects.
--  objects
--    cItpXuaInstProtocol, cItpXuaInstShut, cItpXuaInstActiveASPs, 
--    cItpXuaInstRowStatus, cItpXuaInstOffload, 
--    cItpXuaInstOffloadSlot

ciscoItpXuaAspGroupRev2 OBJECT IDENTIFIER ::= { ciscoItpXuaMIBGroups 17 }
-- OBJECT-GROUP
--  Status
--    mandatory
--  Descr
--    M3UA/SUA ASP objects.
--  objects
--    cItpXuaAspLocalPort, cItpXuaAspRemotePort, cItpXuaAspProtocol, 
--    cItpXuaAspShut, cItpXuaAspBlocked, cItpXuaAspQosClass, 
--    cItpXuaAspIdentifier, cItpXuaAspRowStatus, 
--    cItpXuaAspCongLevel, cItpXuaAspAssocIdU32

ciscoItpXuaAsGroupRev2 OBJECT IDENTIFIER ::= { ciscoItpXuaMIBGroups 18 }
-- OBJECT-GROUP
--  Status
--    deprecated
--  Descr
--    M3UA/SUA AS objects.
--  objects
--    cItpXuaAsProtocol, cItpXuaAsShut, cItpXuaAsState, 
--    cItpXuaAsStateOnSgMate, cItpXuaAsActiveTS, cItpXuaAsQosClass, 
--    cItpXuaAsTrafMode, cItpXuaAsRerouting, 
--    cItpXuaAsRoutingContext, cItpXuaAsRkParameters, 
--    cItpXuaAsRkDpc, cItpXuaAsRkOpc, cItpXuaAsRkOpcMask, 
--    cItpXuaAsRkSi, cItpXuaAsRkSsn, cItpXuaAsRkGtt, 
--    cItpXuaAsRkCicMin, cItpXuaAsRkCicMax, cItpXuaAsPktsFromMtp3, 
--    cItpXuaAsPktsToASPsOfAs, cItpXuaAsRowStatus, 
--    cItpXuaAsNetworkName

ciscoItpXuaAsGroupRev3 OBJECT IDENTIFIER ::= { ciscoItpXuaMIBGroups 19 }
-- OBJECT-GROUP
--  Status
--    mandatory
--  Descr
--    M3UA/SUA AS objects.
--  objects
--    cItpXuaAsProtocol, cItpXuaAsShut, cItpXuaAsState, 
--    cItpXuaAsStateOnSgMate, cItpXuaAsActiveTS, cItpXuaAsQosClass, 
--    cItpXuaAsTrafMode, cItpXuaAsRerouting, 
--    cItpXuaAsRoutingContext, cItpXuaAsRkParameters, 
--    cItpXuaAsRkDpc, cItpXuaAsRkOpc, cItpXuaAsRkOpcMask, 
--    cItpXuaAsRkSi, cItpXuaAsRkSsn, cItpXuaAsRkGtt, 
--    cItpXuaAsRkCicMin, cItpXuaAsRkCicMax, cItpXuaAsPktsFromMtp3, 
--    cItpXuaAsPktsToASPsOfAs, cItpXuaAsRowStatus, 
--    cItpXuaAsNetworkName, cItpXuaAsNetworkAppear, 
--    cItpXuaAsCongLevel

ciscoItpXuaAspAsGroupRev3 OBJECT IDENTIFIER ::= { ciscoItpXuaMIBGroups 20 }
-- OBJECT-GROUP
--  Status
--    mandatory
--  Descr
--    M3UA/SUA ASP-AS objects.
--  objects
--    cItpXuaAspAsState, cItpXuaAspAsActiveTS, 
--    cItpXuaAspAsRowStatus, cItpXuaAspAsWeight

ciscoItpXuaAsrGroup OBJECT IDENTIFIER ::= { ciscoItpXuaMIBGroups 21 }
-- OBJECT-GROUP
--  Status
--    mandatory
--  Descr
--    ASRoute objects.
--  objects
--    cItpXuaAsrNetwork, cItpXuaAsrProtocol, 
--    cItpXuaAsrRoutingContext, cItpXuaAsrDpc, cItpXuaAsrShut, 
--    cItpXuaAsrSgmateState, cItpXuaAsrSgmatePriority, 
--    cItpXuaAsrOutbPktsRcvd, cItpXuaAsrOutbByteRcvd, 
--    cItpXuaAsrOutbPktsSent, cItpXuaAsrOutbByteSent, 
--    cItpXuaAsrSgmateDunaRcvd, cItpXuaAsrSgmateDavaRcvd, 
--    cItpXuaAsrSgmateDrstRcvd, cItpXuaAsrRowStatus

ciscoItpXuaAsrAsGroup OBJECT IDENTIFIER ::= { ciscoItpXuaMIBGroups 22 }
-- OBJECT-GROUP
--  Status
--    mandatory
--  Descr
--    ASRoute-AS objects.
--  objects
--    cItpXuaAsrAsPriority, cItpXuaAsrAsState, 
--    cItpXuaAsrAsOutbPktsRcvd, cItpXuaAsrAsOutbByteRcvd, 
--    cItpXuaAsrAsOutbPktsSent, cItpXuaAsrAsOutbByteSent, 
--    cItpXuaAsrAsDunaRcvd, cItpXuaAsrAsDavaRcvd, 
--    cItpXuaAsrAsDrstRcvd, cItpXuaAsrAsRowStatus

ciscoItpXuaNotificationsGroup OBJECT IDENTIFIER ::= { ciscoItpXuaMIBGroups 11 }
-- NOTIFICATION-GROUP
--  Status
--    deprecated
--  Descr
--    M3UA/SUA notifications.
--  notifications
--    ciscoItpXuaAspStateChange, ciscoItpXuaSgmStateChange, 
--    ciscoItpXuaAsStateChange

ciscoItpXuaNotifGroupRev1 OBJECT IDENTIFIER ::= { ciscoItpXuaMIBGroups 14 }
-- NOTIFICATION-GROUP
--  Status
--    mandatory
--  Descr
--    M3UA/SUA notifications.
--  notifications
--    ciscoItpXuaAspStateChange, ciscoItpXuaSgmStateChange, 
--    ciscoItpXuaAsStateChange, ciscoItpXuaAspCongChange, 
--    ciscoItpXuaSgmCongChange

ciscoItpXuaMIBCompliance OBJECT IDENTIFIER ::= { ciscoItpXuaMIBCompliances 1 }
-- MODULE-COMPLIANCE
--  Status
--    deprecated
--  Descr
--    The compliance statement for entities which
--     implement the Cisco ITP XUA MIB
--  Module
--    >>current<<
--   MandGroup
--    ciscoItpXuaScalarsGroup
--   MandGroup
--    ciscoItpXuaInstGroup
--   MandGroup
--    ciscoItpXuaInstLocalIpGroup
--   MandGroup
--    ciscoItpXuaSgmGroup
--   MandGroup
--    ciscoItpXuaAspGroup
--   MandGroup
--    ciscoItpXuaAspRemoteIpGroup
--   MandGroup
--    ciscoItpXuaAsGroup
--   MandGroup
--    ciscoItpXuaAspAsGroup
--   MandGroup
--    ciscoItpXuaNotifObjectsGroup
--   MandGroup
--    ciscoItpXuaNotificationsGroup

ciscoItpXuaMIBComplianceRev1 OBJECT IDENTIFIER ::= { ciscoItpXuaMIBCompliances 2 }
-- MODULE-COMPLIANCE
--  Status
--    deprecated
--  Descr
--    The compliance statement for entities which
--     implement the Cisco ITP XUA MIB
--  Module
--    >>current<<
--   MandGroup
--    ciscoItpXuaScalarsGroup
--   MandGroup
--    ciscoItpXuaInstGroup
--   MandGroup
--    ciscoItpXuaInstLocalIpGroup
--   MandGroup
--    ciscoItpXuaSgmGroupRev1
--   MandGroup
--    ciscoItpXuaAspGroupRev1
--   MandGroup
--    ciscoItpXuaAspRemoteIpGroup
--   MandGroup
--    ciscoItpXuaAsGroup
--   MandGroup
--    ciscoItpXuaAspAsGroup
--   MandGroup
--    ciscoItpXuaNotifObjectsGroup
--   MandGroup
--    ciscoItpXuaNotifGroupRev1
--   MandGroup
--    ciscoItpXuaSgmRemoteIpGroup

ciscoItpXuaMIBComplianceRev2 OBJECT IDENTIFIER ::= { ciscoItpXuaMIBCompliances 3 }
-- MODULE-COMPLIANCE
--  Status
--    deprecated
--  Descr
--    The compliance statement for entities which
--     implement the Cisco ITP XUA MIB
--  Module
--    >>current<<
--   MandGroup
--    ciscoItpXuaScalarsGroup
--   MandGroup
--    ciscoItpXuaInstLocalIpGroup
--   MandGroup
--    ciscoItpXuaSgmGroupRev1
--   MandGroup
--    ciscoItpXuaAspRemoteIpGroup
--   MandGroup
--    ciscoItpXuaAspAsGroup
--   MandGroup
--    ciscoItpXuaNotifObjectsGroup
--   MandGroup
--    ciscoItpXuaNotifGroupRev1
--   MandGroup
--    ciscoItpXuaSgmRemoteIpGroup
--   MandGroup
--    ciscoItpXuaInstGroupRev2
--   MandGroup
--    ciscoItpXuaAspGroupRev2
--   MandGroup
--    ciscoItpXuaAsGroupRev2
--   OptGroup
--    ciscoItpXuaAspStatsGroup

ciscoItpXuaMIBComplianceRev3 OBJECT IDENTIFIER ::= { ciscoItpXuaMIBCompliances 4 }
-- MODULE-COMPLIANCE
--  Status
--    mandatory
--  Descr
--    The compliance statement for entities which
--     implement the Cisco ITP XUA MIB
--  Module
--    >>current<<
--   MandGroup
--    ciscoItpXuaScalarsGroup
--   MandGroup
--    ciscoItpXuaInstLocalIpGroup
--   MandGroup
--    ciscoItpXuaSgmGroupRev1
--   MandGroup
--    ciscoItpXuaAspRemoteIpGroup
--   MandGroup
--    ciscoItpXuaAspAsGroupRev3
--   MandGroup
--    ciscoItpXuaNotifObjectsGroup
--   MandGroup
--    ciscoItpXuaNotifGroupRev1
--   MandGroup
--    ciscoItpXuaSgmRemoteIpGroup
--   MandGroup
--    ciscoItpXuaInstGroupRev2
--   MandGroup
--    ciscoItpXuaAspGroupRev2
--   MandGroup
--    ciscoItpXuaAsGroupRev3
--   MandGroup
--    ciscoItpXuaAsrGroup
--   MandGroup
--    ciscoItpXuaAsrAsGroup
--   OptGroup
--    ciscoItpXuaAspStatsGroup


END
