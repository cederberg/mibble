-- MIB file created 14-Jan-2004 14:56:23, by
--   SMICng version 2.2.11-beta(PRO)(Solaris), January 20, 2001. Enterprise key cisco.com

CISCO-ENVMON-MIB DEFINITIONS ::= BEGIN

-- From file: "CISCO-ENVMON-MIB.my"
-- Compile options "4 7 F H N W 03 06 0B 0G 0N 0T"

IMPORTS
    DisplayString, TruthValue
            FROM SNMPv2-TC-v1
    ciscoMgmt
            FROM CISCO-SMI
    Gauge
            FROM RFC1155-SMI
    OBJECT-TYPE
            FROM RFC-1212
    TRAP-TYPE
            FROM RFC-1215;

ciscoEnvMonMIB OBJECT IDENTIFIER ::= { ciscoMgmt 13 }
-- MODULE-IDENTITY
--  LastUpdated
--    200311250000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-snmp@cisco.com
--  Descr
--    The MIB module to describe the status of the Environmental
--    Monitor on those devices which support one.
--  RevDate
--    200311250000Z
--  RevDescr
--    Added ciscoEnvMonMIBMiscNotifGroup.
--  RevDate
--    200210150000Z
--  RevDescr
--    Added c7600(12) as values for ciscoEnvMonPresent
--  RevDate
--    200207170000Z
--  RevDescr
--    Added optional groups ciscoEnvMonEnableStatChangeGroup
--     and ciscoEnvMonStatChangeNotifGroup.
--  RevDate
--    200202040000Z
--  RevDescr
--    Added osr7600(11) as values 
--    for ciscoEnvMonPresent
--  RevDate
--    200108300000Z
--  RevDescr
--    Added c10000(10) as values for ciscoEnvMonPresent
--  RevDate
--    200108160000Z
--  RevDescr
--    Added cat4000(9) as values for ciscoEnvMonPresent
--  RevDate
--    200105070000Z
--  RevDescr
--    Added cat6000(7),ubr7200(8) 
--    as values for ciscoEnvMonPresent
--  RevDate
--    200001310000Z
--  RevDescr
--    Add notFunctioning to CiscoEnvMonState.
--  RevDate
--    9810220000Z
--  RevDescr
--    Renamed enumerated value internalRPS(5) as 
--     internalRedundant(5) and added description for
--     ciscoEnvMonSupplySource enumerated values.
--  RevDate
--    9808050000Z
--  RevDescr
--    Add enumerated value internalRPS(5) to 
--    ciscoEnvMonSupplySource.
--  RevDate
--    9611120000Z
--  RevDescr
--    Add monitoring support for c3600 series router
--  RevDate
--    9508150000Z
--  RevDescr
--    Specify a correct (non-negative) range for several
--    index objects.
--  RevDate
--    9503130000Z
--  RevDescr
--    Miscellaneous changes including monitoring support
--    for c7000 series redundant power supplies.

ciscoEnvMonObjects OBJECT IDENTIFIER ::= { ciscoEnvMonMIB 1 }
ciscoEnvMonMIBNotificationEnables OBJECT IDENTIFIER ::= { ciscoEnvMonMIB 2 }
ciscoEnvMonMIBNotificationPrefix OBJECT IDENTIFIER ::= { ciscoEnvMonMIB 3 }
ciscoEnvMonMIBNotifications OBJECT IDENTIFIER ::= { ciscoEnvMonMIBNotificationPrefix 0 }
ciscoEnvMonMIBConformance OBJECT IDENTIFIER ::= { ciscoEnvMonMIB 4 }
ciscoEnvMonMIBCompliances OBJECT IDENTIFIER ::= { ciscoEnvMonMIBConformance 1 }
ciscoEnvMonMIBGroups OBJECT IDENTIFIER ::= { ciscoEnvMonMIBConformance 2 }

CiscoEnvMonState ::= INTEGER {
        normal(1),
        warning(2),
        critical(3),
        shutdown(4),
        notPresent(5),
        notFunctioning(6)
        }
-- TEXTUAL-CONVENTION
--  Status
--    mandatory
--  Descr
--    Represents the state of a device being monitored.
--     Valid values are:
--    
--     normal(1):         the environment is good, such as low
--                        temperature.
--    
--     warning(2):        the environment is bad, such as temperature
--                        above normal operation range but not too
--                        high.
--    
--     critical(3):       the environment is very bad, such as
--                        temperature much higher than normal
--                        operation limit.
--    
--     shutdown(4):       the environment is the worst, the system
--                        should be shutdown immediately.
--    
--     notPresent(5):     the environmental monitor is not present,
--                        such as temperature sensors do not exist.
--    
--     notFunctioning(6): the environmental monitor does not 
--                        function properly, such as a temperature
--                        sensor generates a abnormal data like
--                        1000 C.

CiscoSignedGauge ::= INTEGER
-- TEXTUAL-CONVENTION
--  Status
--    mandatory
--  Descr
--    Represents the current value of an entity, as a signed 
--     integer.

ciscoEnvMonPresent OBJECT-TYPE
    SYNTAX INTEGER {
        oldAgs(1),
        ags(2),
        c7000(3),
        ci(4),
        cAccessMon(6),
        cat6000(7),
        ubr7200(8),
        cat4000(9),
        c10000(10),
        osr7600(11),
        c7600(12)
        }
    ACCESS read-only
    STATUS mandatory
    DESCRIPTION
        "The type of environmental monitor located in the chassis.
        An oldAgs environmental monitor card is identical to an ags
        environmental card except that it is not capable of supplying
        data, and hence no instance of the remaining objects in this
        MIB will be returned in response to an SNMP query.  Note that
        only a firmware upgrade is required to convert an oldAgs into
        an ags card."
    ::= { ciscoEnvMonObjects 1 }

ciscoEnvMonVoltageStatusTable OBJECT-TYPE
    SYNTAX SEQUENCE OF CiscoEnvMonVoltageStatusEntry
    ACCESS not-accessible
    STATUS mandatory
    DESCRIPTION
        "The table of voltage status maintained by the environmental
        monitor."
    ::= { ciscoEnvMonObjects 2 }

ciscoEnvMonVoltageStatusEntry OBJECT-TYPE
    SYNTAX CiscoEnvMonVoltageStatusEntry
    ACCESS not-accessible
    STATUS mandatory
    DESCRIPTION
        "An entry in the voltage status table, representing the status
        of the associated testpoint maintained by the environmental
        monitor."
    INDEX { ciscoEnvMonVoltageStatusIndex }
    ::= { ciscoEnvMonVoltageStatusTable 1 }

CiscoEnvMonVoltageStatusEntry ::= SEQUENCE {
    ciscoEnvMonVoltageStatusIndex INTEGER,
    ciscoEnvMonVoltageStatusDescr DisplayString,
    ciscoEnvMonVoltageStatusValue CiscoSignedGauge,
    ciscoEnvMonVoltageThresholdLow INTEGER,
    ciscoEnvMonVoltageThresholdHigh INTEGER,
    ciscoEnvMonVoltageLastShutdown INTEGER,
    ciscoEnvMonVoltageState CiscoEnvMonState
    }

ciscoEnvMonVoltageStatusIndex OBJECT-TYPE
    SYNTAX INTEGER(0..2147483647)
    ACCESS not-accessible
    STATUS mandatory
    DESCRIPTION
        "Unique index for the testpoint being instrumented.
        This index is for SNMP purposes only, and has no
        intrinsic meaning."
    ::= { ciscoEnvMonVoltageStatusEntry 1 }

ciscoEnvMonVoltageStatusDescr OBJECT-TYPE
    SYNTAX DisplayString(SIZE(0..32))
--    Rsyntax OCTET STRING(SIZE(0..32))
    ACCESS read-only
    STATUS mandatory
    DESCRIPTION
        "Textual description of the testpoint being instrumented.
        This description is a short textual label, suitable as a
        human-sensible identification for the rest of the
        information in the entry."
    ::= { ciscoEnvMonVoltageStatusEntry 2 }

ciscoEnvMonVoltageStatusValue OBJECT-TYPE
    SYNTAX CiscoSignedGauge
--    Rsyntax INTEGER
--  Units
--    millivolts
    ACCESS read-only
    STATUS mandatory
    DESCRIPTION
        "The current measurement of the testpoint being instrumented."
    ::= { ciscoEnvMonVoltageStatusEntry 3 }

ciscoEnvMonVoltageThresholdLow OBJECT-TYPE
    SYNTAX INTEGER
--  Units
--    millivolts
    ACCESS read-only
    STATUS mandatory
    DESCRIPTION
        "The lowest value that the associated instance of the object
        ciscoEnvMonVoltageStatusValue may obtain before an emergency
        shutdown of the managed device is initiated."
    ::= { ciscoEnvMonVoltageStatusEntry 4 }

ciscoEnvMonVoltageThresholdHigh OBJECT-TYPE
    SYNTAX INTEGER
--  Units
--    millivolts
    ACCESS read-only
    STATUS mandatory
    DESCRIPTION
        "The highest value that the associated instance of the object
        ciscoEnvMonVoltageStatusValue may obtain before an emergency
        shutdown of the managed device is initiated."
    ::= { ciscoEnvMonVoltageStatusEntry 5 }

ciscoEnvMonVoltageLastShutdown OBJECT-TYPE
    SYNTAX INTEGER
--  Units
--    millivolts
    ACCESS read-only
    STATUS mandatory
    DESCRIPTION
        "The value of the associated instance of the object
        ciscoEnvMonVoltageStatusValue at the time an emergency
        shutdown of the managed device was last initiated.  This
        value is stored in non-volatile RAM and hence is able to
        survive the shutdown."
    ::= { ciscoEnvMonVoltageStatusEntry 6 }

ciscoEnvMonVoltageState OBJECT-TYPE
    SYNTAX CiscoEnvMonState
--    Rsyntax INTEGER {
--        normal(1),
--        warning(2),
--        critical(3),
--        shutdown(4),
--        notPresent(5),
--        notFunctioning(6)
--        }
    ACCESS read-only
    STATUS mandatory
    DESCRIPTION
        "The current state of the testpoint being instrumented."
    ::= { ciscoEnvMonVoltageStatusEntry 7 }

ciscoEnvMonTemperatureStatusTable OBJECT-TYPE
    SYNTAX SEQUENCE OF CiscoEnvMonTemperatureStatusEntry
    ACCESS not-accessible
    STATUS mandatory
    DESCRIPTION
        "The table of ambient temperature status maintained by the
        environmental monitor."
    ::= { ciscoEnvMonObjects 3 }

ciscoEnvMonTemperatureStatusEntry OBJECT-TYPE
    SYNTAX CiscoEnvMonTemperatureStatusEntry
    ACCESS not-accessible
    STATUS mandatory
    DESCRIPTION
        "An entry in the ambient temperature status table, representing
        the status of the associated testpoint maintained by the
        environmental monitor."
    INDEX { ciscoEnvMonTemperatureStatusIndex }
    ::= { ciscoEnvMonTemperatureStatusTable 1 }

CiscoEnvMonTemperatureStatusEntry ::= SEQUENCE {
    ciscoEnvMonTemperatureStatusIndex INTEGER,
    ciscoEnvMonTemperatureStatusDescr DisplayString,
    ciscoEnvMonTemperatureStatusValue Gauge,
    ciscoEnvMonTemperatureThreshold INTEGER,
    ciscoEnvMonTemperatureLastShutdown INTEGER,
    ciscoEnvMonTemperatureState CiscoEnvMonState
    }

ciscoEnvMonTemperatureStatusIndex OBJECT-TYPE
    SYNTAX INTEGER(0..2147483647)
    ACCESS not-accessible
    STATUS mandatory
    DESCRIPTION
        "Unique index for the testpoint being instrumented.
        This index is for SNMP purposes only, and has no
        intrinsic meaning."
    ::= { ciscoEnvMonTemperatureStatusEntry 1 }

ciscoEnvMonTemperatureStatusDescr OBJECT-TYPE
    SYNTAX DisplayString(SIZE(0..32))
--    Rsyntax OCTET STRING(SIZE(0..32))
    ACCESS read-only
    STATUS mandatory
    DESCRIPTION
        "Textual description of the testpoint being instrumented.
        This description is a short textual label, suitable as a
        human-sensible identification for the rest of the
        information in the entry."
    ::= { ciscoEnvMonTemperatureStatusEntry 2 }

ciscoEnvMonTemperatureStatusValue OBJECT-TYPE
    SYNTAX Gauge
--  Units
--    degrees Celsius
    ACCESS read-only
    STATUS mandatory
    DESCRIPTION
        "The current measurement of the testpoint being instrumented."
    ::= { ciscoEnvMonTemperatureStatusEntry 3 }

ciscoEnvMonTemperatureThreshold OBJECT-TYPE
    SYNTAX INTEGER
--  Units
--    degrees Celsius
    ACCESS read-only
    STATUS mandatory
    DESCRIPTION
        "The highest value that the associated instance of the
        object ciscoEnvMonTemperatureStatusValue may obtain
        before an emergency shutdown of the managed device is
        initiated."
    ::= { ciscoEnvMonTemperatureStatusEntry 4 }

ciscoEnvMonTemperatureLastShutdown OBJECT-TYPE
    SYNTAX INTEGER
--  Units
--    degrees Celsius
    ACCESS read-only
    STATUS mandatory
    DESCRIPTION
        "The value of the associated instance of the object
        ciscoEnvMonTemperatureStatusValue at the time an emergency
        shutdown of the managed device was last initiated.  This
        value is stored in non-volatile RAM and hence is able to
        survive the shutdown."
    ::= { ciscoEnvMonTemperatureStatusEntry 5 }

ciscoEnvMonTemperatureState OBJECT-TYPE
    SYNTAX CiscoEnvMonState
--    Rsyntax INTEGER {
--        normal(1),
--        warning(2),
--        critical(3),
--        shutdown(4),
--        notPresent(5),
--        notFunctioning(6)
--        }
    ACCESS read-only
    STATUS mandatory
    DESCRIPTION
        "The current state of the testpoint being instrumented."
    ::= { ciscoEnvMonTemperatureStatusEntry 6 }

ciscoEnvMonFanStatusTable OBJECT-TYPE
    SYNTAX SEQUENCE OF CiscoEnvMonFanStatusEntry
    ACCESS not-accessible
    STATUS mandatory
    DESCRIPTION
        "The table of fan status maintained by the environmental
        monitor."
    ::= { ciscoEnvMonObjects 4 }

ciscoEnvMonFanStatusEntry OBJECT-TYPE
    SYNTAX CiscoEnvMonFanStatusEntry
    ACCESS not-accessible
    STATUS mandatory
    DESCRIPTION
        "An entry in the fan status table, representing the status of
        the associated fan maintained by the environmental monitor."
    INDEX { ciscoEnvMonFanStatusIndex }
    ::= { ciscoEnvMonFanStatusTable 1 }

CiscoEnvMonFanStatusEntry ::= SEQUENCE {
    ciscoEnvMonFanStatusIndex INTEGER,
    ciscoEnvMonFanStatusDescr DisplayString,
    ciscoEnvMonFanState CiscoEnvMonState
    }

ciscoEnvMonFanStatusIndex OBJECT-TYPE
    SYNTAX INTEGER(0..2147483647)
    ACCESS not-accessible
    STATUS mandatory
    DESCRIPTION
        "Unique index for the fan being instrumented.
        This index is for SNMP purposes only, and has no
        intrinsic meaning."
    ::= { ciscoEnvMonFanStatusEntry 1 }

ciscoEnvMonFanStatusDescr OBJECT-TYPE
    SYNTAX DisplayString(SIZE(0..32))
--    Rsyntax OCTET STRING(SIZE(0..32))
    ACCESS read-only
    STATUS mandatory
    DESCRIPTION
        "Textual description of the fan being instrumented.
        This description is a short textual label, suitable as a
        human-sensible identification for the rest of the
        information in the entry."
    ::= { ciscoEnvMonFanStatusEntry 2 }

ciscoEnvMonFanState OBJECT-TYPE
    SYNTAX CiscoEnvMonState
--    Rsyntax INTEGER {
--        normal(1),
--        warning(2),
--        critical(3),
--        shutdown(4),
--        notPresent(5),
--        notFunctioning(6)
--        }
    ACCESS read-only
    STATUS mandatory
    DESCRIPTION
        "The current state of the fan being instrumented."
    ::= { ciscoEnvMonFanStatusEntry 3 }

ciscoEnvMonSupplyStatusTable OBJECT-TYPE
    SYNTAX SEQUENCE OF CiscoEnvMonSupplyStatusEntry
    ACCESS not-accessible
    STATUS mandatory
    DESCRIPTION
        "The table of power supply status maintained by the
        environmental monitor card."
    ::= { ciscoEnvMonObjects 5 }

ciscoEnvMonSupplyStatusEntry OBJECT-TYPE
    SYNTAX CiscoEnvMonSupplyStatusEntry
    ACCESS not-accessible
    STATUS mandatory
    DESCRIPTION
        "An entry in the power supply status table, representing the
        status of the associated power supply maintained by the
        environmental monitor card."
    INDEX { ciscoEnvMonSupplyStatusIndex }
    ::= { ciscoEnvMonSupplyStatusTable 1 }

CiscoEnvMonSupplyStatusEntry ::= SEQUENCE {
    ciscoEnvMonSupplyStatusIndex INTEGER,
    ciscoEnvMonSupplyStatusDescr DisplayString,
    ciscoEnvMonSupplyState CiscoEnvMonState,
    ciscoEnvMonSupplySource INTEGER
    }

ciscoEnvMonSupplyStatusIndex OBJECT-TYPE
    SYNTAX INTEGER(0..2147483647)
    ACCESS not-accessible
    STATUS mandatory
    DESCRIPTION
        "Unique index for the power supply being instrumented.
        This index is for SNMP purposes only, and has no
        intrinsic meaning."
    ::= { ciscoEnvMonSupplyStatusEntry 1 }

ciscoEnvMonSupplyStatusDescr OBJECT-TYPE
    SYNTAX DisplayString(SIZE(0..32))
--    Rsyntax OCTET STRING(SIZE(0..32))
    ACCESS read-only
    STATUS mandatory
    DESCRIPTION
        "Textual description of the power supply being instrumented.
        This description is a short textual label, suitable as a
        human-sensible identification for the rest of the
        information in the entry."
    ::= { ciscoEnvMonSupplyStatusEntry 2 }

ciscoEnvMonSupplyState OBJECT-TYPE
    SYNTAX CiscoEnvMonState
--    Rsyntax INTEGER {
--        normal(1),
--        warning(2),
--        critical(3),
--        shutdown(4),
--        notPresent(5),
--        notFunctioning(6)
--        }
    ACCESS read-only
    STATUS mandatory
    DESCRIPTION
        "The current state of the power supply being instrumented."
    ::= { ciscoEnvMonSupplyStatusEntry 3 }

ciscoEnvMonSupplySource OBJECT-TYPE
    SYNTAX INTEGER {
        unknown(1),
        ac(2),
        dc(3),
        externalPowerSupply(4),
        internalRedundant(5)
        }
    ACCESS read-only
    STATUS mandatory
    DESCRIPTION
        "The power supply source.
         unknown - Power supply source unknown
         ac      - AC power supply
         dc      - DC power supply
         externalPowerSupply - External power supply
         internalRedundant - Internal redundant power supply "
    ::= { ciscoEnvMonSupplyStatusEntry 4 }

ciscoEnvMonAlarmContacts OBJECT-TYPE
    SYNTAX OCTET STRING(SIZE(1..2))
        -- BITS are:
        --   minorVisual(0)
        --   majorVisual(1)
        --   criticalVisual(2)
        --   minorAudible(3)
        --   majorAudible(4)
        --   criticalAudible(5)
        --   input(6)
    ACCESS read-only
    STATUS mandatory
    DESCRIPTION
        "Each bit is set to reflect the respective
         alarm being set.  The bit will be cleared
         when the respective alarm is cleared."
    ::= { ciscoEnvMonObjects 6 }

ciscoEnvMonEnableShutdownNotification OBJECT-TYPE
    SYNTAX TruthValue
--    Rsyntax INTEGER {
--        true(1),
--        false(2)
--        }
    ACCESS read-write
    STATUS mandatory
    DESCRIPTION
        "This variable  indicates  whether  the  system
         produces the ciscoEnvMonShutdownNotification.  A false 
         value will prevent shutdown notifications 
         from being generated by this system."
    DEFVAL { false }
    ::= { ciscoEnvMonMIBNotificationEnables 1 }

ciscoEnvMonEnableVoltageNotification OBJECT-TYPE
    SYNTAX TruthValue
--    Rsyntax INTEGER {
--        true(1),
--        false(2)
--        }
    ACCESS read-write
    STATUS deprecated
    DESCRIPTION
        "This variable  indicates  whether  the  system
         produces the ciscoEnvMonVoltageNotification. A false 
         value will prevent voltage notifications from being 
         generated by this system. This object is deprecated
         in favour of ciscoEnvMonEnableStatChangeNotif."
    DEFVAL { false }
    ::= { ciscoEnvMonMIBNotificationEnables 2 }

ciscoEnvMonEnableTemperatureNotification OBJECT-TYPE
    SYNTAX TruthValue
--    Rsyntax INTEGER {
--        true(1),
--        false(2)
--        }
    ACCESS read-write
    STATUS deprecated
    DESCRIPTION
        "This variable  indicates  whether  the  system
         produces the ciscoEnvMonTemperatureNotification.
         A false value prevents temperature notifications 
         from being sent by  this entity. This object is 
         deprecated in favour of 
         ciscoEnvMonEnableStatChangeNotif."
    DEFVAL { false }
    ::= { ciscoEnvMonMIBNotificationEnables 3 }

ciscoEnvMonEnableFanNotification OBJECT-TYPE
    SYNTAX TruthValue
--    Rsyntax INTEGER {
--        true(1),
--        false(2)
--        }
    ACCESS read-write
    STATUS deprecated
    DESCRIPTION
        "This variable  indicates  whether  the  system
         produces the ciscoEnvMonFanNotification.
         A false value prevents fan notifications 
         from being sent by  this entity. This object is 
         deprecated in favour of 
         ciscoEnvMonEnableStatChangeNotif."
    DEFVAL { false }
    ::= { ciscoEnvMonMIBNotificationEnables 4 }

ciscoEnvMonEnableRedundantSupplyNotification OBJECT-TYPE
    SYNTAX TruthValue
--    Rsyntax INTEGER {
--        true(1),
--        false(2)
--        }
    ACCESS read-write
    STATUS deprecated
    DESCRIPTION
        "This variable  indicates  whether  the  system
         produces the ciscoEnvMonRedundantSupplyNotification. 
         A false value prevents redundant supply notifications
         from being generated by this system. This object is
         deprecated in favour of 
         ciscoEnvMonEnableStatChangeNotif."
    DEFVAL { false }
    ::= { ciscoEnvMonMIBNotificationEnables 5 }

ciscoEnvMonEnableStatChangeNotif OBJECT-TYPE
    SYNTAX TruthValue
--    Rsyntax INTEGER {
--        true(1),
--        false(2)
--        }
    ACCESS read-write
    STATUS mandatory
    DESCRIPTION
        "This variable indicates whether the system
         produces the ciscoEnvMonVoltStatusChangeNotif,
         ciscoEnvMonTempStatusChangeNotif, 
         ciscoEnvMonFanStatusChangeNotif and  
         ciscoEnvMonSuppStatusChangeNotif. A false value will 
         prevent these notifications from being generated by 
         this system."
    DEFVAL { false }
    ::= { ciscoEnvMonMIBNotificationEnables 6 }

ciscoEnvMonShutdownNotification TRAP-TYPE
-- Reverse mappable trap
    ENTERPRISE ciscoEnvMonMIBNotificationPrefix
--  Status
--    mandatory
    DESCRIPTION
        "A ciscoEnvMonShutdownNotification is sent if the environmental
        monitor detects a testpoint reaching a critical state
        and is about to initiate a shutdown.  This notification 
        contains no objects so that it may be encoded and sent in the
        shortest amount of time possible.  Even so, management
        applications should not rely on receiving such a notification
        as it may not be sent before the shutdown completes."
    ::= 1

ciscoEnvMonVoltageNotification TRAP-TYPE
-- Reverse mappable trap
    ENTERPRISE ciscoEnvMonMIBNotificationPrefix
    VARIABLES {
        ciscoEnvMonVoltageStatusDescr, 
        ciscoEnvMonVoltageStatusValue, ciscoEnvMonVoltageState }
--  Status
--    deprecated
    DESCRIPTION
        "A ciscoEnvMonVoltageNotification is sent if the voltage 
        measured at a given testpoint is outside the normal range 
        for the testpoint (i.e. is at the warning, critical, or
        shutdown stage).  Since such a notification is usually 
        generated before the shutdown state is reached, it can 
        convey more data and has a better chance of being sent 
        than does the ciscoEnvMonShutdownNotification.
        This notification is deprecated in favour of
        ciscoEnvMonVoltStatusChangeNotif."
    ::= 2

ciscoEnvMonTemperatureNotification TRAP-TYPE
-- Reverse mappable trap
    ENTERPRISE ciscoEnvMonMIBNotificationPrefix
    VARIABLES {
        ciscoEnvMonTemperatureStatusDescr, 
        ciscoEnvMonTemperatureStatusValue, 
        ciscoEnvMonTemperatureState }
--  Status
--    deprecated
    DESCRIPTION
        "A ciscoEnvMonTemperatureNotification is sent if the 
        temperature measured at a given testpoint is outside 
        the normal range for the testpoint (i.e. is at the warning, 
        critical, or shutdown stage).  Since such a Notification 
        is usually generated before the shutdown state is reached,
        it can convey more data and has a better chance of being
        sent than does the ciscoEnvMonShutdownNotification.
        This notification is deprecated in favour of 
        ciscoEnvMonTempStatusChangeNotif."
    ::= 3

ciscoEnvMonFanNotification TRAP-TYPE
-- Reverse mappable trap
    ENTERPRISE ciscoEnvMonMIBNotificationPrefix
    VARIABLES {
        ciscoEnvMonFanStatusDescr, ciscoEnvMonFanState }
--  Status
--    deprecated
    DESCRIPTION
        "A ciscoEnvMonFanNotification is sent if any one of
        the fans in the fan array (where extant) fails. 
        Since such a notification is usually generated before 
        the shutdown state is reached, it can convey more 
        data and has a better chance of being sent
        than does the ciscoEnvMonShutdownNotification.
        This notification is deprecated in favour of
        ciscoEnvMonFanStatusChangeNotif."
    ::= 4

ciscoEnvMonRedundantSupplyNotification TRAP-TYPE
-- Reverse mappable trap
    ENTERPRISE ciscoEnvMonMIBNotificationPrefix
    VARIABLES {
        ciscoEnvMonSupplyStatusDescr, ciscoEnvMonSupplyState }
--  Status
--    deprecated
    DESCRIPTION
        "A ciscoEnvMonRedundantSupplyNotification is sent if
        the redundant power supply (where extant) fails. 
        Since such a notification is usually generated before 
        the shutdown state is reached, it can convey more 
        data and has a better chance of being sent
        than does the ciscoEnvMonShutdownNotification.
        This notification is deprecated in favour of 
        ciscoEnvMonSuppStatusChangeNotif."
    ::= 5

ciscoEnvMonVoltStatusChangeNotif TRAP-TYPE
-- Reverse mappable trap
    ENTERPRISE ciscoEnvMonMIBNotificationPrefix
    VARIABLES {
        ciscoEnvMonVoltageStatusDescr, 
        ciscoEnvMonVoltageStatusValue, ciscoEnvMonVoltageState }
--  Status
--    mandatory
    DESCRIPTION
        "A ciscoEnvMonVoltStatusChangeNotif is sent if there is 
         change in the state of a device being monitored
         by ciscoEnvMonVoltageState."
    ::= 6

ciscoEnvMonTempStatusChangeNotif TRAP-TYPE
-- Reverse mappable trap
    ENTERPRISE ciscoEnvMonMIBNotificationPrefix
    VARIABLES {
        ciscoEnvMonTemperatureStatusDescr, 
        ciscoEnvMonTemperatureStatusValue, 
        ciscoEnvMonTemperatureState }
--  Status
--    mandatory
    DESCRIPTION
        "A ciscoEnvMonTempStatusChangeNotif is sent if there 
         is change in the state of a device being monitored
         by ciscoEnvMonTemperatureState."
    ::= 7

ciscoEnvMonFanStatusChangeNotif TRAP-TYPE
-- Reverse mappable trap
    ENTERPRISE ciscoEnvMonMIBNotificationPrefix
    VARIABLES {
        ciscoEnvMonFanStatusDescr, ciscoEnvMonFanState }
--  Status
--    mandatory
    DESCRIPTION
        "A ciscoEnvMonFanStatusChangeNotif is sent if there 
         is change in the state of a device being monitored
         by ciscoEnvMonFanState."
    ::= 8

ciscoEnvMonSuppStatusChangeNotif TRAP-TYPE
-- Reverse mappable trap
    ENTERPRISE ciscoEnvMonMIBNotificationPrefix
    VARIABLES {
        ciscoEnvMonSupplyStatusDescr, ciscoEnvMonSupplyState }
--  Status
--    mandatory
    DESCRIPTION
        "A ciscoEnvMonSupplyStatChangeNotif is sent if there 
         is change in the state of a device being monitored
         by ciscoEnvMonSupplyState."
    ::= 9

ciscoEnvMonMIBGroup OBJECT IDENTIFIER ::= { ciscoEnvMonMIBGroups 1 }
-- OBJECT-GROUP
--  Status
--    deprecated
--  Descr
--    A collection of objects providing environmental 
--    monitoring capability to a cisco chassis. This group 
--    is deprecated in favour of ciscoEnvMonMIBGroupRev.
--  objects
--    ciscoEnvMonPresent, ciscoEnvMonVoltageStatusDescr, 
--    ciscoEnvMonVoltageStatusValue, ciscoEnvMonVoltageThresholdLow, 
--    ciscoEnvMonVoltageThresholdHigh, 
--    ciscoEnvMonVoltageLastShutdown, ciscoEnvMonVoltageState, 
--    ciscoEnvMonTemperatureStatusDescr, 
--    ciscoEnvMonTemperatureStatusValue, 
--    ciscoEnvMonTemperatureThreshold, 
--    ciscoEnvMonTemperatureLastShutdown, 
--    ciscoEnvMonTemperatureState, ciscoEnvMonFanStatusDescr, 
--    ciscoEnvMonFanState, ciscoEnvMonSupplyStatusDescr, 
--    ciscoEnvMonSupplyState, ciscoEnvMonSupplySource, 
--    ciscoEnvMonAlarmContacts, 
--    ciscoEnvMonEnableShutdownNotification, 
--    ciscoEnvMonEnableVoltageNotification, 
--    ciscoEnvMonEnableTemperatureNotification, 
--    ciscoEnvMonEnableFanNotification, 
--    ciscoEnvMonEnableRedundantSupplyNotification

ciscoEnvMonMIBGroupRev OBJECT IDENTIFIER ::= { ciscoEnvMonMIBGroups 2 }
-- OBJECT-GROUP
--  Status
--    mandatory
--  Descr
--    A collection of objects providing environmental 
--     monitoring capability to a cisco chassis.
--  objects
--    ciscoEnvMonPresent, ciscoEnvMonVoltageStatusDescr, 
--    ciscoEnvMonVoltageStatusValue, ciscoEnvMonVoltageThresholdLow, 
--    ciscoEnvMonVoltageThresholdHigh, 
--    ciscoEnvMonVoltageLastShutdown, ciscoEnvMonVoltageState, 
--    ciscoEnvMonTemperatureStatusDescr, 
--    ciscoEnvMonTemperatureStatusValue, 
--    ciscoEnvMonTemperatureThreshold, 
--    ciscoEnvMonTemperatureLastShutdown, 
--    ciscoEnvMonTemperatureState, ciscoEnvMonFanStatusDescr, 
--    ciscoEnvMonFanState, ciscoEnvMonSupplyStatusDescr, 
--    ciscoEnvMonSupplyState, ciscoEnvMonSupplySource, 
--    ciscoEnvMonAlarmContacts, 
--    ciscoEnvMonEnableShutdownNotification

ciscoEnvMonEnableStatChangeGroup OBJECT IDENTIFIER ::= { ciscoEnvMonMIBGroups 3 }
-- OBJECT-GROUP
--  Status
--    mandatory
--  Descr
--    A collection of objects providing enabling/disabling
--     of the status change notifications for environmental 
--     monitoring.
--  objects
--    ciscoEnvMonEnableStatChangeNotif

ciscoEnvMonMIBNotifGroup OBJECT IDENTIFIER ::= { ciscoEnvMonMIBGroups 4 }
-- NOTIFICATION-GROUP
--  Status
--    mandatory
--  Descr
--    A notification group providing shutdown notification
--     for environmental monitoring. 
--  notifications
--    ciscoEnvMonShutdownNotification

ciscoEnvMonStatChangeNotifGroup OBJECT IDENTIFIER ::= { ciscoEnvMonMIBGroups 5 }
-- NOTIFICATION-GROUP
--  Status
--    mandatory
--  Descr
--    A collection of notifications providing the status 
--     change for environmental monitoring.
--  notifications
--    ciscoEnvMonVoltStatusChangeNotif, 
--    ciscoEnvMonTempStatusChangeNotif, 
--    ciscoEnvMonFanStatusChangeNotif, 
--    ciscoEnvMonSuppStatusChangeNotif

ciscoEnvMonMIBMiscNotifGroup OBJECT IDENTIFIER ::= { ciscoEnvMonMIBGroups 6 }
-- NOTIFICATION-GROUP
--  Status
--    deprecated
--  Descr
--    A collection of various notifications for the 
--    enviromental monitoring mib module. The notifications
--    the group and the group are both in deprecated state.
--    The notifications in the group were deprecated in 
--    favour of notifications in
--    ciscoEnvMonStatChangeNotifGroup.
--  notifications
--    ciscoEnvMonVoltageNotification, 
--    ciscoEnvMonTemperatureNotification, 
--    ciscoEnvMonFanNotification, 
--    ciscoEnvMonRedundantSupplyNotification

ciscoEnvMonMIBCompliance OBJECT IDENTIFIER ::= { ciscoEnvMonMIBCompliances 1 }
-- MODULE-COMPLIANCE
--  Status
--    deprecated
--  Descr
--    The compliance statement for entities which implement
--    the Cisco Environmental Monitor MIB. This is
--    deprecated and new compliance
--    ciscoEnvMonMIBComplianceRev1 is added.
--  Module
--    >>current<<
--   MandGroup
--    ciscoEnvMonMIBGroup

ciscoEnvMonMIBComplianceRev1 OBJECT IDENTIFIER ::= { ciscoEnvMonMIBCompliances 2 }
-- MODULE-COMPLIANCE
--  Status
--    mandatory
--  Descr
--    The compliance statement for entities which implement
--    the Cisco Environmental Monitor MIB.
--  Module
--    >>current<<
--   MandGroup
--    ciscoEnvMonMIBGroupRev
--   MandGroup
--    ciscoEnvMonMIBNotifGroup
--   OptGroup
--    ciscoEnvMonEnableStatChangeGroup
--   OptGroup
--    ciscoEnvMonStatChangeNotifGroup


END
