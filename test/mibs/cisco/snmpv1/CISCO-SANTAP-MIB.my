-- MIB file created 09-Mar-2005 00:46:18, by
--   SMICng version 2.2.11-beta(PRO)(Solaris), January 20, 2001. Enterprise key cisco.com

CISCO-SANTAP-MIB DEFINITIONS ::= BEGIN

-- From file: "CISCO-SANTAP-MIB.my"
-- Compile options "4 7 F H N O W 03 06 0B 0G 0N 0T"

IMPORTS
    RowStatus
            FROM SNMPv2-TC-v1
    ciscoMgmt
            FROM CISCO-SMI
    PhysicalIndex
            FROM ENTITY-MIB
    vsanIndex
            FROM CISCO-VSAN-MIB
    FcNameIdOrZero
            FROM CISCO-ST-TC
    OBJECT-TYPE
            FROM RFC-1212;

ciscoSanTapMIB OBJECT IDENTIFIER ::= { ciscoMgmt 463 }
-- MODULE-IDENTITY
--  LastUpdated
--    200502020000Z
--  OrgName
--    Cisco Systems Inc.
--  ContactInfo
--         Cisco Systems
--          Customer Service
--    Postal: 170 W Tasman Drive
--          San Jose, CA  95134
--          USA
--    Tel: +1 800 553 -NETS
--    E-mail: cs-san@cisco.com
--  Descr
--    MIB module to provide information about the SanTap 
--     service configuration.             
--    
--     SanTap is a fibre channel switch based capability that 
--     provides a reliable copy of the data flowing between 
--     a set of one or more initiators and a set of one or 
--     more targets connected to the fabric.
--    
--     Adminstrator must configure the switch to create the 
--     Control Virtual Target (CVT) for the SanTap service. 
--     CVTs are used to implement the control path which process 
--     all SanTap service requests sent out by an appliance. 
--    
--     Prior to requesting for SanTap service the appliance 
--     contacts the CVT, specifies the initiator and the target 
--     for replicating the data flowing between them.
--          
--     This MIB provides an interface to configure the CVT for 
--     the SanTap service on the fibre channel switch modules.
--    
--     Glossary of terms used in this MIB:
--    
--     Fabric - The set of physically connected fibre channel
--              switches.
--    
--     VSAN - Virtual Storage Area Network, similar to a 
--            Virtual Fabric as defined by T11. 
--    
--     WWN  - World Wide Name. Mechanism of uniquely 
--            identifying the devices in Fibre Channel 
--            Networks. 
--    
--     Appliance - It is a storage target, which can  
--            requests the SanTap service for the reliable 
--            copy of the data flowing between a specific 
--            host initiator and a target. 
--    
--     CVT  - Control Virtual Target. It is a logical target 
--            port that resides on the switch and is used 
--            for the purpose of communicating control traffic 
--            from an appliance.
--  RevDate
--    200502020000Z
--  RevDescr
--    Initial version of this MIB.

ciscoSanTapMIBObjects OBJECT IDENTIFIER ::= { ciscoSanTapMIB 1 }
ciscoSanTapMIBConformance OBJECT IDENTIFIER ::= { ciscoSanTapMIB 2 }
ciscoSanTapNotifications OBJECT IDENTIFIER ::= { ciscoSanTapMIB 3 }
ciscoSanTapMIBCompliances OBJECT IDENTIFIER ::= { ciscoSanTapMIBConformance 1 }
ciscoSanTapMIBGroups OBJECT IDENTIFIER ::= { ciscoSanTapMIBConformance 2 }

cstModuleTable OBJECT-TYPE
    SYNTAX SEQUENCE OF CstModuleEntry
    ACCESS not-accessible
    STATUS mandatory
    DESCRIPTION
        "A table listing the modules on which SanTap service can 
         be configured and CVT can be created by the user.
        
         The entry in the cstServiceConfigTable can only be 
         created on a module present in the cstModuleTable."
    ::= { ciscoSanTapMIBObjects 1 }

cstModuleEntry OBJECT-TYPE
    SYNTAX CstModuleEntry
    ACCESS not-accessible
    STATUS mandatory
    DESCRIPTION
        "An entry in this table.
         The cstModuleId denotes the entPhysicalIndex of the
         module on which SanTap service can be configured."
    INDEX { cstModuleId }
    ::= { cstModuleTable 1 }

CstModuleEntry ::= SEQUENCE {
    cstModuleId PhysicalIndex
    }

cstModuleId OBJECT-TYPE
    SYNTAX PhysicalIndex
--    Rsyntax INTEGER(1..2147483647)
    ACCESS read-only
    STATUS mandatory
    DESCRIPTION
        "This object specifies the physical index of the entity  
         with entPhysicalClass as 'module' on which SanTap service 
         can be configured by the user.
         This is same as the entPhysicalIndex of the module."
    ::= { cstModuleEntry 1 }

cstServiceConfigTable OBJECT-TYPE
    SYNTAX SEQUENCE OF CstServiceConfigEntry
    ACCESS not-accessible
    STATUS mandatory
    DESCRIPTION
        "This table provides information about the list of 
         all CVTs created and configured in the system. 
        
         A new entry creation in this table, creates a CVT on the 
         module specified by the corresponding instance index 
         'cstModuleId' and configures the CVT on the VSAN 
         specified by the corresponding instance index 'vsanIndex'.
        
         A row creation in this table, with an existing 
         module physical index  but different 'vsanIndex' 
         configures the already created CVT on the module into
         VSAN specified by the 'vsanIndex'.
        
         Deleting an entry from this table, unconfigures the
         CVT created on the module specified by the corresponding 
         instance index 'cstModuleId' on the VSAN represented 
         by the corresponding instance index 'vsanIndex'. If there 
         are no more entries in this table for this module then
         the CVT will be deleted from the corresponding module.
        
         For example, If there is no entry in this table for a
         module pysical Index '22', then a new entry creation 
         with cstModuleId '22' vsanIndex 'n1' creates a
         CVT on this module and configures the CVT on VSAN 'n1'.
         And a new row is created in this table.
        
         Any subsequent entry creation with cstModuleId '22'
         vsanIndex 'n2' only configures the previously created 
         CVT on vsan 'n2' and a new row is created in this table.
        
         Similarly for any delete request with cstModuleId '22'
         vsanIndex 'n1'/'n2' unconfigures the CVT created on the 
         vsan 'n1'/'n2' and the corresponding row is deleted from 
         the table. 
        
         If there is only one entry with cstModuleId '22' 
         and vsan 'n' exists in the table, then any delete request  
         with cstModuleId '22' vsan 'n' unconfigures the CVT on 
         vsan 'n' and deletes the CVT. The corresponding row is 
         deleted from the table."
    ::= { ciscoSanTapMIBObjects 2 }

cstServiceConfigEntry OBJECT-TYPE
    SYNTAX CstServiceConfigEntry
    ACCESS not-accessible
    STATUS mandatory
    DESCRIPTION
        "An entry containing information about a CVT configuration
         for the SanTap service.
        
         The 'cstModuleId' denotes the module on which the user 
         wants the SanTap service to be configured and the CVT to be
         created.  
        
         The index 'vsanIndex' represents the VSAN on which the
         CVT needs to be configured. It represents the VSAN on 
         which CVT and the appliance communicate to establish the 
         control path for processing the SanTap service requests."
    INDEX { cstModuleId, vsanIndex }
    ::= { cstServiceConfigTable 1 }

CstServiceConfigEntry ::= SEQUENCE {
    cstCVTNodeWwn FcNameIdOrZero,
    cstCVTPortWwn FcNameIdOrZero,
    cstServiceConfigRowStatus RowStatus
    }

cstCVTNodeWwn OBJECT-TYPE
    SYNTAX FcNameIdOrZero
--    Rsyntax OCTET STRING(SIZE(0|8|16))
    ACCESS read-only
    STATUS mandatory
    DESCRIPTION
        "This object represents the Node World-Wide Name of the 
         CVT created on the module represented by the corresponding 
         entity index 'cstModuleId'."
    ::= { cstServiceConfigEntry 1 }

cstCVTPortWwn OBJECT-TYPE
    SYNTAX FcNameIdOrZero
--    Rsyntax OCTET STRING(SIZE(0|8|16))
    ACCESS read-only
    STATUS mandatory
    DESCRIPTION
        "This object represents the Port World-Wide Name of the 
         CVT created on the module represented by the corresponding 
         entity index 'cstModuleId'."
    ::= { cstServiceConfigEntry 2 }

cstServiceConfigRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this conceptual row."
    ::= { cstServiceConfigEntry 3 }

ciscoSanTapServiceConfigGroup OBJECT IDENTIFIER ::= { ciscoSanTapMIBGroups 1 }
-- OBJECT-GROUP
--  Status
--    mandatory
--  Descr
--    A Collection of objects to configure the CVT for SanTap
--     service.
--  objects
--    cstModuleId, cstCVTNodeWwn, cstCVTPortWwn, 
--    cstServiceConfigRowStatus

ciscoSanTapMIBCompliance OBJECT IDENTIFIER ::= { ciscoSanTapMIBCompliances 1 }
-- MODULE-COMPLIANCE
--  Status
--    mandatory
--  Descr
--    Compliance statement for entites which implement 
--     the CISCO SANTAP MIB.
--  Module
--    >>current<<
--   MandGroup
--    ciscoSanTapServiceConfigGroup
--   ObjVar
--    cstServiceConfigRowStatus


END
