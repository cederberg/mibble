-- MIB file created 01-Jan-2006 23:47:49, by
--   SMICng version 2.2.11-beta(PRO)(Solaris), January 20, 2001. Enterprise key cisco.com

CISCO-SNMP-TARGET-EXT-MIB DEFINITIONS ::= BEGIN

-- From file: "CISCO-SNMP-TARGET-EXT-MIB.my"
-- Compile options "4 7 F H N O W 03 06 0B 0G 0N 0T"

IMPORTS
    InterfaceIndexOrZero
            FROM IF-MIB
    ciscoMgmt
            FROM CISCO-SMI
    InetAddressType, InetAddress
            FROM INET-ADDRESS-MIB
    snmpTargetAddrName
            FROM SNMP-TARGET-MIB
    OBJECT-TYPE
            FROM RFC-1212;

ciscoSnmpTargetExtMIB OBJECT IDENTIFIER ::= { ciscoMgmt 412 }
-- MODULE-IDENTITY
--  LastUpdated
--    200404010000Z
--  OrgName
--    Cisco Systems, Inc.
--  ContactInfo
--    Cisco Systems
--     Customer Service
--    
--    Postal: 170 W. Tasman Drive
--     San Jose, CA 95134
--     USA
--    
--    Tel: +1 800 553-NETS
--    
--    E-mail: cs-snmp@cisco.com
--  Descr
--    This MIB is an extension of the SNMP-TARGET-MIB
--    specified in RFC2273.
--    
--    This MIB module contains  Cisco-defined  extension
--    to the snmpTargetAddrTable to represent infomation
--    required for IPv6 Address. 
--    
--    When Target has Link local or Multicast IPv6 address,
--    the information of the interface on which the
--    notification has to be sent is required. This
--    additional information is provided by this extension
--    MIB.
--    
--    This module also contains defination for set of new
--    variable to hold the address of the host that had
--    sent an unauthentic SNMP message to agent.
--  RevDate
--    200404010000Z
--  RevDescr
--    Initial version of this MIB module.

ciscoSnmpTargetExtMIBObjects OBJECT IDENTIFIER ::= { ciscoSnmpTargetExtMIB 1 }
cExtSnmpTargetAuthAddr OBJECT IDENTIFIER ::= { ciscoSnmpTargetExtMIBObjects 1 }
ciscoSnmpTargetExtMIBConformance OBJECT IDENTIFIER ::= { ciscoSnmpTargetExtMIB 2 }
ciscoSnmpTargetExtMIBCompliances OBJECT IDENTIFIER ::= { ciscoSnmpTargetExtMIBConformance 1 }
ciscoSnmpTargetExtMIBGroups OBJECT IDENTIFIER ::= { ciscoSnmpTargetExtMIBConformance 2 }

cExtSnmpTargetAuthInetType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This contains the type of address
         cExtSnmpTargetAuthInetAddr holds when a host sends an
         unauthentic SNMP message."
    ::= { cExtSnmpTargetAuthAddr 1 }

cExtSnmpTargetAuthInetAddr OBJECT-TYPE
    SYNTAX InetAddress
--    Rsyntax OCTET STRING(SIZE(0..255))
    ACCESS read-only
    STATUS mandatory
    DESCRIPTION
        "This contains the address of the host from which
         snmp-agent has received a SNMP message that is not
         authentic."
    ::= { cExtSnmpTargetAuthAddr 2 }

cExtSnmpTargetAddrTable OBJECT-TYPE
    SYNTAX SEQUENCE OF CExtSnmpTargetAddrEntry
    ACCESS not-accessible
    STATUS mandatory
    DESCRIPTION
        "The cExtSnmpTargetAddrTable extends
         the SNMP-TARGET-MIB's snmpTargetAddrTable for providing
                info on the type of interface for Link Local or Multicast
                IPv6 Target Address."
    REFERENCE
        "RFC2737: Section 4.1"
    ::= { ciscoSnmpTargetExtMIBObjects 2 }

cExtSnmpTargetAddrEntry OBJECT-TYPE
    SYNTAX CExtSnmpTargetAddrEntry
    ACCESS not-accessible
    STATUS mandatory
    DESCRIPTION
        "A cExtSnmpTargetAddrTable entry extends 
        snmpTargetAddrTable to provide a new variable
         to hold the value of interface type.
        
         A target which has a link local or a multicast
         address the variable of this table is valid.
         Entries are removed when the corresponding entry in the
         snmpTargetAddrTable is removed."
    INDEX { --?? IMPLIED may cause problems
            IMPLIED snmpTargetAddrName }
-- Augments snmpTargetAddrEntry FROM SNMP-TARGET-MIB
    ::= { cExtSnmpTargetAddrTable 1 }

CExtSnmpTargetAddrEntry ::= SEQUENCE {
    cExtSnmpTargetAddrIntIfIndex InterfaceIndexOrZero
    }

cExtSnmpTargetAddrIntIfIndex OBJECT-TYPE
    SYNTAX InterfaceIndexOrZero
--    Rsyntax INTEGER(0..2147483647)
    ACCESS read-write
    STATUS mandatory
    DESCRIPTION
        "Holds valid ifIndex value of the interface through
        which the notifications for the target with
        Multicast/Link local address specified in the
        snmpTargetAddrTAddress, is sent.  
        
        If snmpTargetAddrTAddress doesn't hold a Linklocal or
        a Multicast target address then the value of this
        object will be zero.
        
        For the entries with snmpTargetAddrTAddress having
        Link Local or Multicast address the
        snmpTargetAddrStatus cannot be set to valid unless the
        value for this object holds a valid ifIndex value."
    ::= { cExtSnmpTargetAddrEntry 1 }

ciscoSnmpTargetAuthFailureGroup OBJECT IDENTIFIER ::= { ciscoSnmpTargetExtMIBGroups 1 }
-- OBJECT-GROUP
--  Status
--    mandatory
--  Descr
--    The collection of objects which gives information about
--     the recent host that has sent a SNMP message to the agent 
--     that is not authentic
--  objects
--    cExtSnmpTargetAuthInetType, cExtSnmpTargetAuthInetAddr

ciscoSnmpTargetExtMIBGroup OBJECT IDENTIFIER ::= { ciscoSnmpTargetExtMIBGroups 2 }
-- OBJECT-GROUP
--  Status
--    mandatory
--  Descr
--    The collection of objects which give information about
--    the interface through which the notifications are sent
--    out for IPv6 Link-local and Multicast Target address.
--  objects
--    cExtSnmpTargetAddrIntIfIndex

ciscoSnmpTargetExtMIBCompliance OBJECT IDENTIFIER ::= { ciscoSnmpTargetExtMIBCompliances 1 }
-- MODULE-COMPLIANCE
--  Status
--    mandatory
--  Descr
--    Compliance for IPv6 address supported by
--     snmpTargetAddrTAddress for Link-Local or Multicast and
--     for holding the recent host address that sent an
--     unauthentic SNMP message in cExtSnmpTargetAuthInetAddr
--     and cExtSnmpTargetAuthInetType.
--  Module
--    >>current<<
--   MandGroup
--    ciscoSnmpTargetExtMIBGroup
--   OptGroup
--    ciscoSnmpTargetAuthFailureGroup


END
