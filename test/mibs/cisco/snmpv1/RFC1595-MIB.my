-- MIB file created 21-Jun-2001 14:43:33, by
--   SMICng version 2.2.11-beta(PRO)(Solaris), January 20, 2001. Enterprise key cisco.com

SONET-MIB DEFINITIONS ::= BEGIN

-- From file: "RFC1595-MIB.my"
-- Compile options "4 7 F H N W 03 06 0B 0G 0N 0T"

IMPORTS
    DisplayString
            FROM SNMPv2-TC-v1
    ifIndex, transmission
            FROM RFC1213-MIB
    Gauge
            FROM RFC1155-SMI
    OBJECT-TYPE
            FROM RFC-1212;

sonetMIB OBJECT IDENTIFIER ::= { transmission 39 }
-- MODULE-IDENTITY
--  LastUpdated
--    9401030000Z
--  OrgName
--    IETF AToM MIB Working Group
--  ContactInfo
--            Tracy Brown
--    
--     Postal: Bell Communications Research
--             331 Newman Springs Road
--             P.O. Box 7020
--             Red Bank, NJ  07701-7020
--             US
--    
--        Tel: +1 908 758 2107
--        Fax: +1 908 758 4177
--    
--     E-mail: tacox@mail.bellcore.com
--    
--    
--             Kaj Tesink
--    
--     Postal: Bell Communications Research
--             331 Newman Springs Road
--             P.O. Box 7020
--             Red Bank, NJ  07701-7020
--             US
--    
--        Tel: +1 908 758 5254
--        Fax: +1 908 758 4196
--    
--     E-mail: kaj@cc.bellcore.com
--  Descr
--    The MIB module to describe
--    SONET/SDH interfaces objects.

sonetObjects    OBJECT IDENTIFIER ::= { sonetMIB 1 }
sonetObjectsPath OBJECT IDENTIFIER ::= { sonetMIB 2 }
sonetObjectsVT  OBJECT IDENTIFIER ::= { sonetMIB 3 }
sonetMedium     OBJECT IDENTIFIER ::= { sonetObjects 1 }
sonetSection    OBJECT IDENTIFIER ::= { sonetObjects 2 }
sonetLine       OBJECT IDENTIFIER ::= { sonetObjects 3 }
sonetFarEndLine OBJECT IDENTIFIER ::= { sonetObjects 4 }
sonetPath       OBJECT IDENTIFIER ::= { sonetObjectsPath 1 }
sonetFarEndPath OBJECT IDENTIFIER ::= { sonetObjectsPath 2 }
sonetVT         OBJECT IDENTIFIER ::= { sonetObjectsVT 1 }
sonetFarEndVT   OBJECT IDENTIFIER ::= { sonetObjectsVT 2 }
sonetConformance OBJECT IDENTIFIER ::= { sonetMIB 4 }
sonetGroups     OBJECT IDENTIFIER ::= { sonetConformance 1 }
sonetCompliances OBJECT IDENTIFIER ::= { sonetConformance 2 }

sonetMediumTable OBJECT-TYPE
    SYNTAX SEQUENCE OF SonetMediumEntry
    ACCESS not-accessible
    STATUS mandatory
    DESCRIPTION
        "The SONET/SDH Medium table."
    ::= { sonetMedium 1 }

sonetMediumEntry OBJECT-TYPE
    SYNTAX SonetMediumEntry
    ACCESS not-accessible
    STATUS mandatory
    DESCRIPTION
        "An entry in the SONET/SDH Medium table."
    INDEX { ifIndex }
    ::= { sonetMediumTable 1 }

SonetMediumEntry ::= SEQUENCE {
    sonetMediumType INTEGER,
    sonetMediumTimeElapsed INTEGER,
    sonetMediumValidIntervals INTEGER,
    sonetMediumLineCoding INTEGER,
    sonetMediumLineType INTEGER,
    sonetMediumCircuitIdentifier DisplayString
    }

sonetMediumType OBJECT-TYPE
    SYNTAX INTEGER {
        sonet(1),
        sdh(2)
        }
    ACCESS read-only
    STATUS mandatory
    DESCRIPTION
        "This variable identifies whether a SONET
        or a SDH signal is used across this interface."
    ::= { sonetMediumEntry 1 }

sonetMediumTimeElapsed OBJECT-TYPE
    SYNTAX INTEGER(1..900)
    ACCESS read-only
    STATUS mandatory
    DESCRIPTION
        "The number of seconds, including partial
        seconds, that have elapsed since the beginning of
        the current error-measurement period."
    ::= { sonetMediumEntry 2 }

sonetMediumValidIntervals OBJECT-TYPE
    SYNTAX INTEGER(0..96)
    ACCESS read-only
    STATUS mandatory
    DESCRIPTION
        "The number of previous intervals for which valid
        data has been stored.  A SONET device must support
        at least n intervals.
        The minimum value of n is 4.
        The default of n is 32.
        The maximum value of n is 96.
        The value of this object will be n unless
        the device was brought online within the last
        (nx15) minutes, in which case the value will be the
        number of complete 15 minute intervals the device has
        been online."
    ::= { sonetMediumEntry 3 }

sonetMediumLineCoding OBJECT-TYPE
    SYNTAX INTEGER {
        sonetMediumOther(1),
        sonetMediumB3ZS(2),
        sonetMediumCMI(3),
        sonetMediumNRZ(4),
        sonetMediumRZ(5)
        }
    ACCESS read-only
    STATUS mandatory
    DESCRIPTION
        "This variable describes the line coding for
        this interface. The B3ZS and CMI are used for
        electrical SONET/SDH signals (STS-1 and STS-3).
        The Non-Return to Zero (NRZ) and the Return
        to Zero are used for optical SONET/SDH signals."
    ::= { sonetMediumEntry 4 }

sonetMediumLineType OBJECT-TYPE
    SYNTAX INTEGER {
        sonetOther(1),
        sonetShortSingleMode(2),
        sonetLongSingleMode(3),
        sonetMultiMode(4),
        sonetCoax(5),
        sonetUTP(6)
        }
    ACCESS read-only
    STATUS mandatory
    DESCRIPTION
        "This variable describes the line type for
        this interface. The line types are
        Short and Long Range
        Single Mode fiber or Multi-Mode fiber interfaces,
        and coax and UTP for electrical interfaces.  The
        value sonetOther should be used when the Line Type is
        not one of the listed values."
    ::= { sonetMediumEntry 5 }

sonetMediumCircuitIdentifier OBJECT-TYPE
    SYNTAX DisplayString(SIZE(0..255))
--    Rsyntax OCTET STRING(SIZE(0..255))
    ACCESS read-only
    STATUS mandatory
    DESCRIPTION
        "This variable contains the transmission
        vendor's circuit identifier, for the
        purpose of facilitating troubleshooting."
    ::= { sonetMediumEntry 6 }

sonetSectionCurrentTable OBJECT-TYPE
    SYNTAX SEQUENCE OF SonetSectionCurrentEntry
    ACCESS not-accessible
    STATUS mandatory
    DESCRIPTION
        "The SONET/SDH Section Current table."
    ::= { sonetSection 1 }

sonetSectionCurrentEntry OBJECT-TYPE
    SYNTAX SonetSectionCurrentEntry
    ACCESS not-accessible
    STATUS mandatory
    DESCRIPTION
        "An entry in the SONET/SDH Section Current table."
    INDEX { ifIndex }
    ::= { sonetSectionCurrentTable 1 }

SonetSectionCurrentEntry ::= SEQUENCE {
    sonetSectionCurrentStatus INTEGER,
    sonetSectionCurrentESs Gauge,
    sonetSectionCurrentSESs Gauge,
    sonetSectionCurrentSEFSs Gauge,
    sonetSectionCurrentCVs Gauge
    }

sonetSectionCurrentStatus OBJECT-TYPE
    SYNTAX INTEGER(1..6)
    ACCESS read-only
    STATUS mandatory
    DESCRIPTION
        "This variable indicates the
        status of the interface.
        The sonetSectionCurrentStatus
        is a bit map represented
        as a sum, therefore,
        it can represent multiple defects
        simultaneously.
        The sonetSectionNoDefect should be
        set if and only if
        no other flag is set.
        
        The various bit positions are:
              1   sonetSectionNoDefect
              2   sonetSectionLOS
              4   sonetSectionLOF"
    ::= { sonetSectionCurrentEntry 1 }

sonetSectionCurrentESs OBJECT-TYPE
    SYNTAX Gauge
    ACCESS read-only
    STATUS mandatory
    DESCRIPTION
        "The counter associated with the number of Errored
        Seconds encountered by a SONET/SDH
        Section in the current 15 minute interval."
    ::= { sonetSectionCurrentEntry 2 }

sonetSectionCurrentSESs OBJECT-TYPE
    SYNTAX Gauge
    ACCESS read-only
    STATUS mandatory
    DESCRIPTION
        "The counter associated with the number of
        Severely Errored Seconds
        encountered by a SONET/SDH Section in the current 15
        minute interval."
    ::= { sonetSectionCurrentEntry 3 }

sonetSectionCurrentSEFSs OBJECT-TYPE
    SYNTAX Gauge
    ACCESS read-only
    STATUS mandatory
    DESCRIPTION
        "The counter associated with the number of
        Severely Errored Framing Seconds
        encountered by a SONET/SDH Section in the current
        15 minute interval."
    ::= { sonetSectionCurrentEntry 4 }

sonetSectionCurrentCVs OBJECT-TYPE
    SYNTAX Gauge
    ACCESS read-only
    STATUS mandatory
    DESCRIPTION
        "The counter associated with the number of Coding
        Violations encountered by a
        SONET/SDH Section in the current 15 minute interval."
    ::= { sonetSectionCurrentEntry 5 }

sonetSectionIntervalTable OBJECT-TYPE
    SYNTAX SEQUENCE OF SonetSectionIntervalEntry
    ACCESS not-accessible
    STATUS mandatory
    DESCRIPTION
        "The SONET/SDH Section Interval table."
    ::= { sonetSection 2 }

sonetSectionIntervalEntry OBJECT-TYPE
    SYNTAX SonetSectionIntervalEntry
    ACCESS not-accessible
    STATUS mandatory
    DESCRIPTION
        "An entry in the SONET/SDH Section Interval table."
    INDEX { ifIndex, sonetSectionIntervalNumber }
    ::= { sonetSectionIntervalTable 1 }

SonetSectionIntervalEntry ::= SEQUENCE {
    sonetSectionIntervalNumber INTEGER,
    sonetSectionIntervalESs Gauge,
    sonetSectionIntervalSESs Gauge,
    sonetSectionIntervalSEFSs Gauge,
    sonetSectionIntervalCVs Gauge
    }

sonetSectionIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetSectionIntervalEntry 1 }

sonetSectionIntervalESs OBJECT-TYPE
    SYNTAX Gauge
    ACCESS read-only
    STATUS mandatory
    DESCRIPTION
        "The counter associated with the number of
        Errored Seconds encountered
        by a SONET/SDH Section in a
        particular 15-minute interval
        in the past 24 hours."
    ::= { sonetSectionIntervalEntry 2 }

sonetSectionIntervalSESs OBJECT-TYPE
    SYNTAX Gauge
    ACCESS read-only
    STATUS mandatory
    DESCRIPTION
        "The counter associated with the number of
        Severely Errored Seconds
        encountered by a SONET/SDH Section in a
        particular 15-minute interval
        in the past 24 hours."
    ::= { sonetSectionIntervalEntry 3 }

sonetSectionIntervalSEFSs OBJECT-TYPE
    SYNTAX Gauge
    ACCESS read-only
    STATUS mandatory
    DESCRIPTION
        "The counter associated with the number of
        Severely Errored Framing Seconds
        encountered by a SONET/SDH Section in a
        particular 15-minute interval
        in the past 24 hours."
    ::= { sonetSectionIntervalEntry 4 }

sonetSectionIntervalCVs OBJECT-TYPE
    SYNTAX Gauge
    ACCESS read-only
    STATUS mandatory
    DESCRIPTION
        "The counter associated with the number of Coding
        Violations encountered by a
        SONET/SDH Section in a particular 15-minute interval
        in the past 24 hours."
    ::= { sonetSectionIntervalEntry 5 }

sonetLineCurrentTable OBJECT-TYPE
    SYNTAX SEQUENCE OF SonetLineCurrentEntry
    ACCESS not-accessible
    STATUS mandatory
    DESCRIPTION
        "The SONET/SDH Line Current table."
    ::= { sonetLine 1 }

sonetLineCurrentEntry OBJECT-TYPE
    SYNTAX SonetLineCurrentEntry
    ACCESS not-accessible
    STATUS mandatory
    DESCRIPTION
        "An entry in the SONET/SDH Line Current table."
    INDEX { ifIndex }
    ::= { sonetLineCurrentTable 1 }

SonetLineCurrentEntry ::= SEQUENCE {
    sonetLineCurrentStatus INTEGER,
    sonetLineCurrentESs Gauge,
    sonetLineCurrentSESs Gauge,
    sonetLineCurrentCVs Gauge,
    sonetLineCurrentUASs Gauge
    }

sonetLineCurrentStatus OBJECT-TYPE
    SYNTAX INTEGER(1..6)
    ACCESS read-only
    STATUS mandatory
    DESCRIPTION
        "This variable indicates the
        status of the interface.
        The sonetLineCurrentStatus
        is a bit map represented
        as a sum, therefore,
        it can represent multiple defects
        simultaneously.
        The sonetLineNoDefect should be
        set if and only if
        no other flag is set.
        
        The various bit positions are:
         1   sonetLineNoDefect
         2   sonetLineAIS
         4   sonetLineRDI"
    ::= { sonetLineCurrentEntry 1 }

sonetLineCurrentESs OBJECT-TYPE
    SYNTAX Gauge
    ACCESS read-only
    STATUS mandatory
    DESCRIPTION
        "The counter associated with the number of Errored
        Seconds encountered by a SONET/SDH
        Line in the current 15 minute interval."
    ::= { sonetLineCurrentEntry 2 }

sonetLineCurrentSESs OBJECT-TYPE
    SYNTAX Gauge
    ACCESS read-only
    STATUS mandatory
    DESCRIPTION
        "The counter associated with the number of
        Severely Errored Seconds
        encountered by a SONET/SDH Line in the current 15
        minute
        interval."
    ::= { sonetLineCurrentEntry 3 }

sonetLineCurrentCVs OBJECT-TYPE
    SYNTAX Gauge
    ACCESS read-only
    STATUS mandatory
    DESCRIPTION
        "The counter associated with the number of Coding
        Violations encountered by a
        SONET/SDH Line in the current 15 minute interval."
    ::= { sonetLineCurrentEntry 4 }

sonetLineCurrentUASs OBJECT-TYPE
    SYNTAX Gauge
    ACCESS read-only
    STATUS mandatory
    DESCRIPTION
        "The counter associated with the number of
        Unavailable Seconds
        encountered by a SONET/SDH Line in the current 15
        minute
        interval."
    ::= { sonetLineCurrentEntry 5 }

sonetLineIntervalTable OBJECT-TYPE
    SYNTAX SEQUENCE OF SonetLineIntervalEntry
    ACCESS not-accessible
    STATUS mandatory
    DESCRIPTION
        "The SONET/SDH Line Interval table."
    ::= { sonetLine 2 }

sonetLineIntervalEntry OBJECT-TYPE
    SYNTAX SonetLineIntervalEntry
    ACCESS not-accessible
    STATUS mandatory
    DESCRIPTION
        "An entry in the SONET/SDH Line Interval table."
    INDEX { ifIndex, sonetLineIntervalNumber }
    ::= { sonetLineIntervalTable 1 }

SonetLineIntervalEntry ::= SEQUENCE {
    sonetLineIntervalNumber INTEGER,
    sonetLineIntervalESs Gauge,
    sonetLineIntervalSESs Gauge,
    sonetLineIntervalCVs Gauge,
    sonetLineIntervalUASs Gauge
    }

sonetLineIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetLineIntervalEntry 1 }

sonetLineIntervalESs OBJECT-TYPE
    SYNTAX Gauge
    ACCESS read-only
    STATUS mandatory
    DESCRIPTION
        "The counter associated with the number of
        Errored Seconds encountered
        by a SONET/SDH Line in a
        particular 15-minute interval
        in the past 24 hours."
    ::= { sonetLineIntervalEntry 2 }

sonetLineIntervalSESs OBJECT-TYPE
    SYNTAX Gauge
    ACCESS read-only
    STATUS mandatory
    DESCRIPTION
        "The counter associated with the number of
        Severely Errored Seconds
        encountered by a SONET/SDH Line in a
        particular 15-minute interval
        in the past 24 hours."
    ::= { sonetLineIntervalEntry 3 }

sonetLineIntervalCVs OBJECT-TYPE
    SYNTAX Gauge
    ACCESS read-only
    STATUS mandatory
    DESCRIPTION
        "The counter associated with the number of Coding
        Violations encountered by a
        SONET/SDH Line in a
        particular 15-minute interval
        in the past 24 hours."
    ::= { sonetLineIntervalEntry 4 }

sonetLineIntervalUASs OBJECT-TYPE
    SYNTAX Gauge
    ACCESS read-only
    STATUS mandatory
    DESCRIPTION
        "The counter associated with the
        number of Unavailable Seconds
        encountered by a SONET/SDH Line in
        a particular 15-minute interval
        in the past 24 hours."
    ::= { sonetLineIntervalEntry 5 }

sonetFarEndLineCurrentTable OBJECT-TYPE
    SYNTAX SEQUENCE OF SonetFarEndLineCurrentEntry
    ACCESS not-accessible
    STATUS mandatory
    DESCRIPTION
        "The SONET/SDH Far End Line Current table."
    ::= { sonetFarEndLine 1 }

sonetFarEndLineCurrentEntry OBJECT-TYPE
    SYNTAX SonetFarEndLineCurrentEntry
    ACCESS not-accessible
    STATUS mandatory
    DESCRIPTION
        "An entry in the SONET/SDH Far End Line Current table."
    INDEX { ifIndex }
    ::= { sonetFarEndLineCurrentTable 1 }

SonetFarEndLineCurrentEntry ::= SEQUENCE {
    sonetFarEndLineCurrentESs Gauge,
    sonetFarEndLineCurrentSESs Gauge,
    sonetFarEndLineCurrentCVs Gauge,
    sonetFarEndLineCurrentUASs Gauge
    }

sonetFarEndLineCurrentESs OBJECT-TYPE
    SYNTAX Gauge
    ACCESS read-only
    STATUS mandatory
    DESCRIPTION
        "The counter associated with the number of Far
        Far End Errored Seconds encountered by a SONET/SDH
        interface in the current 15 minute interval."
    ::= { sonetFarEndLineCurrentEntry 1 }

sonetFarEndLineCurrentSESs OBJECT-TYPE
    SYNTAX Gauge
    ACCESS read-only
    STATUS mandatory
    DESCRIPTION
        "The counter associated with the number of
        Far End Severely Errored Seconds
        encountered by a SONET/SDH Medium/Section/Line
        interface in the current 15 minute
        interval."
    ::= { sonetFarEndLineCurrentEntry 2 }

sonetFarEndLineCurrentCVs OBJECT-TYPE
    SYNTAX Gauge
    ACCESS read-only
    STATUS mandatory
    DESCRIPTION
        "The counter associated with the number of
        Far End Coding Violations reported via
        the far end block error count
        encountered by a
        SONET/SDH Medium/Section/Line
        interface in the current 15 minute interval."
    ::= { sonetFarEndLineCurrentEntry 3 }

sonetFarEndLineCurrentUASs OBJECT-TYPE
    SYNTAX Gauge
    ACCESS read-only
    STATUS mandatory
    DESCRIPTION
        "The counter associated with the number of
        Far End Unavailable Seconds
        encountered by a
        SONET/SDH Medium/Section/Line
        interface in the current 15 minute interval."
    ::= { sonetFarEndLineCurrentEntry 4 }

sonetFarEndLineIntervalTable OBJECT-TYPE
    SYNTAX SEQUENCE OF SonetFarEndLineIntervalEntry
    ACCESS not-accessible
    STATUS mandatory
    DESCRIPTION
        "The SONET/SDH Far End Line Interval table."
    ::= { sonetFarEndLine 2 }

sonetFarEndLineIntervalEntry OBJECT-TYPE
    SYNTAX SonetFarEndLineIntervalEntry
    ACCESS not-accessible
    STATUS mandatory
    DESCRIPTION
        "An entry in the SONET/SDH Far
        End Line Interval table."
    INDEX { ifIndex, sonetFarEndLineIntervalNumber }
    ::= { sonetFarEndLineIntervalTable 1 }

SonetFarEndLineIntervalEntry ::= SEQUENCE {
    sonetFarEndLineIntervalNumber INTEGER,
    sonetFarEndLineIntervalESs Gauge,
    sonetFarEndLineIntervalSESs Gauge,
    sonetFarEndLineIntervalCVs Gauge,
    sonetFarEndLineIntervalUASs Gauge
    }

sonetFarEndLineIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetFarEndLineIntervalEntry 1 }

sonetFarEndLineIntervalESs OBJECT-TYPE
    SYNTAX Gauge
    ACCESS read-only
    STATUS mandatory
    DESCRIPTION
        "The counter associated with the number of
        Far End Errored Seconds encountered
        by a SONET/SDH Line
        interface in a particular 15-minute interval
        in the past 24 hours."
    ::= { sonetFarEndLineIntervalEntry 2 }

sonetFarEndLineIntervalSESs OBJECT-TYPE
    SYNTAX Gauge
    ACCESS read-only
    STATUS mandatory
    DESCRIPTION
        "The counter associated with the number of
        Far End Severely Errored Seconds
        encountered by a SONET/SDH Line
        interface in a particular 15-minute interval
        in the past 24 hours."
    ::= { sonetFarEndLineIntervalEntry 3 }

sonetFarEndLineIntervalCVs OBJECT-TYPE
    SYNTAX Gauge
    ACCESS read-only
    STATUS mandatory
    DESCRIPTION
        "The counter associated with the number of
        Far End Coding Violations reported via
        the far end block error count
        encountered by a
        SONET/SDH Line
        interface in a particular 15-minute interval
        in the past 24 hours."
    ::= { sonetFarEndLineIntervalEntry 4 }

sonetFarEndLineIntervalUASs OBJECT-TYPE
    SYNTAX Gauge
    ACCESS read-only
    STATUS mandatory
    DESCRIPTION
        "The counter associated with the number of
        Far End Unavailable Seconds
        encountered by a
        SONET/SDH Line
        interface in a particular 15-minute interval
        in the past 24 hours."
    ::= { sonetFarEndLineIntervalEntry 5 }

sonetPathCurrentTable OBJECT-TYPE
    SYNTAX SEQUENCE OF SonetPathCurrentEntry
    ACCESS not-accessible
    STATUS mandatory
    DESCRIPTION
        "The SONET/SDH Path Current table."
    ::= { sonetPath 1 }

sonetPathCurrentEntry OBJECT-TYPE
    SYNTAX SonetPathCurrentEntry
    ACCESS not-accessible
    STATUS mandatory
    DESCRIPTION
        "An entry in the SONET/SDH Path Current table."
    INDEX { ifIndex }
    ::= { sonetPathCurrentTable 1 }

SonetPathCurrentEntry ::= SEQUENCE {
    sonetPathCurrentWidth INTEGER,
    sonetPathCurrentStatus INTEGER,
    sonetPathCurrentESs Gauge,
    sonetPathCurrentSESs Gauge,
    sonetPathCurrentCVs Gauge,
    sonetPathCurrentUASs Gauge
    }

sonetPathCurrentWidth OBJECT-TYPE
    SYNTAX INTEGER {
        sts1(1),
        sts3cSTM1(2),
        sts12cSTM4(3),
        sts24c(4),
        sts48cSTM16(5)
        }
    ACCESS read-write
    STATUS mandatory
    DESCRIPTION
        "A value that indicates the type of the SONET/SDH
        Path.  For SONET, the assigned types are
        the STS-Nc SPEs, where N = 1, 3, 12, 24, and 48.
        STS-1 is equal to 51.84 Mbps.  For SDH, the assigned
        types are the STM-Nc VCs, where N = 1, 4, and 16."
    ::= { sonetPathCurrentEntry 1 }

sonetPathCurrentStatus OBJECT-TYPE
    SYNTAX INTEGER(1..14)
    ACCESS read-only
    STATUS mandatory
    DESCRIPTION
        "This variable indicates the
        status of the interface.
        The sonetPathCurrentStatus
        is a bit map represented
        as a sum, therefore,
        it can represent multiple defects
        simultaneously.
        The sonetPathNoDefect should be
        set if and only if
        no other flag is set.
        
        The various bit positions are:
           1   sonetPathNoDefect
           2   sonetPathSTSLOP
           4   sonetPathSTSAIS
           8   sonetPathSTSRDI
          16   sonetPathUnequipped
          32   sonetPathSignalLabelMismatch"
    ::= { sonetPathCurrentEntry 2 }

sonetPathCurrentESs OBJECT-TYPE
    SYNTAX Gauge
    ACCESS read-only
    STATUS mandatory
    DESCRIPTION
        "The counter associated with the number of Errored
        Seconds encountered by a SONET/SDH
        Path in the current 15 minute interval."
    ::= { sonetPathCurrentEntry 3 }

sonetPathCurrentSESs OBJECT-TYPE
    SYNTAX Gauge
    ACCESS read-only
    STATUS mandatory
    DESCRIPTION
        "The counter associated with the number of
        Severely Errored Seconds
        encountered by a SONET/SDH Path in the current 15
        minute
        interval."
    ::= { sonetPathCurrentEntry 4 }

sonetPathCurrentCVs OBJECT-TYPE
    SYNTAX Gauge
    ACCESS read-only
    STATUS mandatory
    DESCRIPTION
        "The counter associated with the number of Coding
        Violations encountered by a
        SONET/SDH Path in the current 15 minute interval."
    ::= { sonetPathCurrentEntry 5 }

sonetPathCurrentUASs OBJECT-TYPE
    SYNTAX Gauge
    ACCESS read-only
    STATUS mandatory
    DESCRIPTION
        "The counter associated with the number of
        Unavailable Seconds
        encountered by a Path in the current
        15 minute, interval."
    ::= { sonetPathCurrentEntry 6 }

sonetPathIntervalTable OBJECT-TYPE
    SYNTAX SEQUENCE OF SonetPathIntervalEntry
    ACCESS not-accessible
    STATUS mandatory
    DESCRIPTION
        "The SONET/SDH Path Interval table."
    ::= { sonetPath 2 }

sonetPathIntervalEntry OBJECT-TYPE
    SYNTAX SonetPathIntervalEntry
    ACCESS not-accessible
    STATUS mandatory
    DESCRIPTION
        "An entry in the SONET/SDH Path Interval table."
    INDEX { ifIndex, sonetPathIntervalNumber }
    ::= { sonetPathIntervalTable 1 }

SonetPathIntervalEntry ::= SEQUENCE {
    sonetPathIntervalNumber INTEGER,
    sonetPathIntervalESs Gauge,
    sonetPathIntervalSESs Gauge,
    sonetPathIntervalCVs Gauge,
    sonetPathIntervalUASs Gauge
    }

sonetPathIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetPathIntervalEntry 1 }

sonetPathIntervalESs OBJECT-TYPE
    SYNTAX Gauge
    ACCESS read-only
    STATUS mandatory
    DESCRIPTION
        "The counter associated with the number of
        Errored Seconds encountered
        by a SONET/SDH Path in a
        particular 15-minute interval
        in the past 24 hours."
    ::= { sonetPathIntervalEntry 2 }

sonetPathIntervalSESs OBJECT-TYPE
    SYNTAX Gauge
    ACCESS read-only
    STATUS mandatory
    DESCRIPTION
        "The counter associated with the number of
        Severely Errored Seconds
        encountered by a SONET/SDH Path in
        a particular 15-minute interval
        in the past 24 hours."
    ::= { sonetPathIntervalEntry 3 }

sonetPathIntervalCVs OBJECT-TYPE
    SYNTAX Gauge
    ACCESS read-only
    STATUS mandatory
    DESCRIPTION
        "The counter associated with the number of Coding
        Violations encountered by a
        SONET/SDH Path in a particular 15-minute interval
        in the past 24 hours."
    ::= { sonetPathIntervalEntry 4 }

sonetPathIntervalUASs OBJECT-TYPE
    SYNTAX Gauge
    ACCESS read-only
    STATUS mandatory
    DESCRIPTION
        "The counter associated with the number of
        Unavailable Seconds
        encountered by a Path in a
        particular 15-minute interval
        in the past 24 hours."
    ::= { sonetPathIntervalEntry 5 }

sonetFarEndPathCurrentTable OBJECT-TYPE
    SYNTAX SEQUENCE OF SonetFarEndPathCurrentEntry
    ACCESS not-accessible
    STATUS mandatory
    DESCRIPTION
        "The SONET/SDH Far End Path Current table."
    ::= { sonetFarEndPath 1 }

sonetFarEndPathCurrentEntry OBJECT-TYPE
    SYNTAX SonetFarEndPathCurrentEntry
    ACCESS not-accessible
    STATUS mandatory
    DESCRIPTION
        "An entry in the SONET/SDH Far End Path Current table."
    INDEX { ifIndex }
    ::= { sonetFarEndPathCurrentTable 1 }

SonetFarEndPathCurrentEntry ::= SEQUENCE {
    sonetFarEndPathCurrentESs Gauge,
    sonetFarEndPathCurrentSESs Gauge,
    sonetFarEndPathCurrentCVs Gauge,
    sonetFarEndPathCurrentUASs Gauge
    }

sonetFarEndPathCurrentESs OBJECT-TYPE
    SYNTAX Gauge
    ACCESS read-only
    STATUS mandatory
    DESCRIPTION
        "The counter associated with the number of Far
        Far End Errored Seconds encountered by a SONET/SDH
        interface in the current 15 minute interval."
    ::= { sonetFarEndPathCurrentEntry 1 }

sonetFarEndPathCurrentSESs OBJECT-TYPE
    SYNTAX Gauge
    ACCESS read-only
    STATUS mandatory
    DESCRIPTION
        "The counter associated with the number of
        Far End Severely Errored Seconds
        encountered by a SONET/SDH Path
        interface in the current 15 minute
        interval."
    ::= { sonetFarEndPathCurrentEntry 2 }

sonetFarEndPathCurrentCVs OBJECT-TYPE
    SYNTAX Gauge
    ACCESS read-only
    STATUS mandatory
    DESCRIPTION
        "The counter associated with the number of
        Far End Coding Violations reported via
        the far end block error count
        encountered by a
        SONET/SDH Path interface in
        the current 15 minute interval."
    ::= { sonetFarEndPathCurrentEntry 3 }

sonetFarEndPathCurrentUASs OBJECT-TYPE
    SYNTAX Gauge
    ACCESS read-only
    STATUS mandatory
    DESCRIPTION
        "The counter associated with the number of
        Far End Unavailable Seconds
        encountered by a
        SONET/SDH Path interface in
        the current 15 minute interval."
    ::= { sonetFarEndPathCurrentEntry 4 }

sonetFarEndPathIntervalTable OBJECT-TYPE
    SYNTAX SEQUENCE OF SonetFarEndPathIntervalEntry
    ACCESS not-accessible
    STATUS mandatory
    DESCRIPTION
        "The SONET/SDH Far End Path Interval table."
    ::= { sonetFarEndPath 2 }

sonetFarEndPathIntervalEntry OBJECT-TYPE
    SYNTAX SonetFarEndPathIntervalEntry
    ACCESS not-accessible
    STATUS mandatory
    DESCRIPTION
        "An entry in the SONET/SDH Far
        End Path Interval table."
    INDEX { ifIndex, sonetFarEndPathIntervalNumber }
    ::= { sonetFarEndPathIntervalTable 1 }

SonetFarEndPathIntervalEntry ::= SEQUENCE {
    sonetFarEndPathIntervalNumber INTEGER,
    sonetFarEndPathIntervalESs Gauge,
    sonetFarEndPathIntervalSESs Gauge,
    sonetFarEndPathIntervalCVs Gauge,
    sonetFarEndPathIntervalUASs Gauge
    }

sonetFarEndPathIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetFarEndPathIntervalEntry 1 }

sonetFarEndPathIntervalESs OBJECT-TYPE
    SYNTAX Gauge
    ACCESS read-only
    STATUS mandatory
    DESCRIPTION
        "The counter associated with the number of
        Far End Errored Seconds encountered
        by a SONET/SDH Path interface in a
        particular 15-minute interval
        in the past 24 hours."
    ::= { sonetFarEndPathIntervalEntry 2 }

sonetFarEndPathIntervalSESs OBJECT-TYPE
    SYNTAX Gauge
    ACCESS read-only
    STATUS mandatory
    DESCRIPTION
        "The counter associated with the number of
        Far End Severely Errored Seconds
        encountered by a SONET/SDH Path interface
        in a particular 15-minute interval
        in the past 24 hours."
    ::= { sonetFarEndPathIntervalEntry 3 }

sonetFarEndPathIntervalCVs OBJECT-TYPE
    SYNTAX Gauge
    ACCESS read-only
    STATUS mandatory
    DESCRIPTION
        "The counter associated with the number of
        Far End Coding Violations reported via
        the far end block error count
        encountered by a
        SONET/SDH Path interface
        in a particular 15-minute interval
        in the past 24 hours."
    ::= { sonetFarEndPathIntervalEntry 4 }

sonetFarEndPathIntervalUASs OBJECT-TYPE
    SYNTAX Gauge
    ACCESS read-only
    STATUS mandatory
    DESCRIPTION
        "The counter associated with the number of
        Far End Unavailable Seconds
        encountered by a
        SONET/SDH Path interface in
        a particular 15-minute interval
        in the past 24 hours."
    ::= { sonetFarEndPathIntervalEntry 5 }

sonetVTCurrentTable OBJECT-TYPE
    SYNTAX SEQUENCE OF SonetVTCurrentEntry
    ACCESS not-accessible
    STATUS mandatory
    DESCRIPTION
        "The SONET/SDH VT Current table."
    ::= { sonetVT 1 }

sonetVTCurrentEntry OBJECT-TYPE
    SYNTAX SonetVTCurrentEntry
    ACCESS not-accessible
    STATUS mandatory
    DESCRIPTION
        "An entry in the SONET/SDH VT Current table."
    INDEX { ifIndex }
    ::= { sonetVTCurrentTable 1 }

SonetVTCurrentEntry ::= SEQUENCE {
    sonetVTCurrentWidth INTEGER,
    sonetVTCurrentStatus INTEGER,
    sonetVTCurrentESs Gauge,
    sonetVTCurrentSESs Gauge,
    sonetVTCurrentCVs Gauge,
    sonetVTCurrentUASs Gauge
    }

sonetVTCurrentWidth OBJECT-TYPE
    SYNTAX INTEGER {
        vtWidth15VC11(1),
        vtWidth2VC12(2),
        vtWidth3(3),
        vtWidth6VC2(4),
        vtWidth6c(5)
        }
    ACCESS read-write
    STATUS mandatory
    DESCRIPTION
        "A value that indicates the type of the SONET
         VT and SDH VC.  Assigned widths are
         VT1.5/VC11, VT2/VC12, VT3, VT6/VC2, and VT6c."
    ::= { sonetVTCurrentEntry 1 }

sonetVTCurrentStatus OBJECT-TYPE
    SYNTAX INTEGER(1..30)
    ACCESS read-only
    STATUS mandatory
    DESCRIPTION
        "This variable indicates the
        status of the interface.
        The sonetVTCurrentStatus
        is a bit map represented
        as a sum, therefore,
        it can represent multiple defects
        and failures
        simultaneously.
        The sonetVTNoDefect should be
        set if and only if
        no other flag is set.
        
        The various bit positions are:
           1   sonetVTNoDefect
           2   sonetVTLOP
           4   sonetVTPathAIS
           8   sonetVTPathRDI
          16   sonetVTPathRFI
          32   sonetVTUnequipped
          64   sonetVTSignalLabelMismatch"
    ::= { sonetVTCurrentEntry 2 }

sonetVTCurrentESs OBJECT-TYPE
    SYNTAX Gauge
    ACCESS read-only
    STATUS mandatory
    DESCRIPTION
        "The counter associated with the number of Errored
        Seconds encountered by a SONET/SDH
        VT in the current 15 minute interval."
    ::= { sonetVTCurrentEntry 3 }

sonetVTCurrentSESs OBJECT-TYPE
    SYNTAX Gauge
    ACCESS read-only
    STATUS mandatory
    DESCRIPTION
        "The counter associated with the number of
        Severely Errored Seconds
        encountered by a SONET/SDH VT in the current 15 minute
        interval."
    ::= { sonetVTCurrentEntry 4 }

sonetVTCurrentCVs OBJECT-TYPE
    SYNTAX Gauge
    ACCESS read-only
    STATUS mandatory
    DESCRIPTION
        "The counter associated with the number of Coding
        Violations encountered by a
        SONET/SDH VT in the current 15 minute interval."
    ::= { sonetVTCurrentEntry 5 }

sonetVTCurrentUASs OBJECT-TYPE
    SYNTAX Gauge
    ACCESS read-only
    STATUS mandatory
    DESCRIPTION
        "The counter associated with the number of
        Unavailable Seconds
        encountered by a VT in the current
        15 minute, interval."
    ::= { sonetVTCurrentEntry 6 }

sonetVTIntervalTable OBJECT-TYPE
    SYNTAX SEQUENCE OF SonetVTIntervalEntry
    ACCESS not-accessible
    STATUS mandatory
    DESCRIPTION
        "The SONET/SDH VT Interval table."
    ::= { sonetVT 2 }

sonetVTIntervalEntry OBJECT-TYPE
    SYNTAX SonetVTIntervalEntry
    ACCESS not-accessible
    STATUS mandatory
    DESCRIPTION
        "An entry in the SONET/SDH VT Interval table."
    INDEX { ifIndex, sonetVTIntervalNumber }
    ::= { sonetVTIntervalTable 1 }

SonetVTIntervalEntry ::= SEQUENCE {
    sonetVTIntervalNumber INTEGER,
    sonetVTIntervalESs Gauge,
    sonetVTIntervalSESs Gauge,
    sonetVTIntervalCVs Gauge,
    sonetVTIntervalUASs Gauge
    }

sonetVTIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetVTIntervalEntry 1 }

sonetVTIntervalESs OBJECT-TYPE
    SYNTAX Gauge
    ACCESS read-only
    STATUS mandatory
    DESCRIPTION
        "The counter associated with the number of
        Errored Seconds encountered
        by a SONET/SDH VT in a particular 15-minute interval
        in the past 24 hours."
    ::= { sonetVTIntervalEntry 2 }

sonetVTIntervalSESs OBJECT-TYPE
    SYNTAX Gauge
    ACCESS read-only
    STATUS mandatory
    DESCRIPTION
        "The counter associated with the number of
        Severely Errored Seconds
        encountered by a SONET/SDH VT
        in a particular 15-minute interval
        in the past 24 hours."
    ::= { sonetVTIntervalEntry 3 }

sonetVTIntervalCVs OBJECT-TYPE
    SYNTAX Gauge
    ACCESS read-only
    STATUS mandatory
    DESCRIPTION
        "The counter associated with the number of Coding
        Violations encountered by a
        SONET/SDH VT in a particular 15-minute interval
        in the past 24 hours."
    ::= { sonetVTIntervalEntry 4 }

sonetVTIntervalUASs OBJECT-TYPE
    SYNTAX Gauge
    ACCESS read-only
    STATUS mandatory
    DESCRIPTION
        "The counter associated with the number of
        Unavailable Seconds
        encountered by a VT in a particular 15-minute interval
        in the past 24 hours."
    ::= { sonetVTIntervalEntry 5 }

sonetFarEndVTCurrentTable OBJECT-TYPE
    SYNTAX SEQUENCE OF SonetFarEndVTCurrentEntry
    ACCESS not-accessible
    STATUS mandatory
    DESCRIPTION
        "The SONET/SDH Far End VT Current table."
    ::= { sonetFarEndVT 1 }

sonetFarEndVTCurrentEntry OBJECT-TYPE
    SYNTAX SonetFarEndVTCurrentEntry
    ACCESS not-accessible
    STATUS mandatory
    DESCRIPTION
        "An entry in the SONET/SDH Far End VT Current table."
    INDEX { ifIndex }
    ::= { sonetFarEndVTCurrentTable 1 }

SonetFarEndVTCurrentEntry ::= SEQUENCE {
    sonetFarEndVTCurrentESs Gauge,
    sonetFarEndVTCurrentSESs Gauge,
    sonetFarEndVTCurrentCVs Gauge,
    sonetFarEndVTCurrentUASs Gauge
    }

sonetFarEndVTCurrentESs OBJECT-TYPE
    SYNTAX Gauge
    ACCESS read-only
    STATUS mandatory
    DESCRIPTION
        "The counter associated with the number of Far
        Far End Errored Seconds encountered by a SONET/SDH
        interface in the current 15 minute interval."
    ::= { sonetFarEndVTCurrentEntry 1 }

sonetFarEndVTCurrentSESs OBJECT-TYPE
    SYNTAX Gauge
    ACCESS read-only
    STATUS mandatory
    DESCRIPTION
        "The counter associated with the number of
        Far End Severely Errored Seconds
        encountered by a SONET/SDH VT interface
        in the current 15 minute
        interval."
    ::= { sonetFarEndVTCurrentEntry 2 }

sonetFarEndVTCurrentCVs OBJECT-TYPE
    SYNTAX Gauge
    ACCESS read-only
    STATUS mandatory
    DESCRIPTION
        "The counter associated with the number of
        Far End Coding Violations reported via
        the far end block error count
        encountered by a
        SONET/SDH VT interface
        in the current 15 minute interval."
    ::= { sonetFarEndVTCurrentEntry 3 }

sonetFarEndVTCurrentUASs OBJECT-TYPE
    SYNTAX Gauge
    ACCESS read-only
    STATUS mandatory
    DESCRIPTION
        "The counter associated with the number of
        Far End Unavailable Seconds
        encountered by a
        SONET/SDH VT interface
        in the current 15 minute interval."
    ::= { sonetFarEndVTCurrentEntry 4 }

sonetFarEndVTIntervalTable OBJECT-TYPE
    SYNTAX SEQUENCE OF SonetFarEndVTIntervalEntry
    ACCESS not-accessible
    STATUS mandatory
    DESCRIPTION
        "The SONET/SDH Far End VT Interval table."
    ::= { sonetFarEndVT 2 }

sonetFarEndVTIntervalEntry OBJECT-TYPE
    SYNTAX SonetFarEndVTIntervalEntry
    ACCESS not-accessible
    STATUS mandatory
    DESCRIPTION
        "An entry in the SONET/SDH Far
        End VT Interval table."
    INDEX { ifIndex, sonetFarEndVTIntervalNumber }
    ::= { sonetFarEndVTIntervalTable 1 }

SonetFarEndVTIntervalEntry ::= SEQUENCE {
    sonetFarEndVTIntervalNumber INTEGER,
    sonetFarEndVTIntervalESs Gauge,
    sonetFarEndVTIntervalSESs Gauge,
    sonetFarEndVTIntervalCVs Gauge,
    sonetFarEndVTIntervalUASs Gauge
    }

sonetFarEndVTIntervalNumber OBJECT-TYPE
    SYNTAX INTEGER(1..96)
    ACCESS not-accessible
    STATUS mandatory
    DESCRIPTION
        "A number between 1 and 96, which identifies the
        interval for which the set of statistics is available.
        The interval identified by 1 is the most recently
        completed 15 minute interval,
        and the interval identified
        by N is the interval immediately preceding the
        one identified
        by N-1."
    ::= { sonetFarEndVTIntervalEntry 1 }

sonetFarEndVTIntervalESs OBJECT-TYPE
    SYNTAX Gauge
    ACCESS read-only
    STATUS mandatory
    DESCRIPTION
        "The counter associated with the number of
        Far End Errored Seconds encountered
        by a SONET/SDH VT interface
        in a particular 15-minute interval
        in the past 24 hours."
    ::= { sonetFarEndVTIntervalEntry 2 }

sonetFarEndVTIntervalSESs OBJECT-TYPE
    SYNTAX Gauge
    ACCESS read-only
    STATUS mandatory
    DESCRIPTION
        "The counter associated with the number of
        Far End Severely Errored Seconds
        encountered by a SONET/SDH VT interface
        in a particular 15-minute interval
        in the past 24 hours."
    ::= { sonetFarEndVTIntervalEntry 3 }

sonetFarEndVTIntervalCVs OBJECT-TYPE
    SYNTAX Gauge
    ACCESS read-only
    STATUS mandatory
    DESCRIPTION
        "The counter associated with the number of
        Far End Coding Violations reported via
        the far end block error count
        encountered by a
        SONET/SDH VT interface in a
        particular 15-minute interval
        in the past 24 hours."
    ::= { sonetFarEndVTIntervalEntry 4 }

sonetFarEndVTIntervalUASs OBJECT-TYPE
    SYNTAX Gauge
    ACCESS read-only
    STATUS mandatory
    DESCRIPTION
        "The counter associated with the number of
        Far End Unavailable Seconds
        encountered by a
        SONET/SDH VT interface in a
        particular 15-minute interval
        in the past 24 hours."
    ::= { sonetFarEndVTIntervalEntry 5 }

sonetMediumStuff OBJECT IDENTIFIER ::= { sonetGroups 1 }
-- OBJECT-GROUP
--  Status
--    mandatory
--  Descr
--    A collection of objects providing configuration
--    information applicable to all SONET/SDH
--    interfaces.
--  objects
--    sonetMediumType, sonetMediumTimeElapsed, 
--    sonetMediumValidIntervals, sonetMediumLineCoding, 
--    sonetMediumLineType, sonetMediumCircuitIdentifier

sonetSectionStuff OBJECT IDENTIFIER ::= { sonetGroups 2 }
-- OBJECT-GROUP
--  Status
--    mandatory
--  Descr
--    A collection of objects providing information
--    specific to SONET/SDH Section interfaces.
--  objects
--    sonetSectionCurrentStatus, sonetSectionCurrentESs, 
--    sonetSectionCurrentSESs, sonetSectionCurrentSEFSs, 
--    sonetSectionCurrentCVs, sonetSectionIntervalESs, 
--    sonetSectionIntervalSESs, sonetSectionIntervalSEFSs, 
--    sonetSectionIntervalCVs

sonetLineStuff OBJECT IDENTIFIER ::= { sonetGroups 3 }
-- OBJECT-GROUP
--  Status
--    mandatory
--  Descr
--    A collection of objects providing information
--    specific to SONET/SDH Line interfaces.
--  objects
--    sonetLineCurrentStatus, sonetLineCurrentESs, 
--    sonetLineCurrentSESs, sonetLineCurrentCVs, 
--    sonetLineCurrentUASs, sonetLineIntervalESs, 
--    sonetLineIntervalSESs, sonetLineIntervalCVs, 
--    sonetLineIntervalUASs

sonetFarEndLineStuff OBJECT IDENTIFIER ::= { sonetGroups 4 }
-- OBJECT-GROUP
--  Status
--    mandatory
--  Descr
--    A collection of objects providing information
--    specific to SONET/SDH Line interfaces,
--    and maintaining Line Far End information.
--  objects
--    sonetFarEndLineCurrentESs, sonetFarEndLineCurrentSESs, 
--    sonetFarEndLineCurrentCVs, sonetFarEndLineCurrentUASs, 
--    sonetFarEndLineIntervalESs, sonetFarEndLineIntervalSESs, 
--    sonetFarEndLineIntervalCVs, sonetFarEndLineIntervalUASs

sonetPathStuff OBJECT IDENTIFIER ::= { sonetGroups 5 }
-- OBJECT-GROUP
--  Status
--    mandatory
--  Descr
--    A collection of objects providing information
--    specific to SONET/SDH Path interfaces.
--  objects
--    sonetPathCurrentWidth, sonetPathCurrentStatus, 
--    sonetPathCurrentESs, sonetPathCurrentSESs, 
--    sonetPathCurrentCVs, sonetPathCurrentUASs, 
--    sonetPathIntervalESs, sonetPathIntervalSESs, 
--    sonetPathIntervalCVs, sonetPathIntervalUASs

sonetFarEndPathStuff OBJECT IDENTIFIER ::= { sonetGroups 6 }
-- OBJECT-GROUP
--  Status
--    mandatory
--  Descr
--    A collection of objects providing information
--    specific to SONET/SDH Path interfaces,
--    and maintaining Path Far End information.
--  objects
--    sonetFarEndPathCurrentESs, sonetFarEndPathCurrentSESs, 
--    sonetFarEndPathCurrentCVs, sonetFarEndPathCurrentUASs, 
--    sonetFarEndPathIntervalESs, sonetFarEndPathIntervalSESs, 
--    sonetFarEndPathIntervalCVs, sonetFarEndPathIntervalUASs

sonetVTStuff OBJECT IDENTIFIER ::= { sonetGroups 7 }
-- OBJECT-GROUP
--  Status
--    mandatory
--  Descr
--    A collection of objects providing information
--    specific to SONET/SDH VT interfaces.
--  objects
--    sonetVTCurrentWidth, sonetVTCurrentStatus, sonetVTCurrentESs, 
--    sonetVTCurrentSESs, sonetVTCurrentCVs, sonetVTCurrentUASs, 
--    sonetVTIntervalESs, sonetVTIntervalSESs, sonetVTIntervalCVs, 
--    sonetVTIntervalUASs

sonetFarEndVTStuff OBJECT IDENTIFIER ::= { sonetGroups 8 }
-- OBJECT-GROUP
--  Status
--    mandatory
--  Descr
--    A collection of objects providing information
--    specific to SONET/SDH VT interfaces,
--    and maintaining VT Far End information.
--  objects
--    sonetFarEndVTCurrentESs, sonetFarEndVTCurrentSESs, 
--    sonetFarEndVTCurrentCVs, sonetFarEndVTCurrentUASs, 
--    sonetFarEndVTIntervalESs, sonetFarEndVTIntervalSESs, 
--    sonetFarEndVTIntervalCVs, sonetFarEndVTIntervalUASs

sonetCompliance OBJECT IDENTIFIER ::= { sonetCompliances 1 }
-- MODULE-COMPLIANCE
--  Status
--    mandatory
--  Descr
--    The compliance statement for SONET/SDH
--     interfaces.
--  Module
--    >>current<<
--   MandGroup
--    sonetMediumStuff
--   MandGroup
--    sonetSectionStuff
--   OptGroup
--    sonetLineStuff
--   OptGroup
--    sonetFarEndLineStuff
--   OptGroup
--    sonetPathStuff
--   ObjVar
--    sonetPathCurrentWidth
--   OptGroup
--    sonetFarEndPathStuff
--   OptGroup
--    sonetVTStuff
--   ObjVar
--    sonetVTCurrentWidth
--   OptGroup
--    sonetFarEndVTStuff


END
