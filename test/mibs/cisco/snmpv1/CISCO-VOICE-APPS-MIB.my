-- MIB file created 08-Jun-2001 11:19:27, by
--   SMICng version 2.2.11-beta(PRO)(Solaris), January 20, 2001. Enterprise key cisco.com

CISCO-VOICE-APPS-MIB DEFINITIONS ::= BEGIN

-- From file: "CISCO-VOICE-APPS-MIB.my"
-- Compile options "4 7 F H N W 03 06 0B 0G 0N 0T"

IMPORTS
    DisplayString, TruthValue
            FROM SNMPv2-TC-v1
    SnmpAdminString
            FROM SNMP-FRAMEWORK-MIB
--    Unsigned32
--            FROM CISCO-TC
    Gauge
            FROM RFC1155-SMI
    ciscoMgmt
            FROM CISCO-SMI
    OBJECT-TYPE
            FROM RFC-1212
    TRAP-TYPE
            FROM RFC-1215;

ciscoVoiceAppsMIB OBJECT IDENTIFIER ::= { ciscoMgmt 190 }
-- MODULE-IDENTITY
--  LastUpdated
--    200102260000Z
--  OrgName
--    Cisco Systems, Inc.
--  ContactInfo
--        Cisco Systems
--        Customer Service
--    
--    Postal: 170 W. Tasman Drive
--        San Jose, CA  95134
--        USA
--    
--    Tel: +1 800 553-NETS
--    
--    E-mail: cs-selsius@cisco.com
--  Descr
--    The MIB Module for the management of Cisco Voice
--     Applications.  This MIB is designed to work in 
--     conjunction with the SYSAPPL-MIB to provide status
--     monitoring, provisioning and notification.

ciscoVoiceAppsMIBObjects OBJECT IDENTIFIER ::= { ciscoVoiceAppsMIB 1 }
cvaGeneralInfo  OBJECT IDENTIFIER ::= { ciscoVoiceAppsMIBObjects 1 }
cvaModuleFailureInfo OBJECT IDENTIFIER ::= { ciscoVoiceAppsMIBObjects 2 }
ciscoVoiceAppsMIBNotificationPrefix OBJECT IDENTIFIER ::= { ciscoVoiceAppsMIB 2 }
ciscoVoiceAppsMIBNotifications OBJECT IDENTIFIER ::= { ciscoVoiceAppsMIBNotificationPrefix 0 }
ciscoVoiceAppsMIBConformance OBJECT IDENTIFIER ::= { ciscoVoiceAppsMIB 3 }
ciscoVoiceAppsMIBCompliances OBJECT IDENTIFIER ::= { ciscoVoiceAppsMIBConformance 1 }
ciscoVoiceAppsMIBGroups OBJECT IDENTIFIER ::= { ciscoVoiceAppsMIBConformance 2 }

cvaWorkflowInstallTable OBJECT-TYPE
    SYNTAX SEQUENCE OF CvaWorkflowInstallEntry
    ACCESS not-accessible
    STATUS mandatory
    DESCRIPTION
        "The table containing the list of installed Workflow 
        applications provisioned on the media server.
        
        For instance, this table may contain an entry for
        each of the Auto Attendant(AA) or Integrated Contact 
        Distribution(ICD) application installed on the Cisco 
        Workflow Application."
    ::= { cvaGeneralInfo 1 }

cvaWorkflowInstallEntry OBJECT-TYPE
    SYNTAX CvaWorkflowInstallEntry
    ACCESS not-accessible
    STATUS mandatory
    DESCRIPTION
        "An entry (conceptual row) in the Workflow Installation 
        Table, containing information associated with the Cisco
        Workflow Application.  This entry is created when a
        workflow application is installed via the application
        Administration page."
    INDEX { cvaWorkflowInstallIndex }
    ::= { cvaWorkflowInstallTable 1 }

CvaWorkflowInstallEntry ::= SEQUENCE {
    cvaWorkflowInstallIndex Gauge,
    cvaWorkflowInstallName SnmpAdminString,
    cvaWorkflowInstallLocator OCTET STRING,
    cvaWorkflowInstallScriptName SnmpAdminString,
    cvaWorkflowInstallEnable TruthValue
    }

cvaWorkflowInstallIndex OBJECT-TYPE
    SYNTAX Gauge
    ACCESS not-accessible
    STATUS mandatory
    DESCRIPTION
        "An arbitrary integer which uniquely identifies an Workflow
         Application."
    ::= { cvaWorkflowInstallEntry 1 }

cvaWorkflowInstallName OBJECT-TYPE
    SYNTAX SnmpAdminString(SIZE(0..128))
--    Rsyntax OCTET STRING(SIZE(0..128))
    ACCESS read-only
    STATUS mandatory
    DESCRIPTION
        "The name of the workflow application."
    ::= { cvaWorkflowInstallEntry 2 }

cvaWorkflowInstallLocator OBJECT-TYPE
    SYNTAX OCTET STRING(SIZE(0..128))
    ACCESS read-only
    STATUS mandatory
    DESCRIPTION
        "The extension number or CTI (Computer 
         Telephony Integration) route point associated
         with the workflow application.  
         For instance, 5000 for extension 5000."
    ::= { cvaWorkflowInstallEntry 3 }

cvaWorkflowInstallScriptName OBJECT-TYPE
    SYNTAX SnmpAdminString(SIZE(0..128))
--    Rsyntax OCTET STRING(SIZE(0..128))
    ACCESS read-only
    STATUS mandatory
    DESCRIPTION
        "The workflow application script name."
    ::= { cvaWorkflowInstallEntry 4 }

cvaWorkflowInstallEnable OBJECT-TYPE
    SYNTAX TruthValue
--    Rsyntax INTEGER {
--        true(1),
--        false(2)
--        }
    ACCESS read-only
    STATUS mandatory
    DESCRIPTION
        "The status of the workflow application.
            true(1):   Workflow Application is enabled
            false(2):  Workflow Application is disabled."
    ::= { cvaWorkflowInstallEntry 5 }

cvaNotificationEnable OBJECT-TYPE
    SYNTAX TruthValue
--    Rsyntax INTEGER {
--        true(1),
--        false(2)
--        }
    ACCESS read-write
    STATUS mandatory
    DESCRIPTION
        "To enable(1) or disable(2) generation of the following 
        notifications:
            cvaModuleStart notification
            cvaModuleStop notification
            cvaModuleRunTimeFailure notification
            cvaProcessStart notification
            cvaProcessStop notification
         The default value is enable(1)."
    ::= { cvaGeneralInfo 3 }

cvaAlarmSeverity OBJECT-TYPE
    SYNTAX INTEGER {
        emergency(1),
        alert(2),
        critical(3),
        error(4),
        warning(5),
        notice(6),
        informational(7)
        }
    ACCESS not-accessible
    STATUS mandatory
    DESCRIPTION
        "The application alarm notification severity code.
            emergency:                System unusable
            alert:                    Immediate response needed
            critical:                 Critical condition
            error:                    Error condition
            warning:                  Warning condition
            notice:                   Normal but significant condition
            informational:            Informational situation."
    ::= { cvaModuleFailureInfo 1 }

cvaModuleName OBJECT-TYPE
    SYNTAX DisplayString(SIZE(0..32))
--    Rsyntax OCTET STRING(SIZE(0..32))
    ACCESS not-accessible
    STATUS mandatory
    DESCRIPTION
        "The application module or subsystem name."
    ::= { cvaModuleFailureInfo 2 }

cvaProcessId OBJECT-TYPE
    SYNTAX Gauge
    ACCESS not-accessible
    STATUS mandatory
    DESCRIPTION
        "A unique value for each of the process running on the host.
        Wherever possible, this should be the system's native, unique
        Identification number (process id)."
    ::= { cvaModuleFailureInfo 3 }

cvaModuleFailureName OBJECT-TYPE
    SYNTAX DisplayString(SIZE(0..32))
--    Rsyntax OCTET STRING(SIZE(0..32))
    ACCESS not-accessible
    STATUS mandatory
    DESCRIPTION
        "The application module name which causes the failure."
    ::= { cvaModuleFailureInfo 4 }

cvaModuleFailureCause OBJECT-TYPE
    SYNTAX INTEGER {
        other(1),
        gracefulShutDown(2),
        heartBeatFailure(3),
        initFailure(4),
        outOfResource(5),
        partialFailure(6)
        }
    ACCESS not-accessible
    STATUS mandatory
    DESCRIPTION
        "The application module failure cause code.  This is used
         by cvaModuleStop to indicate reason of module stop if known.  
            other:            Other unspecified failure cause
            gracefulShutDown: Module is gracefully shut down
            heartBeatStopped: Module heart beat stopped is detected
            initFailure:      Module is failed during initialization
            outOfResource:    Module is failed due to out of resource
            partialFailure:   Module partially failure is detected."
    ::= { cvaModuleFailureInfo 5 }

cvaModuleFailureMessage OBJECT-TYPE
    SYNTAX DisplayString(SIZE(0..255))
--    Rsyntax OCTET STRING(SIZE(0..255))
    ACCESS not-accessible
    STATUS mandatory
    DESCRIPTION
        "The application module failure message."
    ::= { cvaModuleFailureInfo 6 }

cvaModuleRunTimeFailureCause OBJECT-TYPE
    SYNTAX INTEGER {
        other(1),
        readAccessFailure(2),
        writeAccessFailure(3),
        createFailure(4),
        deleteFailure(5),
        updateFailure(6),
        initFailure(7),
        loadFailure(8),
        outOfResource(9),
        callProcessFailure(10),
        registrationFailure(11),
        deRegistrationFailure(12),
        connectionFailure(13),
        disconnectionFailure(14),
        unknownTarget(15),
        unReacheableTarget(16)
        }
    ACCESS not-accessible
    STATUS mandatory
    DESCRIPTION
        "The application module run-time failure cause code.  
            other:                 Other or unspecified failure
            readAccessFailure:     Read Access failure
            writeAccessFailure:    Write Access failure
            createFailure:         Resource Creation failure
            deleteFailure:         Resource Deletion failure
            updateFailure:         Update failure
            initFailure:           Initialization failure
            loadFailure:           Resource Load failure
            outOfResource:         Out of Resource
            callProcessFailure:    Call Processing failure
            registrationFailure:   Registration failure
            deRegistrationFailure: De-Registration failure
            connectionFailure:     Connection failure
            disconnectionFailure:  Desconnection failure
            unknownTarget:         Unknown Target/destination
            unReacheableTarget:    UnReacheable Target/destination"
    ::= { cvaModuleFailureInfo 7 }

cvaModuleStart TRAP-TYPE
-- Reverse mappable trap
    ENTERPRISE ciscoVoiceAppsMIBNotificationPrefix
    VARIABLES {
        cvaAlarmSeverity, cvaModuleName }
--  Status
--    mandatory
    DESCRIPTION
        "A cvaModuleStart notification signifies that an 
        application module or subsystem has successfully
        started and transitioned into in-service state.  
        This notification is working in conjunction with
        the cvaModuleStop notification to notify the start
        and stop status of a particular application module."
    ::= 1

cvaModuleStop TRAP-TYPE
-- Reverse mappable trap
    ENTERPRISE ciscoVoiceAppsMIBNotificationPrefix
    VARIABLES {
        cvaAlarmSeverity, cvaModuleName, cvaModuleFailureCause, 
        cvaModuleFailureName, cvaModuleFailureMessage }
--  Status
--    mandatory
    DESCRIPTION
        "A cvaModuleStop notification signifies that an
        application module or subsystem has stopped.  This 
        notification is working in conjunction with the 
        cvaModuleStart notification to notify the start 
        and stop status of a particular application module. 
        If failure cause is known then it will be specified 
        in the cvaModuleFailureCause variable.  Additional 
        failure information associated with cvaModuleFailureCause
        can be specified in the cvaModuleFailureCauseMessage."
    ::= 2

cvaModuleRunTimeFailure TRAP-TYPE
-- Reverse mappable trap
    ENTERPRISE ciscoVoiceAppsMIBNotificationPrefix
    VARIABLES {
        cvaAlarmSeverity, cvaModuleName, 
        cvaModuleRunTimeFailureCause, cvaModuleFailureName, 
        cvaModuleFailureMessage }
--  Status
--    mandatory
    DESCRIPTION
        "A cvaModuleRunTimeFailure notification signifies that a run
        time failure has occurred.  If failure cause is known then it 
        will be specified in the cvaModuleRunTimeFailureCause 
        variable. Additional failure information associated with 
        cvaModuleRunTimeFailureCause can be specified in the 
        cvaModuleFailureCauseMessage."
    ::= 3

cvaProcessStart TRAP-TYPE
-- Reverse mappable trap
    ENTERPRISE ciscoVoiceAppsMIBNotificationPrefix
    VARIABLES {
        cvaAlarmSeverity, cvaModuleName, cvaProcessId }
--  Status
--    mandatory
    DESCRIPTION
        "A cvaProcessStart notification signifies that a process has 
        just started.  This notification is intended to work in 
        conjunction with the caProcessStop notification to notify 
        the start and stop status of a particular process."
    ::= 4

cvaProcessStop TRAP-TYPE
-- Reverse mappable trap
    ENTERPRISE ciscoVoiceAppsMIBNotificationPrefix
    VARIABLES {
        cvaAlarmSeverity, cvaModuleName, cvaProcessId }
--  Status
--    mandatory
    DESCRIPTION
        "A cvaProcessStop notification signifies that a process has 
        just stopped.  This notification is intended to work in 
        conjunction with the cvaProcessStart notification to notify 
        the start and stop status of a particular process."
    ::= 5

cvaModuleInfoGroup OBJECT IDENTIFIER ::= { ciscoVoiceAppsMIBGroups 1 }
-- OBJECT-GROUP
--  Status
--    mandatory
--  Descr
--    A collection of objects which provide info about the
--     application.  It comprises of all the modules and servers
--     associated with the application.
--  objects
--    cvaWorkflowInstallName, cvaWorkflowInstallLocator, 
--    cvaWorkflowInstallScriptName, cvaWorkflowInstallEnable, 
--    cvaNotificationEnable

cvaNotificationInfoGroup OBJECT IDENTIFIER ::= { ciscoVoiceAppsMIBGroups 2 }
-- OBJECT-GROUP
--  Status
--    mandatory
--  Descr
--    A collection of notification objects which provide info 
--    about the application notification.
--  objects
--    cvaAlarmSeverity, cvaModuleName, cvaProcessId, 
--    cvaModuleFailureName, cvaModuleFailureCause, 
--    cvaModuleFailureMessage, cvaModuleRunTimeFailureCause

ciscoVoiceAppsMIBCompliance OBJECT IDENTIFIER ::= { ciscoVoiceAppsMIBCompliances 1 }
-- MODULE-COMPLIANCE
--  Status
--    mandatory
--  Descr
--    The compliance statement for entities which implement
--    the CISCO APPLICATION MIB.
--  Module
--    >>current<<
--   MandGroup
--    cvaModuleInfoGroup
--   MandGroup
--    cvaNotificationInfoGroup


END
