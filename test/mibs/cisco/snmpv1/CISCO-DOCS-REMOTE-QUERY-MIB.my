-- MIB file created 16-Dec-2002 18:46:52, by
--   SMICng version 2.2.11-beta(PRO)(Solaris), January 20, 2001. Enterprise key cisco.com

CISCO-DOCS-REMOTE-QUERY-MIB DEFINITIONS ::= BEGIN

-- From file: "CISCO-DOCS-REMOTE-QUERY-MIB.my"
-- Compile options "4 7 F H N W 03 06 0B 0G 0N 0T"

IMPORTS
    TruthValue, TimeStamp, TimeInterval
            FROM SNMPv2-TC-v1
    TenthdBmV, TenthdB
            FROM DOCS-IF-MIB
    ciscoExperiment
            FROM CISCO-SMI
--  Unsigned32
--          FROM CISCO-TC
    SnmpAdminString, SnmpEngineID
            FROM SNMP-FRAMEWORK-MIB
    cdxCmCpeMacAddress
            FROM CISCO-DOCS-EXT-MIB
    OBJECT-TYPE
            FROM RFC-1212
    Gauge
            FROM RFC1155-SMI
    TRAP-TYPE
            FROM RFC-1215;


ciscoDocsRemoteQueryMIB OBJECT IDENTIFIER ::= { ciscoExperiment 59 }
-- MODULE-IDENTITY
--  LastUpdated
--    200012210000Z
--  OrgName
--    Cisco Systems, Inc.
--  ContactInfo
--           Cisco Systems
--            Customer Service
--    
--    Postal: 170 West Tasman Drive
--            San Jose, CA 95134
--            U.S.A
--       Tel: +1 800 553-NETS 
--    E-mail: cs-ubr@cisco.com
--  Descr
--    This MIB module provides the management of 
--    the Cisco Cable Modem Termination Systems 
--    (CMTS) Remote Query feature.
--    
--    This feature, implemented on a CMTS, facilitates 
--    SNMP polling of remote cable modems (CMs).
--    
--    This MIB includes the configuration and 
--    status objects of the CMTS CM Poller and 
--    remote CMs that polled by the CMTS CM Poller
--  RevDate
--    200012210000Z
--  RevDescr
--    Change the range of cdrqCmtsCmPollerInterval
--  RevDate
--    200003080000Z
--  RevDescr
--    Initial version of this MIB. 

ciscoDocsRemQueryMIBObjects OBJECT IDENTIFIER ::= { ciscoDocsRemoteQueryMIB 1 }
cdrqPoller      OBJECT IDENTIFIER ::= { ciscoDocsRemQueryMIBObjects 1 }
cdrqCM          OBJECT IDENTIFIER ::= { ciscoDocsRemQueryMIBObjects 2 }
ciscoDocsRQNotificationsPrefix OBJECT IDENTIFIER ::= { ciscoDocsRemoteQueryMIB 2 }
ciscoDocsRQNotifications OBJECT IDENTIFIER ::= { ciscoDocsRQNotificationsPrefix 0 }
ciscoDocsRemoteQueryConformance OBJECT IDENTIFIER ::= { ciscoDocsRemoteQueryMIB 3 }
cdrqDocsRemoteQueryCompliances OBJECT IDENTIFIER ::= { ciscoDocsRemoteQueryConformance 1 }
cdrqDocsRemoteQueryGroups OBJECT IDENTIFIER ::= { ciscoDocsRemoteQueryConformance 2 }

cdrqCmtsCmPollerEnable OBJECT-TYPE
    SYNTAX TruthValue
--    Rsyntax INTEGER {
--        true(1),
--        false(2)
--        }
    ACCESS read-write
    STATUS mandatory
    DESCRIPTION
        "An indication of whether the CMTS CM Poller is running.
        
        When the poller is enabled, it polls the remote CMs 
        periodically specified in the cdrqCmtsCmPollerInterval
        mib object.
        
        The operation can be expensive depending on how many CMs 
        that the poller would be polling.  It is suggested to 
        have it disabled when not needed."
    ::= { cdrqPoller 1 }

cdrqCmtsCmPollerInterval OBJECT-TYPE
    SYNTAX TimeInterval(1..8640000)
--    Rsyntax INTEGER(1..8640000)
    ACCESS read-write
    STATUS mandatory
    DESCRIPTION
        "An interval between two polling cycles of the CMTS CM 
        Poller. 
        
        The poller will not start the next cycle until it 
        finished polling for the last CM , even though the 
        time has expired.  If the cdrqCmtsCmPollerInterval is 
        too small with a large number of CMs, the poller would
        tie up the CPU and resources and possibly degrade the
        system's performance.
        
        Any change in the cdrqCmtsCmPollerInterval will not
        be reflected if the poller has already been enabled."
    ::= { cdrqPoller 2 }

cdrqCmtsCmPollerCommunity OBJECT-TYPE
    SYNTAX OCTET STRING
    ACCESS read-write
    STATUS mandatory
    DESCRIPTION
        "The read community string is used for polling the CMs.
        
        Any change in the cdrqCmtsCmPollerCommunity will not
        be reflected if the poller has already been enabled.
        
        For SNMPv3, this object will contain a user name 
        instead of a community string."
    ::= { cdrqPoller 3 }

cdrqCmtsCmPollerContextEngineID OBJECT-TYPE
    SYNTAX SnmpEngineID
--    Rsyntax OCTET STRING(SIZE(5..32))
    ACCESS read-write
    STATUS mandatory
    DESCRIPTION
        "The contextEngineID indicating the location of the
        context in which management information is accessed
        when using the user name specified by the
        corresponding instance of cdrqCmtsCmPollerCommunity.
        
        This object is implemented to support SNMPv3"
    ::= { cdrqPoller 4 }

cdrqCmtsCmPollerContextName OBJECT-TYPE
    SYNTAX SnmpAdminString(SIZE(0..32))
--    Rsyntax OCTET STRING(SIZE(0..32))
    ACCESS read-write
    STATUS mandatory
    DESCRIPTION
        "The context in which management information is accessed
        when using the user name specified by the 
        corresponding instance of cdrqCmtsCmPollerCommunity.
        
        This object is implemented to support SNMPv3"
    DEFVAL { ''H }
    ::= { cdrqPoller 5 }

cdrqCmtsCmPollerStartTime OBJECT-TYPE
    SYNTAX TimeStamp
--    Rsyntax TimeTicks
    ACCESS read-only
    STATUS mandatory
    DESCRIPTION
        "The value of sysUpTime when the last polling cycle 
         started. 
        
        cdrqCmtsCmPollerStartTime is set to 0 when the CMTS 
        is first restarted and doesn't get reset after the 
        poller is disabled."
    ::= { cdrqPoller 6 }

cdrqCmtsCmPollerStopTime OBJECT-TYPE
    SYNTAX TimeStamp
--    Rsyntax TimeTicks
    ACCESS read-only
    STATUS mandatory
    DESCRIPTION
        "The value of sysUpTime when the last polling cycle 
        finished.
            
        cdrqCmtsCmPollerStopTime is set to 0 when the CMTS 
        is first restarted and doesn't get reset after the poller
        is disabled."
    ::= { cdrqPoller 7 }

cdrqCmtsCmStatusTable OBJECT-TYPE
    SYNTAX SEQUENCE OF CdrqCmtsCmStatusEntry
    ACCESS not-accessible
    STATUS mandatory
    DESCRIPTION
        "This table contains the status of the cable modems that 
        are polled by the CMTS CM Poller. The information will be 
        overwritten when a new polling cycle starts.
        
        The removal of CM from the list or adding a new CM to the 
        list won't be reflected until the next polling cycle.
        
        Depending on how many CMs that the poller is polling, 
        polling this table constantly can be quite expensive; 
        Therefore, it is best to poll upon receipt of the 
        cdrqCmtsCmRQDoneNotification. As a hedge against lost 
        notifications, periodic background polling should 
        be performed.  Howerver, excessive polling could 
        degrade performance."
    ::= { cdrqCM 1 }

cdrqCmtsCmStatusEntry OBJECT-TYPE
    SYNTAX CdrqCmtsCmStatusEntry
    ACCESS not-accessible
    STATUS mandatory
    DESCRIPTION
        "A list of the cable modem's attributes 
         that are polled by a CMTS. "
    INDEX { cdxCmCpeMacAddress }
    ::= { cdrqCmtsCmStatusTable 1 }

CdrqCmtsCmStatusEntry ::= SEQUENCE {
    cdrqCmtsCmDownChannelPower TenthdBmV,
    cdrqCmtsCmStatusTxPower TenthdBmV,
    cdrqCmtsCmUpChnlTxTimingOffset Gauge,
    cdrqCmtsCmSigQSignalNoise TenthdB,
    cdrqCmtsCmSigQMicroreflections INTEGER,
    cdrqCmtsCmPollTime TimeStamp
    }

cdrqCmtsCmDownChannelPower OBJECT-TYPE
    SYNTAX TenthdBmV
--    Rsyntax INTEGER
--  Units
--    dBmV
    ACCESS read-only
    STATUS mandatory
    DESCRIPTION
        "The CM's received power level.  This object
        may be set to zero if the CM does not support
        power level measurement.
        
        If the CM downstream interface is down, this object 
        either returns the most current value or the value of 0."
    REFERENCE
        "DOCSIS Radio Frequency Interface Specification,
         Table 4-12 and Table 4-13."
    ::= { cdrqCmtsCmStatusEntry 1 }

cdrqCmtsCmStatusTxPower OBJECT-TYPE
    SYNTAX TenthdBmV
--    Rsyntax INTEGER
--  Units
--    dBmV
    ACCESS read-only
    STATUS mandatory
    DESCRIPTION
        "The operational transmit power for the CM upstream 
        channel."
    REFERENCE
        "DOCSIS Radio Frequency Interface specification, 
        Section 4.2.8."
    ::= { cdrqCmtsCmStatusEntry 2 }

cdrqCmtsCmUpChnlTxTimingOffset OBJECT-TYPE
    SYNTAX Gauge
    ACCESS read-only
    STATUS mandatory
    DESCRIPTION
        "A measure of the current round trip time.  Used for 
        timing of CM upstream transmissions to ensure 
        synchronized arrivals at the CMTS."
    REFERENCE
        "DOCSIS Radio Frequency Interface Specification,
        Section 6.5."
    ::= { cdrqCmtsCmStatusEntry 3 }

cdrqCmtsCmSigQSignalNoise OBJECT-TYPE
    SYNTAX TenthdB
--    Rsyntax INTEGER
--  Units
--    dB
    ACCESS read-only
    STATUS mandatory
    DESCRIPTION
        "Signal/Noise ratio as perceived for the CM downstream 
        channel."
    REFERENCE
        "DOCSIS Radio Frequency Interface specification,
        Table 2-1 and 2-2"
    ::= { cdrqCmtsCmStatusEntry 4 }

cdrqCmtsCmSigQMicroreflections OBJECT-TYPE
    SYNTAX INTEGER(0..255)
--  Units
--    dBc
    ACCESS read-only
    STATUS mandatory
    DESCRIPTION
        "Total microreflections including in-channel 
        response as perceived on the CM downstream, 
        measured in dBc below the signal level.
        
        This object is not assumed to return an absolutely
        accurate value, but is meant to give a rough indication
        of microreflections received on this interface.
        It is up to the implementor to provide information
        as accurate as possible."
    REFERENCE
        "DOCSIS Radio Frequency Interface specification,
        Table 2-1 and 2-2"
    ::= { cdrqCmtsCmStatusEntry 5 }

cdrqCmtsCmPollTime OBJECT-TYPE
    SYNTAX TimeStamp
--    Rsyntax TimeTicks
    ACCESS read-only
    STATUS mandatory
    DESCRIPTION
        "The value of sysUpTime when this CM entry was polled.  
        
        If this value is larger than the cdrqCmtsCmPollerStopTime,
        either by receiving it from the 
        cdrqCmtsCmRQDoneNotification or by polling the object 
        itself, it indicates that the status has already been 
        overwritten by a new polling cycle.  To avoid this 
        to happen, the NMS can increase the cdrqCmtsCmPollInterval 
        so that the cdrqCmtsCmPollTime 
        would fall in between the cdrqCmtsCmPollerStartTime and 
        the cdrqCmtsCmPollerStopTime."
    ::= { cdrqCmtsCmStatusEntry 6 }

cdrqCmtsCmRQDoneNotification TRAP-TYPE
-- Reverse mappable trap
    ENTERPRISE ciscoDocsRQNotificationsPrefix
    VARIABLES {
        cdrqCmtsCmPollerStartTime, cdrqCmtsCmPollerStopTime }
--  Status
--    mandatory
    DESCRIPTION
        "This notification is sent when CMTS CM Poller 
        finished polling for the current cycle. 
        
        The cdrqCmtsCmPollerStartTime is the time when the 
        polling cycle started.
        
        The cdrqCmtsCmPollerStopTime is the time when the 
        polling cycle finished."
    ::= 1

cdrqPollerGroup OBJECT IDENTIFIER ::= { cdrqDocsRemoteQueryGroups 1 }
-- OBJECT-GROUP
--  Status
--    mandatory
--  Descr
--    Group of objects implemented in Cable Modem 
--    Termination Systems (CMTS) for configuring and 
--    monitoring the CMTS CM Poller.
--  objects
--    cdrqCmtsCmPollerInterval, cdrqCmtsCmPollerCommunity, 
--    cdrqCmtsCmPollerContextEngineID, cdrqCmtsCmPollerContextName, 
--    cdrqCmtsCmPollerEnable, cdrqCmtsCmPollerStartTime, 
--    cdrqCmtsCmPollerStopTime

cdrqCMGroup OBJECT IDENTIFIER ::= { cdrqDocsRemoteQueryGroups 2 }
-- OBJECT-GROUP
--  Status
--    mandatory
--  Descr
--    Group of objects implemented in Cable Modem 
--    Termination Systems (CMTS) for monitoring cable 
--    modems via CMTS CM Poller.
--  objects
--    cdrqCmtsCmDownChannelPower, cdrqCmtsCmStatusTxPower, 
--    cdrqCmtsCmUpChnlTxTimingOffset, cdrqCmtsCmSigQSignalNoise, 
--    cdrqCmtsCmSigQMicroreflections, cdrqCmtsCmPollTime

cdrqDocsRemoteQueryCompliance OBJECT IDENTIFIER ::= { cdrqDocsRemoteQueryCompliances 1 }
-- MODULE-COMPLIANCE
--  Status
--    mandatory
--  Descr
--    The compliance statement for entities which 
--    implement the Cisco Remote Query MIB
--  Module
--    >>current<<
--   MandGroup
--    cdrqPollerGroup
--   MandGroup
--    cdrqCMGroup


END
