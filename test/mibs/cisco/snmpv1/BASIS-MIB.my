-- MIB file created 17-Jun-2002 14:30:23, by
--   SMICng version 2.2.11-beta(PRO)(Solaris), January 20, 2001. Enterprise key cisco.com

BASIS-MIB DEFINITIONS ::= BEGIN

-- From file: "BASIS-MIB.my"
-- Compile options "4 7 F H N W 03 06 0B 0G 0N 0T"

IMPORTS
    stratacom
            FROM CISCOWAN-SMI;

basis           OBJECT IDENTIFIER ::= { stratacom 110 }
par             OBJECT IDENTIFIER ::= { stratacom 130 }
basisSystem     OBJECT IDENTIFIER ::= { basis 1 }
cardGeneric     OBJECT IDENTIFIER ::= { basis 2 }
cardSpecific    OBJECT IDENTIFIER ::= { basis 3 }
basisLines      OBJECT IDENTIFIER ::= { basis 4 }
basisServices   OBJECT IDENTIFIER ::= { basis 5 }
axisDiagnostics OBJECT IDENTIFIER ::= { basis 6 }
basisShelf      OBJECT IDENTIFIER ::= { basisSystem 1 }
basisAsm        OBJECT IDENTIFIER ::= { basisSystem 2 }
axisRedundancy  OBJECT IDENTIFIER ::= { basisSystem 3 }
axisSvc         OBJECT IDENTIFIER ::= { basisSystem 4 }
atmLmiSignaling OBJECT IDENTIFIER ::= { cardSpecific 4 }
atmAddressRegistration OBJECT IDENTIFIER ::= { axisSvc 1 }
dsx1            OBJECT IDENTIFIER ::= { basisLines 3 }
dsx3            OBJECT IDENTIFIER ::= { basisLines 4 }
x21             OBJECT IDENTIFIER ::= { basisLines 5 }
sonet           OBJECT IDENTIFIER ::= { basisLines 6 }
dsx0Vism        OBJECT IDENTIFIER ::= { basisLines 7 }
dsx1Line        OBJECT IDENTIFIER ::= { dsx1 1 }
dsx1Framing     OBJECT IDENTIFIER ::= { dsx1 2 }
dsx1Plcp        OBJECT IDENTIFIER ::= { dsx1 3 }
dsx3Line        OBJECT IDENTIFIER ::= { dsx3 1 }
dsx3Framing     OBJECT IDENTIFIER ::= { dsx3 2 }
plcp            OBJECT IDENTIFIER ::= { dsx3 3 }
cwsonetObjects  OBJECT IDENTIFIER ::= { sonet 1 }
frameRelay      OBJECT IDENTIFIER ::= { basisServices 1 }
frPort          OBJECT IDENTIFIER ::= { frameRelay 1 }
frChan          OBJECT IDENTIFIER ::= { frameRelay 2 }
frPortCnf       OBJECT IDENTIFIER ::= { frPort 1 }
frPortCnfSig    OBJECT IDENTIFIER ::= { frPortCnf 2 }
frPortCnfX21PortGrp OBJECT IDENTIFIER ::= { frPortCnf 3 }
frPortServiceQueGrp OBJECT IDENTIFIER ::= { frPortCnf 4 }
frPortCnfResPartGrp OBJECT IDENTIFIER ::= { frPortCnf 5 }
frPortCnt       OBJECT IDENTIFIER ::= { frPort 2 }
frPortCntSig    OBJECT IDENTIFIER ::= { frPortCnt 2 }
atm             OBJECT IDENTIFIER ::= { basisServices 2 }
ausmPort        OBJECT IDENTIFIER ::= { atm 1 }
ausmPortCnf     OBJECT IDENTIFIER ::= { ausmPort 1 }
ausmPortCnt     OBJECT IDENTIFIER ::= { ausmPort 3 }
ausmChan        OBJECT IDENTIFIER ::= { atm 2 }
circuitEmulation OBJECT IDENTIFIER ::= { basisServices 3 }
cesmChan        OBJECT IDENTIFIER ::= { circuitEmulation 2 }
sna             OBJECT IDENTIFIER ::= { basisServices 4 }
snaport         OBJECT IDENTIFIER ::= { sna 1 }
snaportCnf      OBJECT IDENTIFIER ::= { snaport 1 }
snaportCnfSig   OBJECT IDENTIFIER ::= { snaportCnf 2 }
snaportCnt      OBJECT IDENTIFIER ::= { snaport 2 }
snaPortCntSig   OBJECT IDENTIFIER ::= { snaportCnt 2 }
voice           OBJECT IDENTIFIER ::= { basisServices 5 }
vismPort        OBJECT IDENTIFIER ::= { voice 2 }
vismChanGrp     OBJECT IDENTIFIER ::= { voice 3 }
vismChanCnfGrp  OBJECT IDENTIFIER ::= { vismChanGrp 1 }
atmLines        OBJECT IDENTIFIER ::= { atm 5 }
bbInterface     OBJECT IDENTIFIER ::= { atm 6 }
bbChan          OBJECT IDENTIFIER ::= { atm 7 }
virtualInterface OBJECT IDENTIFIER ::= { atm 8 }
rpmInterface    OBJECT IDENTIFIER ::= { atm 9 }
rpmChan         OBJECT IDENTIFIER ::= { atm 10 }
atmLineCnfGrp   OBJECT IDENTIFIER ::= { atmLines 1 }
atmLineCntGrp   OBJECT IDENTIFIER ::= { atmLines 2 }
bbIfCnf         OBJECT IDENTIFIER ::= { bbInterface 1 }
bbIfCnfResPartGrp OBJECT IDENTIFIER ::= { bbInterface 2 }
bbIfStateGrp    OBJECT IDENTIFIER ::= { bbInterface 3 }
bbIfCnt         OBJECT IDENTIFIER ::= { bbInterface 4 }
bbChanCnfGrp    OBJECT IDENTIFIER ::= { bbChan 1 }
bbChanStateGrp  OBJECT IDENTIFIER ::= { bbChan 2 }
bbChanCntGrp    OBJECT IDENTIFIER ::= { bbChan 3 }
rpmPort         OBJECT IDENTIFIER ::= { rpmInterface 1 }
rpmChanGrp      OBJECT IDENTIFIER ::= { rpmChan 1 }


END
