-- MIB created 3/18/98 12:43:41, by
--   SMIC (the next generation) version 1.6.29, November 22, 1994.

CISCO-ATM-EXT-MIB DEFINITIONS ::= BEGIN

-- From file: "CISCO-ATM-EXT-MIB.my"

IMPORTS
    Counter32
            FROM SNMPv2-SMI-v1
    OBJECT-TYPE
            FROM RFC-1212
    TruthValue
            FROM SNMPv2-TC-v1
    ciscoMgmt
            FROM CISCO-SMI
    aal5VccVci, aal5VccVpi
            FROM ATM-MIB
    ifIndex
            FROM RFC1213-MIB;

ciscoAtmExtMIB OBJECT IDENTIFIER ::= { ciscoMgmt 88 }
-- MODULE-IDENTITY
--  LastUpdated
--    9706200000Z
--  OrgName
--    Cisco Systems, Inc.
--  ContactInfo
--     Cisco Systems
--     Customer Service
--    
--    Postal: 170 W. Tasman Drive
--     San Jose, CA  95134
--     USA
--    
--       Tel: +1 800 553-NETS
--    
--    E-mail: cs-atm@cisco.com
--  Descr
--    An extension to the Cisco ATM MIB module for managing
--    ATM implementations
--  RevDate
--    9706200000Z
--  RevDescr
--    Initial version of this MIB module.

cAal5VccExtMIBObjects OBJECT IDENTIFIER ::= { ciscoAtmExtMIB 1 }
ciscoAal5ExtMIBConformance OBJECT IDENTIFIER ::= { ciscoAtmExtMIB 3 }
ciscoAal5ExtMIBCompliances OBJECT IDENTIFIER ::= { ciscoAal5ExtMIBConformance 1 }
ciscoAal5ExtMIBGroups OBJECT IDENTIFIER ::= { ciscoAal5ExtMIBConformance 2 }

cAal5VccExtTable OBJECT-TYPE
    SYNTAX SEQUENCE OF CAal5VccExtEntry
    ACCESS not-accessible
    STATUS mandatory
    DESCRIPTION
        "This table contains AAL5 VCC performance
        parameters beyond that provided by cAal5VccEntry."
    ::= { cAal5VccExtMIBObjects 1 }

cAal5VccExtEntry OBJECT-TYPE
    SYNTAX CAal5VccExtEntry
    ACCESS not-accessible
    STATUS mandatory
    DESCRIPTION
        "This list contains the additinal AAL5 VCC performance
        parameters beyond that provided by cAal5VccEntry."
    INDEX { ifIndex, aal5VccVpi, aal5VccVci }
-- Augments aal5VccEntry FROM ATM-MIB
    ::= { cAal5VccExtTable 1 }

CAal5VccExtEntry ::= SEQUENCE {
    cAal5VccExtCompEnabled TruthValue,
    cAal5VccExtVoice TruthValue,
    cAal5VccExtInF5OamCells Counter32,
    cAal5VccExtOutF5OamCells Counter32
    }

cAal5VccExtCompEnabled OBJECT-TYPE
    SYNTAX TruthValue
--    Rsyntax INTEGER {
--        true(1),
--        false(2)
--        }
    ACCESS read-only
    STATUS mandatory
    DESCRIPTION
        "Boolean, if compression enabled for VCC."
    ::= { cAal5VccExtEntry 1 }

cAal5VccExtVoice OBJECT-TYPE
    SYNTAX TruthValue
--    Rsyntax INTEGER {
--        true(1),
--        false(2)
--        }
    ACCESS read-only
    STATUS mandatory
    DESCRIPTION
        "Boolean, TRUE if VCC is used to carry voice."
    ::= { cAal5VccExtEntry 2 }

cAal5VccExtInF5OamCells OBJECT-TYPE
    SYNTAX Counter32
    ACCESS read-only
    STATUS mandatory
    DESCRIPTION
        "Number of OAM F5 end to end loopback cells received through the
        VCC."
    ::= { cAal5VccExtEntry 3 }

cAal5VccExtOutF5OamCells OBJECT-TYPE
    SYNTAX Counter32
    ACCESS read-only
    STATUS mandatory
    DESCRIPTION
        "Number of OAM F5 end to end loopback cells sent through the VCC."
    ::= { cAal5VccExtEntry 4 }

ciscoAal5ExtMIBGroup OBJECT IDENTIFIER ::= { ciscoAal5ExtMIBGroups 1 }
-- OBJECT-GROUP
--  Status
--    mandatory
--  Descr
--    A collection of objects providing AAL5 related parameters.
--  objects
--    cAal5VccExtCompEnabled, cAal5VccExtVoice, 
--    cAal5VccExtInF5OamCells, cAal5VccExtOutF5OamCells

ciscoAal5ExtMIBCompliance OBJECT IDENTIFIER ::= { ciscoAal5ExtMIBCompliances 1 }
-- MODULE-COMPLIANCE
--  Status
--    mandatory
--  Descr
--    The compliance statement for entities which implement
--    this Cisco AAL5 Extention MIB and support data compression
--    or voice features.
--  Module
--    >>current<<
--   MandGroup
--    ciscoAal5ExtMIBGroup


END
