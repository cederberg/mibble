-- MIB file created 08-Mar-2005 11:39:25, by
--   SMICng version 2.2.11-beta(PRO)(Solaris), January 20, 2001. Enterprise key cisco.com

CISCO-ITP-GSCCP-MIB DEFINITIONS ::= BEGIN

-- From file: "CISCO-ITP-GSCCP-MIB.my"
-- Compile options "4 7 F H N O W 03 06 0B 0G 0N 0T"

IMPORTS
    CItpTcDisplayPC, CItpTcGtaLongAddr, CItpTcGtaLongDisplay, 
    CItpTcGtaLongDisplayLen, CItpTcNAI, CItpTcNetworkName, 
    CItpTcNumberingPlan, CItpTcPointCode, CItpTcSubSystemNumber, 
    CItpTcTranslationType, CItpTcTableLoadStatus, CItpTcURL, 
    CItpTcXuaName
            FROM CISCO-ITP-TC-MIB
    cgspCLLICode, cgspEventSequenceNumber, cgspInstNetwork
            FROM CISCO-ITP-GSP-MIB
    RowStatus, TimeStamp, TruthValue
            FROM SNMPv2-TC-v1
    ciscoMgmt
            FROM CISCO-SMI
    Counter, Gauge
            FROM RFC1155-SMI
    OBJECT-TYPE
            FROM RFC-1212
    TRAP-TYPE
            FROM RFC-1215;

ciscoGsccpMIB OBJECT IDENTIFIER ::= { ciscoMgmt 335 }
-- MODULE-IDENTITY
--  LastUpdated
--    200412220000Z
--  OrgName
--    Cisco Systems, Inc.
--  ContactInfo
--           Cisco Systems, Inc
--            Customer Service
--    
--    Postal: 170 W. Tasman Drive
--            San Jose, CA  95134
--            USA
--    
--       Tel: +1 800 553-NETS
--    
--    E-mail: cs-ss7@cisco.com
--  Descr
--    The MIB for signalling Connection Control Part(SCCP)
--     messages transported over Signalling System 
--     No. 7 (SS7) Network via Cisco IP Transfer
--     Point.  
--     
--     This MIB provides information specified
--     in ITU Q752 Monitoring and Measurements for
--     Signalling System No. 7(SS7) Network. 
--    
--     The Cisco IP Transfer Point (ITP) is a hardware 
--     and software solution that transports SS7 traffic 
--     using IP. Each ITP node provides function similar
--     to SS7 Signalling point.   
--     
--     The relevant ITU documents describing this technology
--     is the ITU Q series, including ITU Q.700: Introduction
--     to CCITT Signalling System No. 7 and ITU Q.701 
--     Functional description of the message transfer part
--     (MTP) of Signalling System No. 7.
--    
--     The IETF Working Group Signalling Transport (SIGTRAN)
--     has defined MTP3 User Adaptation (M3UA) and SCCP
--     User Adaptation (SUA) protocols. The drafts can be
--     found at:
--     http://www.ietf.org/html.charters/sigtran-charter.html
--    
--     This MIB consists of the following tables:
--       Instance Table
--       Concerned Point Code List Table
--       Mated Application (MAP) Table
--       Global Title Translation (GTT) Selector Table
--       Global Title Address (GTA) Table
--       Application Group Table
--       Prefix Conversion Table
--       Translation Entries Table
--       Global Title Errors Table
--    
--    
--     Abbreviations:
--       CDPA  - Called Party Address
--       CGPA  - Calling Party Address
--       CLLI  - Common Language Location Codes
--       CR    - Connection Request message
--       CREF  - Connection Refusal message
--       DPC   - Destination Point Code
--       ERR   - Error message
--       GTA   - Global Title Address 
--       GTI   - Global Title Indicator
--       GTT   - Global Title Translation
--       LUDT  - long unitdata message
--       LUDTS - long unitdata service message
--       M2PA  - MTP2 Peer-to-Peer Adaptation Layer
--       M3UA  - MTP3-User Adaptation 
--       MAP   - Mated Application Table
--       MSU   - Message Signal Unit 
--       MTP   - Message Transport Protocol
--       MTP2  - Layer 2 of Message Transport Protocol
--       MTP3  - Layer 3 of Message Transport Protocol
--       NAI   - Nature of Address Indicator
--       NP    - Numbering Plan         
--       OPC   - Originating Point Code
--       PC    - Point Code
--       RTN   - Route Table Name
--       RSR   - Reset Request message
--       SCCP  - Signalling Connection Control Part
--       SCTP  - Stream Transmission Protocol(RFC 2960)
--       SI    - Signalling Indicator
--       SP    - Signalling Point
--       SLC   - Signalling Link Code
--       SLS   - Signalling Link Selector
--       SSN   - Subsystem Number
--       SUA   - SCCP-User Adaptation 
--       TFR   - Transfer Restricted messages  
--       TT    - Title Translation
--       UDT   - unitdata message
--       UDTS  - unitdata service message
--       XUDT  - extended unitdata message
--       XUDTS - extended unitdata service message
--     
--  RevDate
--    200412220000Z
--  RevDescr
--    New cgsccpGttPref2EncodingScheme object to allow 
--     customer to specify encoding scheme when 
--     performing internation translation.
--  RevDate
--    200411160000Z
--  RevDescr
--    New ciscoGsccpGttErrors notification to indicate
--     global title translation errors.
--     
--     The following objects were added to support new
--     notification.
--     
--     cgsccpGttErrorPeriod,
--     cgsccpGttErrorRecoveryCount,
--     cgsccpInstErrorIndicator,
--     cgsccpGttTransErrorsNotifEnabled,
--     cgsccpGttErrorsSelectorNotFound,
--     cgsccpGttErrorsIncorrectFormat,
--     cgsccpGttErrorsGtaNotFound,
--     cgsccpGttErrorsHopViolation,
--     cgsccpGttErrorsMapNotFound,
--     cgsccpGttErrorsUnequipedSS,
--     cgsccpGttErrorsSccpUnavailable,
--     cgsccpGttErrorsDpcUnavailable,
--     cgsccpGttErrorsSsUnavailable,
--     cgsccpGttErrorsDpcCongested,
--     cgsccpGttErrorsSsCongested,
--     cgsccpGttErrorsRouteFailure,
--     cgsccpGttErrorsSccpUnqualified
--  RevDate
--    200404300000Z
--  RevDescr
--    Deprecated table cgsccpGttAppGrTable and added
--     cgsccpGttAppGr2Table.
--     Also added 'cgpa' enumeration to CgsccpGttMultInd
--     textual-convention.
--  RevDate
--    200309300000Z
--  RevDescr
--    Changes to allow cross instance Global title
--     translation.
--     
--     Added following objects:
--          cgsccpGttAppGrNetwork
--          cgsccpGttGtaNetwork
--     
--  RevDate
--    200308210000Z
--  RevDescr
--    Changes to allow GTT prefix conversion 
--     to be specified per instance. 
--      
--     Added the following table:
--        cgsccpGttPref2Table 
--      
--     Deprecated the following table:
--        cgsccpGttPrefTable
--  RevDate
--    200303030000Z
--  RevDescr
--    Initial version of this MIB module.

ciscoGsccpMIBNotifs OBJECT IDENTIFIER ::= { ciscoGsccpMIB 0 }
ciscoGsccpMIBObjects OBJECT IDENTIFIER ::= { ciscoGsccpMIB 1 }
ciscoGsccpMIBConform OBJECT IDENTIFIER ::= { ciscoGsccpMIB 2 }
cgsccpScalars   OBJECT IDENTIFIER ::= { ciscoGsccpMIBObjects 1 }
cgsccpInst      OBJECT IDENTIFIER ::= { ciscoGsccpMIBObjects 2 }
cgsccpGttConPc  OBJECT IDENTIFIER ::= { ciscoGsccpMIBObjects 3 }
cgsccpGttMap    OBJECT IDENTIFIER ::= { ciscoGsccpMIBObjects 4 }
cgsccpGttSel    OBJECT IDENTIFIER ::= { ciscoGsccpMIBObjects 5 }
cgsccpGttGta    OBJECT IDENTIFIER ::= { ciscoGsccpMIBObjects 6 }
cgsccpGttAppGr  OBJECT IDENTIFIER ::= { ciscoGsccpMIBObjects 7 }
cgsccpGttPref   OBJECT IDENTIFIER ::= { ciscoGsccpMIBObjects 8 }
cgsccpGttTranslate OBJECT IDENTIFIER ::= { ciscoGsccpMIBObjects 9 }
cgsccpGttPref2  OBJECT IDENTIFIER ::= { ciscoGsccpMIBObjects 10 }
cgsccpGttAppGr2 OBJECT IDENTIFIER ::= { ciscoGsccpMIBObjects 11 }
cgsccpGttErrors OBJECT IDENTIFIER ::= { ciscoGsccpMIBObjects 12 }
ciscoGsccpMIBCompliances OBJECT IDENTIFIER ::= { ciscoGsccpMIBConform 1 }
ciscoGsccpMIBGroups OBJECT IDENTIFIER ::= { ciscoGsccpMIBConform 2 }

CgsccpConPcListName ::= OCTET STRING(SIZE(0..12))
-- TEXTUAL-CONVENTION
--  Status
--    mandatory
--  Descr
--    The configured name associated with SCCP GTT
--     Concerned Point Code list name.

CgsccpGttSelName ::= OCTET STRING(SIZE(0..12))
-- TEXTUAL-CONVENTION
--  Status
--    mandatory
--  Descr
--    The configured name associated with SCCP GTT
--     Selector.

CgsccpGttAppName ::= OCTET STRING(SIZE(0..12))
-- TEXTUAL-CONVENTION
--  Status
--    mandatory
--  Descr
--    The configured name associated with SCCP GTT
--     Application Group.

CgsccpGttPrefName ::= OCTET STRING(SIZE(0..12))
-- TEXTUAL-CONVENTION
--  Status
--    mandatory
--  Descr
--    The configured name associated with SCCP GTT
--     Prefix Conversion table.
--    
--     This name is supported as octet string containing
--     administrative information in human-readable form.
--    
--     The use of control codes should be avoided.
--    
--     The use of newline should be avoided.
--    
--     The use of leading or trailing white space should
--     be avoided.

CgsccpGttDisplaySS ::= OCTET STRING(SIZE(0..3))
-- TEXTUAL-CONVENTION
--  Status
--    mandatory
--  Descr
--    The subsystem number in display format.

CgsccpGttAppCost ::= Gauge(1..8)
-- TEXTUAL-CONVENTION
--  Status
--    mandatory
--  Descr
--    The cost associated with an entry in SCCP GTT
--     Application Group.

CgsccpGttAppType ::= INTEGER {
        pc(1),
        pcssn(2),
        as(3)
        }
-- TEXTUAL-CONVENTION
--  Status
--    mandatory
--  Descr
--    The list of application types in Application Group
--    'pc'    : The application type is a point code.
--    'pcssn' : The application type is a point code
--              and subsystem number (SSN).
--    'as'    : The application type is an M3UA or SUA
--              Application Server (AS).

CgsccpGttMapType ::= INTEGER {
        primary(1),
        backup(2)
        }
-- TEXTUAL-CONVENTION
--  Status
--    mandatory
--  Descr
--    The list of SCCP GTT Mated Application type
--    'primary' : The mated application is primary
--    'backup'  : The mated application is backup.

CgsccpGttGtaResType ::= INTEGER {
        pc(1),
        pcssn(2),
        app(3),
        as(4)
        }
-- TEXTUAL-CONVENTION
--  Status
--    mandatory
--  Descr
--    The list of SCCP GTT Result Type
--    'pc'    : The GTA translates to a point code.
--    'pcssn' : The GTA translates to a point code
--              and optional SSN
--    'app'   : The GTA translates to a GTT
--              Application Group.
--    'as'    : The GTA translates to an M3UA or
--              SUA Application Server (AS) name.

CgsccpGttRoutingInd ::= INTEGER {
        ri2gt(1),
        ri2ssn(2),
        ssnRI2gt(3),
        ssnRI2ssn(4),
        replTT(5),
        riNotAppl(6),
        riUndef(7)
        }
-- TEXTUAL-CONVENTION
--  Status
--    mandatory
--  Descr
--    The SCCP GTT Routing Indicator
--    'ri2gt'     : Set RI to GT
--    'ri2ssn'    : Set RI to SSN
--    'ssnRI2ssn' : Replace SSN and set RI to GT
--    'ssnRI2gt'  : Replace SSN and set RI to SSN
--    'replTT'    : Replace the TT
--    'riNotAppl' : RI is not applicable
--    'riUndef'   : RI is undefined.

CgsccpGttMapPcStatus ::= INTEGER {
        allowed(1),
        prohibited(2)
        }
-- TEXTUAL-CONVENTION
--  Status
--    mandatory
--  Descr
--    The list of SCCP GTT Mated App point code status
--    'allowed'    : The mated application is allowed
--    'prohibited' : The mated application is prohibited.

CgsccpGttMapSsStatus ::= INTEGER {
        allowed(1),
        prohibited(2)
        }
-- TEXTUAL-CONVENTION
--  Status
--    mandatory
--  Descr
--    The list of SCCP GTT Mated App subsystem status
--    'allowed' : The mated application is allowed
--    'prohibited'   : The mated application is prohibited.

CgsccpGttMultInd ::= INTEGER {
        solitary(1),
        shared(2),
        dominant(3),
        cost(4),
        cgpa(5)
        }
-- TEXTUAL-CONVENTION
--  Status
--    mandatory
--  Descr
--    The list of SCCP GTT Multiplicity Indicator
--    'solitary' : The application is solitary
--    'shared'   : The application is shared
--    'dominant' : The application is dominant
--    'cost'     : The application uses cost
--    'cgpa'     : The application is shared and uses calling
--                 party address and weighting factor.

CgsccpGttMapCongStatus ::= INTEGER {
        notCong(1),
        congLevel1(2),
        congLevel2(3),
        congLevel3(4)
        }
-- TEXTUAL-CONVENTION
--  Status
--    mandatory
--  Descr
--    The list of SCCP GTT Mated App congestion status
--    'NotCong'    : The point code not congested
--    'CongLevel1' : The congestion level 1
--    'CongLevel2' : The congestion level 2
--    'CongLevel3' : The congestion level 3.

CgsccpGttTransType ::= Gauge(0..255)
-- TEXTUAL-CONVENTION
--  Status
--    mandatory
--  Descr
--    The SCCP GTT Translation Type (TT).

CgsccpGttQOS ::= Gauge(0..255)
-- TEXTUAL-CONVENTION
--  Status
--    mandatory
--  Descr
--    The SCCP GTT Quality of Service (QOS).

CgsccpGttGlobalTitleInd ::= Gauge(0..255)
-- TEXTUAL-CONVENTION
--  Status
--    mandatory
--  Descr
--    The SCCP GTT Global Title Indicator (GTI).
--     The following values are generally used:
--      No global title included (0),
--      For ITU,  GT includes NAI only (1),
--      For ANSI, GT includes TT, NP and encoding scheme (1),
--      GT includes only TT (2),
--      GT includes TT, NP and encoding scheme (3),
--      GT includes TT, NP, encoding scheme, NAI (4),
--      Maximum GTI (15),
--      Invalid GTI (253),
--      Wild    GTI (254).
--  Refer
--    The Global Title Indicator is defined in the
--     International Telecommunication Union standard Q.713:
--     Specifications of Signalling System No. 7 - Signalling
--     Connection Control Part (SCCP) section 3.4.1 Address
--     Indicator.

cgsccpGttTranslateSample OBJECT-TYPE
    SYNTAX Gauge(1..60)
--  Units
--    seconds
    ACCESS read-write
    STATUS mandatory
    DESCRIPTION
        "The length of the sample interval used to collect
         number of maximum Global Title Translations per second."
    ::= { cgsccpScalars 1 }

cgsccpGttTranslatePeriod OBJECT-TYPE
    SYNTAX Gauge(1..3600)
--  Units
--    seconds
    ACCESS read-write
    STATUS mandatory
    DESCRIPTION
        "The length of the period used to collect the maximum
         Global Title Translations rate.  Samples are calculated
         for the time period specified by the 
         cgsccpGttTranslateSample object."
    ::= { cgsccpScalars 2 }

cgsccpGttMapStateNotifEnabled OBJECT-TYPE
    SYNTAX TruthValue
--    Rsyntax INTEGER {
--        true(1),
--        false(2)
--        }
    ACCESS read-write
    STATUS mandatory
    DESCRIPTION
        "The Map state notification truth value.
        'true'  Indicates that the ciscoGsccpGttMapStateChange
                notification is to be generated when the
                state changes. That is, the notification
                generation is enabled.
        'false' Indicates that the ciscoGsccpGttMapStateChange
                notification generation is disabled."
    DEFVAL { false }
    ::= { cgsccpScalars 3 }

cgsccpGttLoadTableNotifEnabled OBJECT-TYPE
    SYNTAX TruthValue
--    Rsyntax INTEGER {
--        true(1),
--        false(2)
--        }
    ACCESS read-write
    STATUS mandatory
    DESCRIPTION
        "The GTT load table notification truth value.
        'true'  Indicates that the ciscoGsccpGttLoadTable
                notification is to be generated when the
                a configuration is loaded. That is, the 
                notification generation is enabled.
        'false' Indicates that the ciscoGsccpGttLoadTable
                notification generation is disabled."
    DEFVAL { false }
    ::= { cgsccpScalars 4 }

cgsccpGttTransErrorsNotifEnabled OBJECT-TYPE
    SYNTAX TruthValue
--    Rsyntax INTEGER {
--        true(1),
--        false(2)
--        }
    ACCESS read-write
    STATUS mandatory
    DESCRIPTION
        "The global title translation errors notification truth 
         value as follows.
         
        'true'  Indicates that the ciscoGsccpGttErrors
                notification is to be generated when the
                a configuration is loaded. That is, the 
                notification generation is enabled.
        'false' Indicates that the ciscoGsccpGttErrors
                notification generation is disabled."
    DEFVAL { false }
    ::= { cgsccpScalars 5 }

cgsccpGttErrorPeriod OBJECT-TYPE
    SYNTAX Gauge(30..3600)
--  Units
--    seconds
    ACCESS read-write
    STATUS mandatory
    DESCRIPTION
        "The length of the sample window used to collect 
         global title translations errors."
    DEFVAL { 300 }
    ::= { cgsccpScalars 6 }

cgsccpGttErrorRecoveryCount OBJECT-TYPE
    SYNTAX Gauge(1..10)
--  Units
--    windows
    ACCESS read-write
    STATUS mandatory
    DESCRIPTION
        "The number contiguous sample windows that have to be
         error free before the ciscoGsccpGttErrors notifications
         will be generated indicating end of global title 
         translation errors condition."
    DEFVAL { 3 }
    ::= { cgsccpScalars 7 }

cgsccpInstTable OBJECT-TYPE
    SYNTAX SEQUENCE OF CgsccpInstTableEntry
    ACCESS not-accessible
    STATUS mandatory
    DESCRIPTION
        "SCCP information per instance of signalling
         point."
    ::= { cgsccpInst 1 }

cgsccpInstTableEntry OBJECT-TYPE
    SYNTAX CgsccpInstTableEntry
    ACCESS not-accessible
    STATUS mandatory
    DESCRIPTION
        "Global Title information per instance of 
         signalling point."
    INDEX { cgspInstNetwork }
    ::= { cgsccpInstTable 1 }

CgsccpInstTableEntry ::= SEQUENCE {
    cgsccpInstTotalMsgs Counter,
    cgsccpInstLocalMsgs Counter,
    cgsccpInstTotalGttMsgs Counter,
    cgsccpInstUDTMsgsSent Counter,
    cgsccpInstUDTSMsgsSent Counter,
    cgsccpInstUDTSMsgsAttempted Counter,
    cgsccpInstUDTMsgsRcvd Counter,
    cgsccpInstUDTSMsgsRcvd Counter,
    cgsccpInstXUDTMsgsSent Counter,
    cgsccpInstXUDTSMsgsAttempted Counter,
    cgsccpInstXUDTSMsgsSent Counter,
    cgsccpInstXUDTMsgsRcvd Counter,
    cgsccpInstXUDTSMsgsRcvd Counter,
    cgsccpInstLUDTMsgsSent Counter,
    cgsccpInstLUDTSMsgsSent Counter,
    cgsccpInstLUDTMsgsRcvd Counter,
    cgsccpInstLUDTSMsgsRcvd Counter,
    cgsccpInstCrToMtp Counter,
    cgsccpInstCrefToMtp Counter,
    cgsccpInstCrFromMtp Counter,
    cgsccpInstCrefFromMtp Counter,
    cgsccpInstRsrToMtp Counter,
    cgsccpInstRsrFromMtp Counter,
    cgsccpInstErrToMtp Counter,
    cgsccpInstErrFromMtp Counter,
    cgsccpInstQ752T7E1 Counter,
    cgsccpInstInvalidGttFormat Counter,
    cgsccpInstQ752T7E13 Counter,
    cgsccpInstMapNotFound Counter,
    cgsccpInstQ752T7E7 Counter,
    cgsccpInstGttConfigStatus CItpTcTableLoadStatus,
    cgsccpInstConfigTS TimeStamp,
    cgsccpInstGttConfigTS TimeStamp,
    cgsccpInstLastURL CItpTcURL,
    cgsccpInstConPcTableEntries Gauge,
    cgsccpInstMapTableEntries Gauge,
    cgsccpInstGtaTableEntries Gauge,
    cgsccpInstSelTableEntries Gauge,
    cgsccpInstAppGrTableEntries Gauge,
    cgsccpInstRowStatus RowStatus,
    cgsccpInstPrefTableEntries Gauge,
    cgsccpInstQ752Unqualified Counter,
    cgsccpInstErrorIndicator TruthValue
    }

cgsccpInstTotalMsgs OBJECT-TYPE
    SYNTAX Counter
--  Units
--    packets
    ACCESS read-only
    STATUS mandatory
    DESCRIPTION
        "This counter is incremented every time a message is
         handled from a local or remote subsystem(Q752/9.3)."
    REFERENCE
        "ITU  Q752 Monitoring and Measurements for Signalling
         System No. 7(SS7) Network Table 9.  ANSI GR-82-CORE 
         6.4.3 Translation Type Measurements item 1."
    ::= { cgsccpInstTableEntry 1 }

cgsccpInstLocalMsgs OBJECT-TYPE
    SYNTAX Counter
--  Units
--    packets
    ACCESS read-only
    STATUS mandatory
    DESCRIPTION
        "This counter is incremented every time a message is
         handled from a local subsystem(Q752/9.4)."
    REFERENCE
        "ITU  Q752 Monitoring and Measurements for Signalling
         System No. 7(SS7) Network Table 9."
    ::= { cgsccpInstTableEntry 2 }

cgsccpInstTotalGttMsgs OBJECT-TYPE
    SYNTAX Counter
--  Units
--    packets
    ACCESS read-only
    STATUS mandatory
    DESCRIPTION
        "This counter is incremented every time a message
         requiring global title translation (Q752/9.5) is 
         handled."
    REFERENCE
        "ITU  Q752 Monitoring and Measurements for Signalling
         System No. 7(SS7) Network Table 9.  ANSI GR-82-CORE 
         6.4.2 System Total Measurements Item 7."
    ::= { cgsccpInstTableEntry 3 }

cgsccpInstUDTMsgsSent OBJECT-TYPE
    SYNTAX Counter
--  Units
--    packets
    ACCESS read-only
    STATUS mandatory
    DESCRIPTION
        "This counter is incremented every time a  
         unitdata (UDT) message is sent (Q752/9 bis.1)."
    REFERENCE
        "ITU  Q752 Monitoring and Measurements for Signalling
         System No. 7(SS7) Network Table 9."
    ::= { cgsccpInstTableEntry 4 }

cgsccpInstUDTSMsgsSent OBJECT-TYPE
    SYNTAX Counter
--  Units
--    packets
    ACCESS read-only
    STATUS mandatory
    DESCRIPTION
        "This counter is incremented every time a unitdata
         service (UDTS) message is sent (Q752/9 bis.2)."
    REFERENCE
        "ITU  Q752 Monitoring and Measurements for Signalling
         System No. 7(SS7) Network Table 9."
    ::= { cgsccpInstTableEntry 5 }

cgsccpInstUDTSMsgsAttempted OBJECT-TYPE
    SYNTAX Counter
--  Units
--    packets
    ACCESS read-only
    STATUS mandatory
    DESCRIPTION
        "This counter is incremented every time a unitdata
         service (UDTS) message attempted, but may or may
         not be sent.  The actual number of unitdata
         service (UDTS) message sent is reflected in the
         cgsccpInstUDTSMsgsSent object."
    ::= { cgsccpInstTableEntry 6 }

cgsccpInstUDTMsgsRcvd OBJECT-TYPE
    SYNTAX Counter
--  Units
--    packets
    ACCESS read-only
    STATUS mandatory
    DESCRIPTION
        "This counter is incremented every time a unitdata
         (UDT) message is received (Q752/9 bis.3)."
    REFERENCE
        "ITU  Q752 Monitoring and Measurements for Signalling
         System No. 7(SS7) Network Table 9."
    ::= { cgsccpInstTableEntry 7 }

cgsccpInstUDTSMsgsRcvd OBJECT-TYPE
    SYNTAX Counter
--  Units
--    packets
    ACCESS read-only
    STATUS mandatory
    DESCRIPTION
        "This counter is incremented every time a unitdata 
         service (UDTS) message is received  (Q752/9 bis.4)."
    REFERENCE
        "ITU  Q752 Monitoring and Measurements for Signalling
         System No. 7(SS7) Network Table 9."
    ::= { cgsccpInstTableEntry 8 }

cgsccpInstXUDTMsgsSent OBJECT-TYPE
    SYNTAX Counter
--  Units
--    packets
    ACCESS read-only
    STATUS mandatory
    DESCRIPTION
        "This counter is incremented every time an extended 
         unitdata (XUDT) message is sent (Q752/9 bis.13)."
    REFERENCE
        "ITU  Q752 Monitoring and Measurements for Signalling
         System No. 7(SS7) Network Table 9."
    ::= { cgsccpInstTableEntry 9 }

cgsccpInstXUDTSMsgsAttempted OBJECT-TYPE
    SYNTAX Counter
--  Units
--    packets
    ACCESS read-only
    STATUS mandatory
    DESCRIPTION
        "This counter is incremented every time an extended
         unitdata service (XUDTS) message attempted, but may
         or may not be sent.  The actual number of extended
         unitdata service (UDTS) message sent is reflected 
         in the cgsccpInstXUDTMsgsSent object."
    ::= { cgsccpInstTableEntry 10 }

cgsccpInstXUDTSMsgsSent OBJECT-TYPE
    SYNTAX Counter
--  Units
--    packets
    ACCESS read-only
    STATUS mandatory
    DESCRIPTION
        "This counter is incremented every time an extended 
         unitdata service (XUDTS) message is sent 
         (Q752/9 bis.14)."
    REFERENCE
        "ITU  Q752 Monitoring and Measurements for Signalling
         System No. 7(SS7) Network Table 9."
    ::= { cgsccpInstTableEntry 11 }

cgsccpInstXUDTMsgsRcvd OBJECT-TYPE
    SYNTAX Counter
--  Units
--    packets
    ACCESS read-only
    STATUS mandatory
    DESCRIPTION
        "This counter is incremented every time a extended 
         unitdata (XUDT) message is received (Q752/9 bis.15)."
    REFERENCE
        "ITU  Q752 Monitoring and Measurements for Signalling
         System No. 7(SS7) Network Table 9."
    ::= { cgsccpInstTableEntry 12 }

cgsccpInstXUDTSMsgsRcvd OBJECT-TYPE
    SYNTAX Counter
--  Units
--    packets
    ACCESS read-only
    STATUS mandatory
    DESCRIPTION
        "This counter is incremented every time a extended 
         unitdata service (XUDTS) message is received 
         (Q752/9 bis.16)."
    REFERENCE
        "ITU  Q752 Monitoring and Measurements for Signalling
         System No. 7(SS7) Network Table 9."
    ::= { cgsccpInstTableEntry 13 }

cgsccpInstLUDTMsgsSent OBJECT-TYPE
    SYNTAX Counter
--  Units
--    packets
    ACCESS read-only
    STATUS mandatory
    DESCRIPTION
        "This counter is incremented every time a long 
         unitdata (LUDT) message is sent (Q752/9 bis.17)."
    REFERENCE
        "ITU  Q752 Monitoring and Measurements for Signalling
         System No. 7(SS7) Network Table 9."
    ::= { cgsccpInstTableEntry 14 }

cgsccpInstLUDTSMsgsSent OBJECT-TYPE
    SYNTAX Counter
--  Units
--    packets
    ACCESS read-only
    STATUS mandatory
    DESCRIPTION
        "This counter is incremented every time a long 
         unitdata (LUDT) service message is sent 
         (Q752/9 bis.18)."
    REFERENCE
        "ITU  Q752 Monitoring and Measurements for Signalling
         System No. 7(SS7) Network Table 9."
    ::= { cgsccpInstTableEntry 15 }

cgsccpInstLUDTMsgsRcvd OBJECT-TYPE
    SYNTAX Counter
--  Units
--    packets
    ACCESS read-only
    STATUS mandatory
    DESCRIPTION
        "This counter is incremented every time a long 
         unitdata (LUDT) message is received (Q752/9 bis.19)."
    REFERENCE
        "ITU  Q752 Monitoring and Measurements for Signalling
         System No. 7(SS7) Network Table 9."
    ::= { cgsccpInstTableEntry 16 }

cgsccpInstLUDTSMsgsRcvd OBJECT-TYPE
    SYNTAX Counter
--  Units
--    packets
    ACCESS read-only
    STATUS mandatory
    DESCRIPTION
        "This counter is incremented every time a long 
         unitdata (LUDT) service message is received 
         (Q752/9 bis.20)."
    REFERENCE
        "ITU  Q752 Monitoring and Measurements for Signalling
         System No. 7(SS7) Network Table 9."
    ::= { cgsccpInstTableEntry 17 }

cgsccpInstCrToMtp OBJECT-TYPE
    SYNTAX Counter
--  Units
--    packets
    ACCESS read-only
    STATUS mandatory
    DESCRIPTION
        "This counter is incremented every time a Connection
         Request(CR) messages sent to MTP.  This count 
         include ISDN-UP with embedded CRs (Q752/9 bis.5)."
    REFERENCE
        "ITU  Q752 Monitoring and Measurements for Signalling
         System No. 7(SS7) Network Table 9."
    ::= { cgsccpInstTableEntry 18 }

cgsccpInstCrefToMtp OBJECT-TYPE
    SYNTAX Counter
--  Units
--    packets
    ACCESS read-only
    STATUS mandatory
    DESCRIPTION
        "This counter is incremented every time a Connection
         Refusal (CREF) message is sent to MTP (Q752/9 bis.6)."
    REFERENCE
        "ITU  Q752 Monitoring and Measurements for Signalling
         System No. 7(SS7) Network Table 9."
    ::= { cgsccpInstTableEntry 19 }

cgsccpInstCrFromMtp OBJECT-TYPE
    SYNTAX Counter
--  Units
--    packets
    ACCESS read-only
    STATUS mandatory
    DESCRIPTION
        "This counter is incremented every time a Connection
         Request messages received from MTP. This count
         includes ISDN- UP with embedded CRs (Q752/9 bis.7)."
    REFERENCE
        "ITU  Q752 Monitoring and Measurements for Signalling
         System No. 7(SS7) Network Table 9."
    ::= { cgsccpInstTableEntry 20 }

cgsccpInstCrefFromMtp OBJECT-TYPE
    SYNTAX Counter
--  Units
--    packets
    ACCESS read-only
    STATUS mandatory
    DESCRIPTION
        "This counter is incremented every time a Connection
         Refusal (CREF) message is received from
         MTP (Q752/9 bis.8)."
    REFERENCE
        "ITU  Q752 Monitoring and Measurements for Signalling
         System No. 7(SS7) Network Table 9."
    ::= { cgsccpInstTableEntry 21 }

cgsccpInstRsrToMtp OBJECT-TYPE
    SYNTAX Counter
--  Units
--    packets
    ACCESS read-only
    STATUS mandatory
    DESCRIPTION
        "This counter is incremented every time a Reset Request
         (RSR) message is sent to MTP (Q752/9 bis.9)."
    REFERENCE
        "ITU  Q752 Monitoring and Measurements for Signalling
         System No. 7(SS7) Network Table 9."
    ::= { cgsccpInstTableEntry 22 }

cgsccpInstRsrFromMtp OBJECT-TYPE
    SYNTAX Counter
--  Units
--    packets
    ACCESS read-only
    STATUS mandatory
    DESCRIPTION
        "This counter is incremented every time a Reset Request
         (RSR) message is received from MTP (Q752/9 bis.10)."
    REFERENCE
        "ITU  Q752 Monitoring and Measurements for Signalling
         System No. 7(SS7) Network Table 9."
    ::= { cgsccpInstTableEntry 23 }

cgsccpInstErrToMtp OBJECT-TYPE
    SYNTAX Counter
--  Units
--    packets
    ACCESS read-only
    STATUS mandatory
    DESCRIPTION
        "This counter is incremented every time a Error Message
         (ERR) message is sent to MTP (Q752/9 bis.11)."
    REFERENCE
        "ITU  Q752 Monitoring and Measurements for Signalling
         System No. 7(SS7) Network Table 9."
    ::= { cgsccpInstTableEntry 24 }

cgsccpInstErrFromMtp OBJECT-TYPE
    SYNTAX Counter
--  Units
--    packets
    ACCESS read-only
    STATUS mandatory
    DESCRIPTION
        "This counter is incremented every time a Error Message
         (ERR) message is received from MTP (Q752/9 bis.12)."
    REFERENCE
        "ITU  Q752 Monitoring and Measurements for Signalling
         System No. 7(SS7) Network Table 9."
    ::= { cgsccpInstTableEntry 25 }

cgsccpInstQ752T7E1 OBJECT-TYPE
    SYNTAX Counter
--  Units
--    packets
    ACCESS read-only
    STATUS mandatory
    DESCRIPTION
        "This counter is incremented every time a translation
         was requested for a combination of Translation Type,
         Numbering Plan and Nature of Address for which no 
         translation exists in the signalling point.  This 
         occurs when no selector is available for the 
         combination of parameters provided in the MSU."
    REFERENCE
        "Q752 - Monitoring and measurements for SS7 Network 
         table 7 entry 1. ANSI GR-82-CORE 6.4.2 System Total
         Measurements Item 8."
    ::= { cgsccpInstTableEntry 26 }

cgsccpInstInvalidGttFormat OBJECT-TYPE
    SYNTAX Counter
--  Units
--    packets
    ACCESS read-only
    STATUS mandatory
    DESCRIPTION
        "This counter is incremented every time an invalid 
         Global Title format is found while performing the
         global title translation.  This counter provides 
         information related to the Q752 table 7 entry 8 
         measurement indicating syntax error detected in MSU"
    REFERENCE
        "Q752 - Monitoring and measurements for SS7 Network 
         table 7 entry 8. ANSI GR-82-CORE 
         6.4.2 System Total Measurements Item 9."
    ::= { cgsccpInstTableEntry 27 }

cgsccpInstQ752T7E13 OBJECT-TYPE
    SYNTAX Counter
--  Units
--    packets
    ACCESS read-only
    STATUS mandatory
    DESCRIPTION
        "This counter is incremented every time a
         hop count violation is found in the MSU."
    REFERENCE
        "Q752 - Monitoring and measurements for SS7 Network 
         table 7 entry 13"
    ::= { cgsccpInstTableEntry 28 }

cgsccpInstMapNotFound OBJECT-TYPE
    SYNTAX Counter
--  Units
--    packets
    ACCESS read-only
    STATUS mandatory
    DESCRIPTION
        "This counter is incremented every time a global 
         title translation is successful to a certain
         PC/SSN but it was not found in the GTT 
         Mated Application table."
    ::= { cgsccpInstTableEntry 29 }

cgsccpInstQ752T7E7 OBJECT-TYPE
    SYNTAX Counter
--  Units
--    packets
    ACCESS read-only
    STATUS mandatory
    DESCRIPTION
        "This counter is incremented every time a global 
         title translation could not be performed due to an
         unequipped subsystem (SS)."
    REFERENCE
        "Q752 - Monitoring and measurements for SS7 Network 
         table 7 entry 13"
    ::= { cgsccpInstTableEntry 30 }

cgsccpInstGttConfigStatus OBJECT-TYPE
    SYNTAX CItpTcTableLoadStatus
--    Rsyntax INTEGER {
--        loadNotRequested(1),
--        loadInProgress(2),
--        loadComplete(3),
--        loadCompleteWithErrors(4),
--        loadFailed(5)
--        }
    ACCESS read-only
    STATUS mandatory
    DESCRIPTION
        "The status of the current load or status from
         the prior load operation."
    ::= { cgsccpInstTableEntry 31 }

cgsccpInstConfigTS OBJECT-TYPE
    SYNTAX TimeStamp
--    Rsyntax TimeTicks
    ACCESS read-only
    STATUS mandatory
    DESCRIPTION
        "The value of sysUpTime at the time of the last creation
         or deletion or modification of an entry in the 
         cgsccpGttConPcTable, cgsccpGttMapTable, 
         cgsccpGttSelTable, cgsccpGttGtaTable,  
         cgsccpGttAppGr2Table, or cgsccpGttPref2Table.
          
         If the local network management subsystem is 
         re-initialization, then this object contains the 
         sysUpTime at the time when this occurred. This value 
         can be used to prevent unnecessary walks of the 
         these tables."
    ::= { cgsccpInstTableEntry 32 }

cgsccpInstGttConfigTS OBJECT-TYPE
    SYNTAX TimeStamp
--    Rsyntax TimeTicks
    ACCESS read-only
    STATUS mandatory
    DESCRIPTION
        "The value of sysUpTime at the time of the last
         load of the GTT table using file format."
    ::= { cgsccpInstTableEntry 33 }

cgsccpInstLastURL OBJECT-TYPE
    SYNTAX CItpTcURL
--    Rsyntax OCTET STRING(SIZE(0..255))
    ACCESS read-only
    STATUS mandatory
    DESCRIPTION
        "The URL used to load GTT tables."
    ::= { cgsccpInstTableEntry 34 }

cgsccpInstConPcTableEntries OBJECT-TYPE
    SYNTAX Gauge
--  Units
--    entries
    ACCESS read-only
    STATUS mandatory
    DESCRIPTION
        "The number of entries in the cgsccpGttConPcTable
         Table for this instance.  Or in other words,
         the number concerned point-code entries for this
         signalling point."
    ::= { cgsccpInstTableEntry 35 }

cgsccpInstMapTableEntries OBJECT-TYPE
    SYNTAX Gauge
--  Units
--    entries
    ACCESS read-only
    STATUS mandatory
    DESCRIPTION
        "The number of entries in the cgsccpGttMapTable 
         Table for this instance.  Or in other words,
         the number of GTT Mated Application entries 
         for this signalling point."
    ::= { cgsccpInstTableEntry 36 }

cgsccpInstGtaTableEntries OBJECT-TYPE
    SYNTAX Gauge
--  Units
--    entries
    ACCESS read-only
    STATUS mandatory
    DESCRIPTION
        "The number of entries in the cgsccpGttGtaTable 
         Table for this instance.  Or in other words,
         the number of GTT Global Title Address Table 
         entries for this signalling point."
    ::= { cgsccpInstTableEntry 37 }

cgsccpInstSelTableEntries OBJECT-TYPE
    SYNTAX Gauge
--  Units
--    entries
    ACCESS read-only
    STATUS mandatory
    DESCRIPTION
        "The number of entries in the cgsccpGttSelTable 
         Table for this instance.  Or in other words,
         the number of GTT Selector Table entries for 
         this signalling point."
    ::= { cgsccpInstTableEntry 38 }

cgsccpInstAppGrTableEntries OBJECT-TYPE
    SYNTAX Gauge
--  Units
--    entries
    ACCESS read-only
    STATUS mandatory
    DESCRIPTION
        "The number of entries in the cgsccpGttAppGrTable 
         Table for this instance.  Or in other words,
         the number of GTT Application Group Table entries
         for this signalling point."
    ::= { cgsccpInstTableEntry 39 }

cgsccpInstRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpInstTable
         following the RowStatus textual convention."
    ::= { cgsccpInstTableEntry 40 }

cgsccpInstPrefTableEntries OBJECT-TYPE
    SYNTAX Gauge
--  Units
--    entries
    ACCESS read-only
    STATUS mandatory
    DESCRIPTION
        "The number of entries in the cgsccpGttPref2Table 
         Table for this instance.  Or in other words,
         the number of GTT prefix conversion table entries
         for this signalling point."
    ::= { cgsccpInstTableEntry 41 }

cgsccpInstQ752Unqualified OBJECT-TYPE
    SYNTAX Counter
--  Units
--    packets
    ACCESS read-only
    STATUS mandatory
    DESCRIPTION
        "This counter is incremented every time a global 
         title translation is unsuccessful and the error
         type not covered by other specific error types."
    ::= { cgsccpInstTableEntry 42 }

cgsccpInstErrorIndicator OBJECT-TYPE
    SYNTAX TruthValue
--    Rsyntax INTEGER {
--        true(1),
--        false(2)
--        }
    ACCESS read-only
    STATUS mandatory
    DESCRIPTION
        "This object indicates whether global title 
         translation errors have occurred in last interval
         specified by the cgsccpGttErrorPeriod object."
    DEFVAL { false }
    ::= { cgsccpInstTableEntry 43 }

cgsccpGttConPcTable OBJECT-TYPE
    SYNTAX SEQUENCE OF CgsccpGttConPcTableEntry
    ACCESS not-accessible
    STATUS mandatory
    DESCRIPTION
        "A table of concerned point codes."
    ::= { cgsccpGttConPc 1 }

cgsccpGttConPcTableEntry OBJECT-TYPE
    SYNTAX CgsccpGttConPcTableEntry
    ACCESS not-accessible
    STATUS mandatory
    DESCRIPTION
        "A list of concerned point codes."
    INDEX { cgspInstNetwork, cgsccpGttConPcListName, cgsccpGttConPointCode }
    ::= { cgsccpGttConPcTable 1 }

CgsccpGttConPcTableEntry ::= SEQUENCE {
    cgsccpGttConPcListName CgsccpConPcListName,
    cgsccpGttConPointCode CItpTcPointCode,
    cgsccpGttConPcRowStatus RowStatus
    }

cgsccpGttConPcListName OBJECT-TYPE
    SYNTAX CgsccpConPcListName
--    Rsyntax OCTET STRING(SIZE(0..12))
    ACCESS not-accessible
    STATUS mandatory
    DESCRIPTION
        "The name of the Concerned Point Code list."
    ::= { cgsccpGttConPcTableEntry 1 }

cgsccpGttConPointCode OBJECT-TYPE
    SYNTAX CItpTcPointCode
--    Rsyntax Gauge(0..16777216)
    ACCESS not-accessible
    STATUS mandatory
    DESCRIPTION
        "The concerned point code for SCCP GTT."
    ::= { cgsccpGttConPcTableEntry 2 }

cgsccpGttConPcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpGttConPcTable
         following the RowStatus textual convention."
    ::= { cgsccpGttConPcTableEntry 3 }

cgsccpGttAppGrTable OBJECT-TYPE
    SYNTAX SEQUENCE OF CgsccpGttAppGrTableEntry
    ACCESS not-accessible
    STATUS deprecated
    DESCRIPTION
        "A table of SCCP GTT Application Group Table entries."
    ::= { cgsccpGttAppGr 1 }

cgsccpGttAppGrTableEntry OBJECT-TYPE
    SYNTAX CgsccpGttAppGrTableEntry
    ACCESS not-accessible
    STATUS deprecated
    DESCRIPTION
        "A list of SCCP GTT Application Group attributes."
    INDEX { cgspInstNetwork, cgsccpGttAppGrName, cgsccpGttAppGrCost, cgsccpGttAppGrEntNum }
    ::= { cgsccpGttAppGrTable 1 }

CgsccpGttAppGrTableEntry ::= SEQUENCE {
    cgsccpGttAppGrName CgsccpGttAppName,
    cgsccpGttAppGrCost CgsccpGttAppCost,
    cgsccpGttAppGrEntNum Gauge,
    cgsccpGttAppGrType CgsccpGttAppType,
    cgsccpGttAppGrPc CItpTcPointCode,
    cgsccpGttAppGrSsn CItpTcSubSystemNumber,
    cgsccpGttAppGrRi CgsccpGttRoutingInd,
    cgsccpGttAppGrMult CgsccpGttMultInd,
    cgsccpGttAppGrRefCount Gauge,
    cgsccpGttAppGrAsName CItpTcXuaName,
    cgsccpGttAppGrNewSsn CItpTcSubSystemNumber,
    cgsccpGttAppGrNumUsed Counter,
    cgsccpGttAppGrRowStatus RowStatus,
    cgsccpGttAppGrNetwork CItpTcNetworkName
    }

cgsccpGttAppGrName OBJECT-TYPE
    SYNTAX CgsccpGttAppName
--    Rsyntax OCTET STRING(SIZE(0..12))
    ACCESS not-accessible
    STATUS deprecated
    DESCRIPTION
        "The GTT Application Group name."
    ::= { cgsccpGttAppGrTableEntry 1 }

cgsccpGttAppGrCost OBJECT-TYPE
    SYNTAX CgsccpGttAppCost
--    Rsyntax Gauge(1..8)
    ACCESS not-accessible
    STATUS deprecated
    DESCRIPTION
        "The cost for the item in the GTT Application Group."
    ::= { cgsccpGttAppGrTableEntry 2 }

cgsccpGttAppGrEntNum OBJECT-TYPE
    SYNTAX Gauge(0..65535)
    ACCESS not-accessible
    STATUS deprecated
    DESCRIPTION
        "The entry number used to identify each application 
         group entry that have the same cost."
    ::= { cgsccpGttAppGrTableEntry 3 }

cgsccpGttAppGrType OBJECT-TYPE
    SYNTAX CgsccpGttAppType
--    Rsyntax INTEGER {
--        pc(1),
--        pcssn(2),
--        as(3)
--        }
    ACCESS read-write
    STATUS deprecated
    DESCRIPTION
        "The type of the item in the GTT Application Group."
    ::= { cgsccpGttAppGrTableEntry 4 }

cgsccpGttAppGrPc OBJECT-TYPE
    SYNTAX CItpTcPointCode
--    Rsyntax Gauge(0..16777216)
    ACCESS read-write
    STATUS deprecated
    DESCRIPTION
        "The point code specified by the item in the GTT
         Application Group.  When the cgsccpGttAppGrType
         object has 'pc' or pcssn' values this object 
         is required when entry is created.  Otherwise,
         this value does not apply and can default to 
         zero."
    DEFVAL { 0 }
    ::= { cgsccpGttAppGrTableEntry 5 }

cgsccpGttAppGrSsn OBJECT-TYPE
    SYNTAX CItpTcSubSystemNumber
--    Rsyntax Gauge(0|2..255)
    ACCESS read-write
    STATUS deprecated
    DESCRIPTION
        "The subsystem number (SSN) specified by the item
         in the GTT Application Group. It is valid only when
         cgsccpGttAppGrType is 'pcssn'. Otherwise it is zero."
    DEFVAL { 0 }
    ::= { cgsccpGttAppGrTableEntry 6 }

cgsccpGttAppGrRi OBJECT-TYPE
    SYNTAX CgsccpGttRoutingInd
--    Rsyntax INTEGER {
--        ri2gt(1),
--        ri2ssn(2),
--        ssnRI2gt(3),
--        ssnRI2ssn(4),
--        replTT(5),
--        riNotAppl(6),
--        riUndef(7)
--        }
    ACCESS read-write
    STATUS deprecated
    DESCRIPTION
        "The routing indicator (RI) specified by the item
         in the GTT Application Group."
    ::= { cgsccpGttAppGrTableEntry 7 }

cgsccpGttAppGrMult OBJECT-TYPE
    SYNTAX CgsccpGttMultInd
--    Rsyntax INTEGER {
--        solitary(1),
--        shared(2),
--        dominant(3),
--        cost(4),
--        cgpa(5)
--        }
    ACCESS read-write
    STATUS deprecated
    DESCRIPTION
        "The multiplicity of the GTT Application Group."
    ::= { cgsccpGttAppGrTableEntry 8 }

cgsccpGttAppGrRefCount OBJECT-TYPE
    SYNTAX Gauge(0..2147483647)
    ACCESS read-only
    STATUS deprecated
    DESCRIPTION
        "The number of global title addresses referring to 
         this application group."
    ::= { cgsccpGttAppGrTableEntry 9 }

cgsccpGttAppGrAsName OBJECT-TYPE
    SYNTAX CItpTcXuaName
--    Rsyntax OCTET STRING(SIZE(0..12))
    ACCESS read-write
    STATUS deprecated
    DESCRIPTION
        "The Application Server (AS) name specified by the item
         in the GTT Application Group. It is valid only when
         cgsccpGttAppGrType is 'as'. Otherwise it
         is a zero length string."
    DEFVAL { "" }
    ::= { cgsccpGttAppGrTableEntry 10 }

cgsccpGttAppGrNewSsn OBJECT-TYPE
    SYNTAX CItpTcSubSystemNumber
--    Rsyntax Gauge(0|2..255)
    ACCESS read-write
    STATUS deprecated
    DESCRIPTION
        "The new subsystem number (SSN) specified by the item
         in the GTT Application Group.  It is valid only when
         cgsccpGttAppGrType is 'as'.  Otherwise it is zero."
    DEFVAL { 0 }
    ::= { cgsccpGttAppGrTableEntry 11 }

cgsccpGttAppGrNumUsed OBJECT-TYPE
    SYNTAX Counter
    ACCESS read-only
    STATUS deprecated
    DESCRIPTION
        "The number of times this item in the GTT Application
         Group is used successfully."
    ::= { cgsccpGttAppGrTableEntry 12 }

cgsccpGttAppGrRowStatus OBJECT-TYPE
    SYNTAX RowStatus
--    Rsyntax INTEGER {
--        active(1),
--        notInService(2),
--        notReady(3),
--        createAndGo(4),
--        createAndWait(5),
--        destroy(6)
--        }
    ACCESS read-write
    STATUS deprecated
    DESCRIPTION
        "The object is used by a management station to 
         create or delete the row entry in cgsccpGttAppGrTable
         following the RowStatus textual convention."
    ::= { cgsccpGttAppGrTableEntry 13 }

cgsccpGttAppGrNetwork OBJECT-TYPE
    SYNTAX CItpTcNetworkName
--    Rsyntax OCTET STRING(SIZE(0..19))
    ACCESS read-write
    STATUS deprecated
    DESCRIPTION
        "The processing of global title translation may
         result in a packet being transferred from one
         network to another.  This object specifies
         the target network."
    ::= { cgsccpGttAppGrTableEntry 14 }

cgsccpGttMapTable OBJECT-TYPE
    SYNTAX SEQUENCE OF CgsccpGttMapTableEntry
    ACCESS not-accessible
    STATUS mandatory
    DESCRIPTION
        "A table of SCCP GTT Mated Application (MAP) entries."
    ::= { cgsccpGttMap 1 }

cgsccpGttMapTableEntry OBJECT-TYPE
    SYNTAX CgsccpGttMapTableEntry
    ACCESS not-accessible
    STATUS mandatory
    DESCRIPTION
        "A list of SCCP GTT MAP attributes."
    INDEX { cgspInstNetwork, cgsccpGttMapPc, cgsccpGttMapSsn }
    ::= { cgsccpGttMapTable 1 }

CgsccpGttMapTableEntry ::= SEQUENCE {
    cgsccpGttMapPc CItpTcPointCode,
    cgsccpGttMapSsn CItpTcSubSystemNumber,
    cgsccpGttMapDisplayPC CItpTcDisplayPC,
    cgsccpGttMapDisplaySS CgsccpGttDisplaySS,
    cgsccpGttMapType CgsccpGttMapType,
    cgsccpGttMapPcStatus CgsccpGttMapPcStatus,
    cgsccpGttMapSsStatus CgsccpGttMapSsStatus,
    cgsccpGttMapMultInd CgsccpGttMultInd,
    cgsccpGttMapBackupPc CItpTcPointCode,
    cgsccpGttMapBackupSsn CItpTcSubSystemNumber,
    cgsccpGttMapConPcList CgsccpConPcListName,
    cgsccpGttMapReRouteOnCong TruthValue,
    cgsccpGttMapAdjacent TruthValue,
    cgsccpGttMapLastSsUsed TruthValue,
    cgsccpGttMapUsed Counter,
    cgsccpGttMapAltUsed Counter,
    cgsccpGttMapSccpUnavail Counter,
    cgsccpGttMapQ752T7E3Fail Counter,
    cgsccpGttMapQ752T7E3Un Counter,
    cgsccpGttMapQ752T7E4 Counter,
    cgsccpGttMapQ752T7E5 Counter,
    cgsccpGttMapQ752T7E6 Counter,
    cgsccpGttMapRefCount Gauge,
    cgsccpGttMapCongStatus CgsccpGttMapCongStatus,
    cgsccpGttMapRowStatus RowStatus
    }

cgsccpGttMapPc OBJECT-TYPE
    SYNTAX CItpTcPointCode
--    Rsyntax Gauge(0..16777216)
    ACCESS not-accessible
    STATUS mandatory
    DESCRIPTION
        "The point code for GTT MAP entry."
    ::= { cgsccpGttMapTableEntry 1 }

cgsccpGttMapSsn OBJECT-TYPE
    SYNTAX CItpTcSubSystemNumber
--    Rsyntax Gauge(0|2..255)
    ACCESS not-accessible
    STATUS mandatory
    DESCRIPTION
        "The subsystem number (SSN) for GTT MAP entry."
    ::= { cgsccpGttMapTableEntry 2 }

cgsccpGttMapDisplayPC OBJECT-TYPE
    SYNTAX CItpTcDisplayPC
--    Rsyntax OCTET STRING(SIZE(1..12))
    ACCESS read-only
    STATUS mandatory
    DESCRIPTION
        "The MAP point code in display format."
    ::= { cgsccpGttMapTableEntry 3 }

cgsccpGttMapDisplaySS OBJECT-TYPE
    SYNTAX CgsccpGttDisplaySS
--    Rsyntax OCTET STRING(SIZE(0..3))
    ACCESS read-only
    STATUS mandatory
    DESCRIPTION
        "The MAP subsystem number in display format."
    ::= { cgsccpGttMapTableEntry 4 }

cgsccpGttMapType OBJECT-TYPE
    SYNTAX CgsccpGttMapType
--    Rsyntax INTEGER {
--        primary(1),
--        backup(2)
--        }
    ACCESS read-write
    STATUS mandatory
    DESCRIPTION
        "The GTT MAP subsystem type."
    ::= { cgsccpGttMapTableEntry 5 }

cgsccpGttMapPcStatus OBJECT-TYPE
    SYNTAX CgsccpGttMapPcStatus
--    Rsyntax INTEGER {
--        allowed(1),
--        prohibited(2)
--        }
    ACCESS read-only
    STATUS mandatory
    DESCRIPTION
        "The GTT MAP point code status."
    ::= { cgsccpGttMapTableEntry 6 }

cgsccpGttMapSsStatus OBJECT-TYPE
    SYNTAX CgsccpGttMapSsStatus
--    Rsyntax INTEGER {
--        allowed(1),
--        prohibited(2)
--        }
    ACCESS read-only
    STATUS mandatory
    DESCRIPTION
        "The GTT MAP subsystem status."
    ::= { cgsccpGttMapTableEntry 7 }

cgsccpGttMapMultInd OBJECT-TYPE
    SYNTAX CgsccpGttMultInd
--    Rsyntax INTEGER {
--        solitary(1),
--        shared(2),
--        dominant(3),
--        cost(4),
--        cgpa(5)
--        }
    ACCESS read-write
    STATUS mandatory
    DESCRIPTION
        "The GTT mated application multiplicity indicator."
    ::= { cgsccpGttMapTableEntry 8 }

cgsccpGttMapBackupPc OBJECT-TYPE
    SYNTAX CItpTcPointCode
--    Rsyntax Gauge(0..16777216)
    ACCESS read-write
    STATUS mandatory
    DESCRIPTION
        "The backup point code for the mated Application. 
         The special value of zero indicates that no backup
         point code has been specified."
    DEFVAL { 0 }
    ::= { cgsccpGttMapTableEntry 9 }

cgsccpGttMapBackupSsn OBJECT-TYPE
    SYNTAX CItpTcSubSystemNumber
--    Rsyntax Gauge(0|2..255)
    ACCESS read-write
    STATUS mandatory
    DESCRIPTION
        "The backup subsystem number for the mated
         Application.  The special value of zero indicates
         that no backup subsystem number has been 
         specified."
    DEFVAL { 0 }
    ::= { cgsccpGttMapTableEntry 10 }

cgsccpGttMapConPcList OBJECT-TYPE
    SYNTAX CgsccpConPcListName
--    Rsyntax OCTET STRING(SIZE(0..12))
    ACCESS read-write
    STATUS mandatory
    DESCRIPTION
        "The concerned point code list for the mated
         Application.  The null string indicates that
         no concerned point code list has been specified."
    DEFVAL { "" }
    ::= { cgsccpGttMapTableEntry 11 }

cgsccpGttMapReRouteOnCong OBJECT-TYPE
    SYNTAX TruthValue
--    Rsyntax INTEGER {
--        true(1),
--        false(2)
--        }
    ACCESS read-write
    STATUS mandatory
    DESCRIPTION
        "The GTT Mated App re-route on congestion truth value.
         'true'  Re-routing on congestion is enabled.
         'false' Re-routing on congestion is disabled."
    DEFVAL { false }
    ::= { cgsccpGttMapTableEntry 12 }

cgsccpGttMapAdjacent OBJECT-TYPE
    SYNTAX TruthValue
--    Rsyntax INTEGER {
--        true(1),
--        false(2)
--        }
    ACCESS read-write
    STATUS mandatory
    DESCRIPTION
        "The GTT Mated App Point Code adjacent truth value.
         'true'  Indicates that MAP PC is adjacent.
         'false' Indicates that MAP PC is not adjacent."
    DEFVAL { false }
    ::= { cgsccpGttMapTableEntry 13 }

cgsccpGttMapLastSsUsed OBJECT-TYPE
    SYNTAX TruthValue
--    Rsyntax INTEGER {
--        true(1),
--        false(2)
--        }
    ACCESS read-only
    STATUS mandatory
    DESCRIPTION
        "The GTT MAP last subsystem used truth value.
         'true'  It is the last used subsystem.
         'false' It is not the last used subsystem."
    ::= { cgsccpGttMapTableEntry 14 }

cgsccpGttMapUsed OBJECT-TYPE
    SYNTAX Counter
--  Units
--    messages
    ACCESS read-only
    STATUS mandatory
    DESCRIPTION
        "This counter is incremented every time a message is
         routed by the GTT Mated Application."
    ::= { cgsccpGttMapTableEntry 15 }

cgsccpGttMapAltUsed OBJECT-TYPE
    SYNTAX Counter
--  Units
--    messages
    ACCESS read-only
    STATUS mandatory
    DESCRIPTION
        "This counter is incremented every time a message is
         re-routed on congestion by the GTT Mated Application."
    REFERENCE
        "ANSI GR-82-CORE 6.4.2 System Total Measurements Item 12."
    ::= { cgsccpGttMapTableEntry 16 }

cgsccpGttMapSccpUnavail OBJECT-TYPE
    SYNTAX Counter
--  Units
--    occurrences
    ACCESS read-only
    STATUS mandatory
    DESCRIPTION
        "This counter is incremented every time a SCCP
         is unavailable at the GTT Mated Application."
    ::= { cgsccpGttMapTableEntry 17 }

cgsccpGttMapQ752T7E3Fail OBJECT-TYPE
    SYNTAX Counter
--  Units
--    occurrences
    ACCESS read-only
    STATUS mandatory
    DESCRIPTION
        "This counter is incremented every time a the MTP3
         layer failed at the GTT Mated Application."
    REFERENCE
        "Q752 - Monitoring and measurements for SS7 Network 
         table 7 entry 3"
    ::= { cgsccpGttMapTableEntry 18 }

cgsccpGttMapQ752T7E3Un OBJECT-TYPE
    SYNTAX Counter
--  Units
--    occurrences
    ACCESS read-only
    STATUS mandatory
    DESCRIPTION
        "This counter is incremented every time a point code
         is unavailable at the GTT Mated Application."
    ::= { cgsccpGttMapTableEntry 19 }

cgsccpGttMapQ752T7E4 OBJECT-TYPE
    SYNTAX Counter
--  Units
--    occurrences
    ACCESS read-only
    STATUS mandatory
    DESCRIPTION
        "This counter is incremented every time a point code
         is congested at the GTT Mated Application."
    REFERENCE
        "Q752 - Monitoring and measurements for SS7 Network 
         table 7 entry 4"
    ::= { cgsccpGttMapTableEntry 20 }

cgsccpGttMapQ752T7E5 OBJECT-TYPE
    SYNTAX Counter
--  Units
--    occurrences
    ACCESS read-only
    STATUS mandatory
    DESCRIPTION
        "This counter is incremented every time a subsystem
         is unavailable at the GTT Mated Application."
    REFERENCE
        "Q752 - Monitoring and measurements for SS7 Network 
         table 7 entry 5"
    ::= { cgsccpGttMapTableEntry 21 }

cgsccpGttMapQ752T7E6 OBJECT-TYPE
    SYNTAX Counter
--  Units
--    occurrences
    ACCESS read-only
    STATUS mandatory
    DESCRIPTION
        "This counter is incremented every time a subsystem
         is congested at the GTT Mated Application."
    REFERENCE
        "Q752 - Monitoring and measurements for SS7 Network 
         table 7 entry 6"
    ::= { cgsccpGttMapTableEntry 22 }

cgsccpGttMapRefCount OBJECT-TYPE
    SYNTAX Gauge(0..2147483647)
    ACCESS read-only
    STATUS mandatory
    DESCRIPTION
        "The number of global title addresses referring to this
         MAP entry."
    ::= { cgsccpGttMapTableEntry 23 }

cgsccpGttMapCongStatus OBJECT-TYPE
    SYNTAX CgsccpGttMapCongStatus
--    Rsyntax INTEGER {
--        notCong(1),
--        congLevel1(2),
--        congLevel2(3),
--        congLevel3(4)
--        }
    ACCESS read-only
    STATUS mandatory
    DESCRIPTION
        "The status of congestion level for this MAP point code."
    ::= { cgsccpGttMapTableEntry 24 }

cgsccpGttMapRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpGttMapTable
         following the RowStatus textual convention."
    ::= { cgsccpGttMapTableEntry 25 }

cgsccpGttSelTable OBJECT-TYPE
    SYNTAX SEQUENCE OF CgsccpGttSelTableEntry
    ACCESS not-accessible
    STATUS mandatory
    DESCRIPTION
        "A table of SCCP GTT Selector entries."
    ::= { cgsccpGttSel 1 }

cgsccpGttSelTableEntry OBJECT-TYPE
    SYNTAX CgsccpGttSelTableEntry
    ACCESS not-accessible
    STATUS mandatory
    DESCRIPTION
        "A list of SCCP GTT Selector attributes."
    INDEX { cgspInstNetwork, cgsccpGttSelTT, cgsccpGttSelNAI, cgsccpGttSelNP, cgsccpGttSelGTI }
    ::= { cgsccpGttSelTable 1 }

CgsccpGttSelTableEntry ::= SEQUENCE {
    cgsccpGttSelTT CgsccpGttTransType,
    cgsccpGttSelNAI CItpTcNAI,
    cgsccpGttSelNP CItpTcNumberingPlan,
    cgsccpGttSelGTI CgsccpGttGlobalTitleInd,
    cgsccpGttSelName CgsccpGttSelName,
    cgsccpGttSelNumPerf Counter,
    cgsccpGttQ752T7E2 Counter,
    cgsccpGttSelQOS CgsccpGttQOS,
    cgsccpGttSelRefCount Gauge,
    cgsccpGttSelPrePrefConv CgsccpGttPrefName,
    cgsccpGttSelPostPrefConv CgsccpGttPrefName,
    cgsccpGttSelRowStatus RowStatus
    }

cgsccpGttSelTT OBJECT-TYPE
    SYNTAX CgsccpGttTransType
--    Rsyntax Gauge(0..255)
    ACCESS not-accessible
    STATUS mandatory
    DESCRIPTION
        "Translation Type (TT) for this GTT Selector."
    ::= { cgsccpGttSelTableEntry 1 }

cgsccpGttSelNAI OBJECT-TYPE
    SYNTAX CItpTcNAI
--    Rsyntax INTEGER(0..255)
    ACCESS not-accessible
    STATUS mandatory
    DESCRIPTION
        "Nature of Address Indicator (NAI) for GTT Selector."
    ::= { cgsccpGttSelTableEntry 2 }

cgsccpGttSelNP OBJECT-TYPE
    SYNTAX CItpTcNumberingPlan
--    Rsyntax INTEGER(0..255)
    ACCESS not-accessible
    STATUS mandatory
    DESCRIPTION
        "Numbering Plan (NP) for this GTT Selector."
    ::= { cgsccpGttSelTableEntry 3 }

cgsccpGttSelGTI OBJECT-TYPE
    SYNTAX CgsccpGttGlobalTitleInd
--    Rsyntax Gauge(0..255)
    ACCESS not-accessible
    STATUS mandatory
    DESCRIPTION
        "Global Title Indicator (GTI) for
         this GTT Selector."
    ::= { cgsccpGttSelTableEntry 4 }

cgsccpGttSelName OBJECT-TYPE
    SYNTAX CgsccpGttSelName
--    Rsyntax OCTET STRING(SIZE(0..12))
    ACCESS read-write
    STATUS mandatory
    DESCRIPTION
        "The name of the GTT selector."
    ::= { cgsccpGttSelTableEntry 5 }

cgsccpGttSelNumPerf OBJECT-TYPE
    SYNTAX Counter
    ACCESS read-only
    STATUS mandatory
    DESCRIPTION
        "This counter is incremented every time a global title
         translations is performed using this GTT Selector."
    ::= { cgsccpGttSelTableEntry 6 }

cgsccpGttQ752T7E2 OBJECT-TYPE
    SYNTAX Counter
    ACCESS read-only
    STATUS mandatory
    DESCRIPTION
        "This counter is incremented every time a global title
         title translations was required and a selector was 
         not found."
    REFERENCE
        "Q752 - Monitoring and measurements for SS7 Network 
         table 7 entry 2. ANSI GR-82-CORE 6.4.2 System 
         Total Measurements Item 10."
    ::= { cgsccpGttSelTableEntry 7 }

cgsccpGttSelQOS OBJECT-TYPE
    SYNTAX CgsccpGttQOS
--    Rsyntax Gauge(0..255)
    ACCESS read-write
    STATUS mandatory
    DESCRIPTION
        "The SCCP GTT Selector specifies the QOS."
    DEFVAL { 0 }
    ::= { cgsccpGttSelTableEntry 8 }

cgsccpGttSelRefCount OBJECT-TYPE
    SYNTAX Gauge(0..2147483647)
    ACCESS read-only
    STATUS mandatory
    DESCRIPTION
        "The number of entries in the global title addresses
         that belong to this selector."
    ::= { cgsccpGttSelTableEntry 9 }

cgsccpGttSelPrePrefConv OBJECT-TYPE
    SYNTAX CgsccpGttPrefName
--    Rsyntax OCTET STRING(SIZE(0..12))
    ACCESS read-write
    STATUS mandatory
    DESCRIPTION
        "The Prefix Conversion Table is used to convert
         GTA digits.  This object specifies that the
         conversion occurs 'before' global title
         translation.  The null string indicates
         that a prefix conversion table has not been
         specified."
    DEFVAL { "" }
    ::= { cgsccpGttSelTableEntry 10 }

cgsccpGttSelPostPrefConv OBJECT-TYPE
    SYNTAX CgsccpGttPrefName
--    Rsyntax OCTET STRING(SIZE(0..12))
    ACCESS read-write
    STATUS mandatory
    DESCRIPTION
        "The Post Prefix Conversion Table is used to convert
         GTA digits.  This object specifies that the
         conversion occurs 'after' global title
         translation.  The null string indicates
         that a post conversion table has not been
         specified."
    DEFVAL { "" }
    ::= { cgsccpGttSelTableEntry 11 }

cgsccpGttSelRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpGttSelTable
         following the RowStatus textual convention."
    ::= { cgsccpGttSelTableEntry 12 }

cgsccpGttGtaTable OBJECT-TYPE
    SYNTAX SEQUENCE OF CgsccpGttGtaTableEntry
    ACCESS not-accessible
    STATUS mandatory
    DESCRIPTION
        "A table of SCCP Global Title Address entries."
    ::= { cgsccpGttGta 1 }

cgsccpGttGtaTableEntry OBJECT-TYPE
    SYNTAX CgsccpGttGtaTableEntry
    ACCESS not-accessible
    STATUS mandatory
    DESCRIPTION
        "A list of SCCP Global Title Address attributes."
    INDEX { cgspInstNetwork, cgsccpGttSelTT, cgsccpGttSelNAI, cgsccpGttSelNP, cgsccpGttSelGTI, cgsccpGttGtaAddr }
    ::= { cgsccpGttGtaTable 1 }

CgsccpGttGtaTableEntry ::= SEQUENCE {
    cgsccpGttGtaAddr CItpTcGtaLongAddr,
    cgsccpGttGtaSelName CgsccpGttSelName,
    cgsccpGttGtaResType CgsccpGttGtaResType,
    cgsccpGttGtaResPc CItpTcPointCode,
    cgsccpGttGtaResMap CItpTcPointCode,
    cgsccpGttGtaResAppGroup CgsccpGttAppName,
    cgsccpGttGtaTTorSSN CItpTcTranslationType,
    cgsccpGttGtaTTorSSNvalue Gauge,
    cgsccpGttGtaRoutingInd CgsccpGttRoutingInd,
    cgsccpGttGtaQOS CgsccpGttQOS,
    cgsccpGttGtaAddrDisp CItpTcGtaLongDisplay,
    cgsccpGttGtaAddrLen CItpTcGtaLongDisplayLen,
    cgsccpGttGtaAsName CItpTcXuaName,
    cgsccpGttGtaRowStatus RowStatus,
    cgsccpGttGtaNetwork CItpTcNetworkName
    }

cgsccpGttGtaAddr OBJECT-TYPE
    SYNTAX CItpTcGtaLongAddr
--    Rsyntax OCTET STRING(SIZE(0..64))
    ACCESS not-accessible
    STATUS mandatory
    DESCRIPTION
        "The Global Title Address is 8 octets
         of the Called Party Address (CDPA)."
    ::= { cgsccpGttGtaTableEntry 1 }

cgsccpGttGtaSelName OBJECT-TYPE
    SYNTAX CgsccpGttSelName
--    Rsyntax OCTET STRING(SIZE(0..12))
    ACCESS read-write
    STATUS mandatory
    DESCRIPTION
        "The Global Title Address selector name from
         cgsccpGttSelTable."
    ::= { cgsccpGttGtaTableEntry 2 }

cgsccpGttGtaResType OBJECT-TYPE
    SYNTAX CgsccpGttGtaResType
--    Rsyntax INTEGER {
--        pc(1),
--        pcssn(2),
--        app(3),
--        as(4)
--        }
    ACCESS read-write
    STATUS mandatory
    DESCRIPTION
        "The SCCP Global Title Translation result type."
    ::= { cgsccpGttGtaTableEntry 3 }

cgsccpGttGtaResPc OBJECT-TYPE
    SYNTAX CItpTcPointCode
--    Rsyntax Gauge(0..16777216)
    ACCESS read-write
    STATUS mandatory
    DESCRIPTION
        "When the GTA translates to a point code,
         it has a valid point code and cgsccpGttGtaResType
         is 'pc'. Otherwise it is zero."
    DEFVAL { 0 }
    ::= { cgsccpGttGtaTableEntry 4 }

cgsccpGttGtaResMap OBJECT-TYPE
    SYNTAX CItpTcPointCode
--    Rsyntax Gauge(0..16777216)
    ACCESS read-write
    STATUS mandatory
    DESCRIPTION
        "When the GTA translates to a point code and an
         optional SSN, it has a valid point code and
         cgsccpGttGtaResType is 'pcssn'. Otherwise it is
         zero."
    DEFVAL { 0 }
    ::= { cgsccpGttGtaTableEntry 5 }

cgsccpGttGtaResAppGroup OBJECT-TYPE
    SYNTAX CgsccpGttAppName
--    Rsyntax OCTET STRING(SIZE(0..12))
    ACCESS read-write
    STATUS mandatory
    DESCRIPTION
        "When the GTA translates to an application group,
         it has a valid application group name and
         cgsccpGttGtaResType is 'app'.  The null string 
         indicates that an application group has not been
         specified."
    DEFVAL { "" }
    ::= { cgsccpGttGtaTableEntry 6 }

cgsccpGttGtaTTorSSN OBJECT-TYPE
    SYNTAX CItpTcTranslationType
--    Rsyntax INTEGER {
--        tt(1),
--        ssn(2)
--        }
    ACCESS read-write
    STATUS mandatory
    DESCRIPTION
        "When this object is 'tt', the object
         cgsccpGttGtaTTorSSNvalue specifies the SCCP GTT
         Translation Type (TT). When this object is 'ssn',
         the object cgsccpGttGtaTTorSSNvalue specifies
         the SCCP SubSystem Number (SSN)."
    ::= { cgsccpGttGtaTableEntry 7 }

cgsccpGttGtaTTorSSNvalue OBJECT-TYPE
    SYNTAX Gauge(0..255)
    ACCESS read-write
    STATUS mandatory
    DESCRIPTION
        "This object specifies SCCP GTT Translation Type (TT)
         value when cgsccpGttGtaTTorSSN is 'tt'. 
         It specifies SCCP SubSystem Number (SSN) value when
         cgsccpGttGtaTTorSSN is 'ssn'.
         A zero value specifies that the TT or the SSN is not
         applicable for this GTA entry."
    DEFVAL { 0 }
    ::= { cgsccpGttGtaTableEntry 8 }

cgsccpGttGtaRoutingInd OBJECT-TYPE
    SYNTAX CgsccpGttRoutingInd
--    Rsyntax INTEGER {
--        ri2gt(1),
--        ri2ssn(2),
--        ssnRI2gt(3),
--        ssnRI2ssn(4),
--        replTT(5),
--        riNotAppl(6),
--        riUndef(7)
--        }
    ACCESS read-write
    STATUS mandatory
    DESCRIPTION
        "The SCCP GTT GTA specifies the routing indicator.
        
         When cgsccpGttGtaResType is 'pc' or 'pcssn',
         this object has a valid routing indicator.
        
         When cgsccpGttGtaResType is 'app' or 'as',
         the routing indicator is not applicable."
    ::= { cgsccpGttGtaTableEntry 9 }

cgsccpGttGtaQOS OBJECT-TYPE
    SYNTAX CgsccpGttQOS
--    Rsyntax Gauge(0..255)
    ACCESS read-write
    STATUS mandatory
    DESCRIPTION
        "The SCCP GTT GTA specifies the QOS."
    DEFVAL { 0 }
    ::= { cgsccpGttGtaTableEntry 10 }

cgsccpGttGtaAddrDisp OBJECT-TYPE
    SYNTAX CItpTcGtaLongDisplay
--    Rsyntax OCTET STRING(SIZE(0..64))
    ACCESS read-only
    STATUS mandatory
    DESCRIPTION
        "The ASCII display string of Global Title Address
         up to 64 hex digits of the Called Party Address
         (CDPA). A zero length string specifies a
         default GTA value for the selector."
    ::= { cgsccpGttGtaTableEntry 11 }

cgsccpGttGtaAddrLen OBJECT-TYPE
    SYNTAX CItpTcGtaLongDisplayLen
--    Rsyntax Gauge(0..64)
    ACCESS read-only
    STATUS mandatory
    DESCRIPTION
        "The number of hex digits in the Global Title
         Address of the Called Party Address (CDPA).
         For a default GTA, the address length is zero."
    ::= { cgsccpGttGtaTableEntry 12 }

cgsccpGttGtaAsName OBJECT-TYPE
    SYNTAX CItpTcXuaName
--    Rsyntax OCTET STRING(SIZE(0..12))
    ACCESS read-write
    STATUS mandatory
    DESCRIPTION
        "The Application Server (AS) name specified by the GTA.
         It is valid only when cgsccpGttGtaResType is 'as'.
         Otherwise it is a zero length string.  The null string
         indicates that a application server name has not been
         specified."
    DEFVAL { "" }
    ::= { cgsccpGttGtaTableEntry 13 }

cgsccpGttGtaRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpGttGtaTable
         following the RowStatus textual convention."
    ::= { cgsccpGttGtaTableEntry 14 }

cgsccpGttGtaNetwork OBJECT-TYPE
    SYNTAX CItpTcNetworkName
--    Rsyntax OCTET STRING(SIZE(0..19))
    ACCESS read-write
    STATUS mandatory
    DESCRIPTION
        "The processing of global title translation may
         result in a packet being transferred from one
         network to another.  This object specifies
         the target network."
    ::= { cgsccpGttGtaTableEntry 15 }

cgsccpGttPrefTable OBJECT-TYPE
    SYNTAX SEQUENCE OF CgsccpGttPrefTableEntry
    ACCESS not-accessible
    STATUS deprecated
    DESCRIPTION
        "A table of SCCP GTT Prefix Conversion Table entries.
        
         When a packet with GTA is received, it may need
         global title translation depending on Translation
         Type (TT), Numbering Plan (NP), Network Address
         Indicator (NAI) and Global Title Indicator (GTI)
         present in the packet. To perform the translation
         a selector (cgsccpGttSelTable) corresponding to
         TT, NP, NAI and GTI is used. The selector also
         specifies prefix conversion of the GTA before (pre)
         performing the global title translation or after
         (post) performing the global title translation.
        
         A selector can specify any or both (pre and post)
         prefix conversion tables.
        
         The prefix conversion involves matching of GTA digits
         in the cgsccpGttPrefInAddr and then replacing those
         digits with the digits in cgsccpGttPrefOutAddr."
    ::= { cgsccpGttPref 1 }

cgsccpGttPrefTableEntry OBJECT-TYPE
    SYNTAX CgsccpGttPrefTableEntry
    ACCESS not-accessible
    STATUS deprecated
    DESCRIPTION
        "A list of SCCP GTT Prefix Conversion attributes."
    INDEX { cgsccpGttPrefName, cgsccpGttPrefInAddr }
    ::= { cgsccpGttPrefTable 1 }

CgsccpGttPrefTableEntry ::= SEQUENCE {
    cgsccpGttPrefName CgsccpGttPrefName,
    cgsccpGttPrefInAddr CItpTcGtaLongAddr,
    cgsccpGttPrefOutAddr CItpTcGtaLongAddr,
    cgsccpGttPrefTblNAI CItpTcNAI,
    cgsccpGttPrefTblNP CItpTcNumberingPlan,
    cgsccpGttPrefItemNAI CItpTcNAI,
    cgsccpGttPrefItemNP CItpTcNumberingPlan,
    cgsccpGttPrefRowStatus RowStatus
    }

cgsccpGttPrefName OBJECT-TYPE
    SYNTAX CgsccpGttPrefName
--    Rsyntax OCTET STRING(SIZE(0..12))
    ACCESS not-accessible
    STATUS deprecated
    DESCRIPTION
        "The GTT Prefix Conversion table name."
    ::= { cgsccpGttPrefTableEntry 1 }

cgsccpGttPrefInAddr OBJECT-TYPE
    SYNTAX CItpTcGtaLongAddr
--    Rsyntax OCTET STRING(SIZE(0..64))
    ACCESS not-accessible
    STATUS deprecated
    DESCRIPTION
        "If the GTA of the Called Party Address (CDPA)
         matches the digits in this object, then the
         prefix conversion is performed."
    ::= { cgsccpGttPrefTableEntry 2 }

cgsccpGttPrefOutAddr OBJECT-TYPE
    SYNTAX CItpTcGtaLongAddr
--    Rsyntax OCTET STRING(SIZE(0..64))
    ACCESS read-write
    STATUS deprecated
    DESCRIPTION
        "If the GTA of the Called Party Address (CDPA)
         matches the digits in cgsccpGttPrefInAddr
         then this object is used in the prefix
         conversion."
    ::= { cgsccpGttPrefTableEntry 3 }

cgsccpGttPrefTblNAI OBJECT-TYPE
    SYNTAX CItpTcNAI
--    Rsyntax INTEGER(0..255)
    ACCESS read-write
    STATUS deprecated
    DESCRIPTION
        "Nature of Address Indicator (NAI) for the Prefix
         Conversion Table."
    DEFVAL { 253 }
    ::= { cgsccpGttPrefTableEntry 4 }

cgsccpGttPrefTblNP OBJECT-TYPE
    SYNTAX CItpTcNumberingPlan
--    Rsyntax INTEGER(0..255)
    ACCESS read-write
    STATUS deprecated
    DESCRIPTION
        "Numbering Plan (NP) for the Prefix Conversion Table."
    DEFVAL { 253 }
    ::= { cgsccpGttPrefTableEntry 5 }

cgsccpGttPrefItemNAI OBJECT-TYPE
    SYNTAX CItpTcNAI
--    Rsyntax INTEGER(0..255)
    ACCESS read-write
    STATUS deprecated
    DESCRIPTION
        "Nature of Address Indicator (NAI) for the current
         item in this Prefix Conversion Table."
    DEFVAL { 253 }
    ::= { cgsccpGttPrefTableEntry 6 }

cgsccpGttPrefItemNP OBJECT-TYPE
    SYNTAX CItpTcNumberingPlan
--    Rsyntax INTEGER(0..255)
    ACCESS read-write
    STATUS deprecated
    DESCRIPTION
        "Numbering Plan (NP) for the current item in this
         Prefix Conversion Table."
    DEFVAL { 253 }
    ::= { cgsccpGttPrefTableEntry 7 }

cgsccpGttPrefRowStatus OBJECT-TYPE
    SYNTAX RowStatus
--    Rsyntax INTEGER {
--        active(1),
--        notInService(2),
--        notReady(3),
--        createAndGo(4),
--        createAndWait(5),
--        destroy(6)
--        }
    ACCESS read-write
    STATUS deprecated
    DESCRIPTION
        "The object is used by a management station to 
         create or delete the row entry in cgsccpGttPrefTable
         following the RowStatus textual convention."
    ::= { cgsccpGttPrefTableEntry 8 }

cgsccpGttTranslateTable OBJECT-TYPE
    SYNTAX SEQUENCE OF CgsccpGttTranslateTableEntry
    ACCESS not-accessible
    STATUS mandatory
    DESCRIPTION
        "The translate table contains a history of the 
         number of global title packets that were translated
         on the various processors enabled for this function.
         The ability to translate GTT is critical to many 
         SS7 functions.  This table provides peak utilization
         to allow planning of maximum load on SS7 network. "
    REFERENCE
        "ANSI GR-82-CORE 6.4.5 Processor Measurements Item 2."
    ::= { cgsccpGttTranslate 1 }

cgsccpGttTranslateTableEntry OBJECT-TYPE
    SYNTAX CgsccpGttTranslateTableEntry
    ACCESS not-accessible
    STATUS mandatory
    DESCRIPTION
        "A list of global title translate statistics."
    INDEX { cgsccpGttTranslateSlot, cgsccpGttTranslateEntry }
    ::= { cgsccpGttTranslateTable 1 }

CgsccpGttTranslateTableEntry ::= SEQUENCE {
    cgsccpGttTranslateSlot Gauge,
    cgsccpGttTranslateEntry Gauge,
    cgsccpGttTranslateRate Gauge,
    cgsccpGttTranslateTS TimeStamp
    }

cgsccpGttTranslateSlot OBJECT-TYPE
    SYNTAX Gauge(0..32767)
    ACCESS not-accessible
    STATUS mandatory
    DESCRIPTION
        "The slot number containing the CPU that is 
         performing Global Title translation."
    ::= { cgsccpGttTranslateTableEntry 1 }

cgsccpGttTranslateEntry OBJECT-TYPE
    SYNTAX Gauge(0..4294967295)
    ACCESS not-accessible
    STATUS mandatory
    DESCRIPTION
        "The entry number.  Each entry represents a period
         of time as specified by the 
         cgsccpGttTranslatePeriod object.  The entries are
         ordered from old to new."
    ::= { cgsccpGttTranslateTableEntry 2 }

cgsccpGttTranslateRate OBJECT-TYPE
    SYNTAX Gauge(0..2147483647)
    ACCESS read-only
    STATUS mandatory
    DESCRIPTION
        "During each interval the rate of global title 
         translations is calculated every second.  This object
         is the highest rate of global title translation 
         encountered in the interval specified by the 
         cgsccpGttTranslatePeriod object."
    ::= { cgsccpGttTranslateTableEntry 3 }

cgsccpGttTranslateTS OBJECT-TYPE
    SYNTAX TimeStamp
--    Rsyntax TimeTicks
    ACCESS read-only
    STATUS mandatory
    DESCRIPTION
        "This timestamp indicates when time period ended 
         for this sample."
    ::= { cgsccpGttTranslateTableEntry 4 }

cgsccpGttPref2Table OBJECT-TYPE
    SYNTAX SEQUENCE OF CgsccpGttPref2TableEntry
    ACCESS not-accessible
    STATUS mandatory
    DESCRIPTION
        "A table of SCCP GTT Prefix Conversion Table entries.
        
         This table replaces the cgsccpGttPrefTable tables and 
         allow prefix conversion to be specified per instance.
         
         When a packet with GTA is received, it may need
         global title translation depending on Translation
         Type (TT), Numbering Plan (NP), Network Address
         Indicator (NAI) and Global Title Indicator (GTI)
         present in the packet. To perform the translation
         a selector (cgsccpGttSelTable) corresponding to
         TT, NP, NAI and GTI is used. The selector also
         specifies prefix conversion of the GTA before (pre)
         performing the global title translation or after
         (post) performing the global title translation.
        
         A selector can specify any or both (pre and post)
         prefix conversion tables.
        
         The prefix conversion involves matching of GTA digits
         in the cgsccpGttPref2InAddr and then replacing those
         digits with the digits in cgsccpGttPref2OutAddr."
    ::= { cgsccpGttPref2 1 }

cgsccpGttPref2TableEntry OBJECT-TYPE
    SYNTAX CgsccpGttPref2TableEntry
    ACCESS not-accessible
    STATUS mandatory
    DESCRIPTION
        "A list of SCCP GTT Prefix Conversion attributes."
    INDEX { cgspInstNetwork, cgsccpGttPref2Name, cgsccpGttPref2InAddr }
    ::= { cgsccpGttPref2Table 1 }

CgsccpGttPref2TableEntry ::= SEQUENCE {
    cgsccpGttPref2Name CgsccpGttPrefName,
    cgsccpGttPref2InAddr CItpTcGtaLongAddr,
    cgsccpGttPref2OutAddr CItpTcGtaLongAddr,
    cgsccpGttPref2TblNAI CItpTcNAI,
    cgsccpGttPref2TblNP CItpTcNumberingPlan,
    cgsccpGttPref2ItemNAI CItpTcNAI,
    cgsccpGttPref2ItemNP CItpTcNumberingPlan,
    cgsccpGttPref2RowStatus RowStatus,
    cgsccpGttPref2EncodingScheme INTEGER
    }

cgsccpGttPref2Name OBJECT-TYPE
    SYNTAX CgsccpGttPrefName
--    Rsyntax OCTET STRING(SIZE(0..12))
    ACCESS not-accessible
    STATUS mandatory
    DESCRIPTION
        "The GTT Prefix Conversion table name."
    ::= { cgsccpGttPref2TableEntry 1 }

cgsccpGttPref2InAddr OBJECT-TYPE
    SYNTAX CItpTcGtaLongAddr
--    Rsyntax OCTET STRING(SIZE(0..64))
    ACCESS not-accessible
    STATUS mandatory
    DESCRIPTION
        "If the GTA of the Called Party Address (CDPA)
         matches the digits in this object, then the
         prefix conversion is performed."
    ::= { cgsccpGttPref2TableEntry 2 }

cgsccpGttPref2OutAddr OBJECT-TYPE
    SYNTAX CItpTcGtaLongAddr
--    Rsyntax OCTET STRING(SIZE(0..64))
    ACCESS read-write
    STATUS mandatory
    DESCRIPTION
        "If the GTA of the Called Party Address (CDPA)
         matches the digits in cgsccpGttPref2InAddr
         then this object is used in the prefix
         conversion."
    ::= { cgsccpGttPref2TableEntry 3 }

cgsccpGttPref2TblNAI OBJECT-TYPE
    SYNTAX CItpTcNAI
--    Rsyntax INTEGER(0..255)
    ACCESS read-write
    STATUS mandatory
    DESCRIPTION
        "Nature of Address Indicator (NAI) for the Prefix
         Conversion Table."
    DEFVAL { 253 }
    ::= { cgsccpGttPref2TableEntry 4 }

cgsccpGttPref2TblNP OBJECT-TYPE
    SYNTAX CItpTcNumberingPlan
--    Rsyntax INTEGER(0..255)
    ACCESS read-write
    STATUS mandatory
    DESCRIPTION
        "Numbering Plan (NP) for the Prefix Conversion Table."
    DEFVAL { 253 }
    ::= { cgsccpGttPref2TableEntry 5 }

cgsccpGttPref2ItemNAI OBJECT-TYPE
    SYNTAX CItpTcNAI
--    Rsyntax INTEGER(0..255)
    ACCESS read-write
    STATUS mandatory
    DESCRIPTION
        "Nature of Address Indicator (NAI) for the current
         item in this Prefix Conversion Table."
    DEFVAL { 253 }
    ::= { cgsccpGttPref2TableEntry 6 }

cgsccpGttPref2ItemNP OBJECT-TYPE
    SYNTAX CItpTcNumberingPlan
--    Rsyntax INTEGER(0..255)
    ACCESS read-write
    STATUS mandatory
    DESCRIPTION
        "Numbering Plan (NP) for the current item in this
         Prefix Conversion Table."
    DEFVAL { 253 }
    ::= { cgsccpGttPref2TableEntry 7 }

cgsccpGttPref2RowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpGttPref2Table
         following the RowStatus textual convention."
    ::= { cgsccpGttPref2TableEntry 8 }

cgsccpGttPref2EncodingScheme OBJECT-TYPE
    SYNTAX INTEGER {
        --?? enum value of zero may cause problems
        unknown(0),
        bcdOdd(1),
        bcdEven(2),
        national(3)
        }
    ACCESS read-write
    STATUS mandatory
    DESCRIPTION
        "The encoding scheme to be used for output GTT address
         as follows.
          
         unknown  - encoding scheme is not specified at the address
                    level.
         bcdOdd   - Use BCD odd encoding scheme.
         bcdEven  - Use BCD even encoding scheme.
         national - national specific."
    REFERENCE
        "E.164 and E.214 address formats and Q.713"
    ::= { cgsccpGttPref2TableEntry 9 }

cgsccpGttAppGr2Table OBJECT-TYPE
    SYNTAX SEQUENCE OF CgsccpGttAppGr2TableEntry
    ACCESS not-accessible
    STATUS mandatory
    DESCRIPTION
        "A table of SCCP GTT Application Group Table entries."
    ::= { cgsccpGttAppGr2 1 }

cgsccpGttAppGr2TableEntry OBJECT-TYPE
    SYNTAX CgsccpGttAppGr2TableEntry
    ACCESS not-accessible
    STATUS mandatory
    DESCRIPTION
        "A list of SCCP GTT Application Group attributes."
    INDEX { cgspInstNetwork, cgsccpGttAppGr2Name, cgsccpGttAppGr2EntNum }
    ::= { cgsccpGttAppGr2Table 1 }

CgsccpGttAppGr2TableEntry ::= SEQUENCE {
    cgsccpGttAppGr2Name CgsccpGttAppName,
    cgsccpGttAppGr2EntNum Gauge,
    cgsccpGttAppGr2Mult CgsccpGttMultInd,
    cgsccpGttAppGr2Type CgsccpGttAppType,
    cgsccpGttAppGr2Cost CgsccpGttAppCost,
    cgsccpGttAppGr2Weight Gauge,
    cgsccpGttAppGr2Pc CItpTcPointCode,
    cgsccpGttAppGr2Ssn CItpTcSubSystemNumber,
    cgsccpGttAppGr2Ri CgsccpGttRoutingInd,
    cgsccpGttAppGr2RefCount Gauge,
    cgsccpGttAppGr2AsName CItpTcXuaName,
    cgsccpGttAppGr2NewSsn CItpTcSubSystemNumber,
    cgsccpGttAppGr2NumUsed Counter,
    cgsccpGttAppGr2Network CItpTcNetworkName,
    cgsccpGttAppGr2RowStatus RowStatus
    }

cgsccpGttAppGr2Name OBJECT-TYPE
    SYNTAX CgsccpGttAppName
--    Rsyntax OCTET STRING(SIZE(0..12))
    ACCESS not-accessible
    STATUS mandatory
    DESCRIPTION
        "The GTT Application Group name."
    ::= { cgsccpGttAppGr2TableEntry 1 }

cgsccpGttAppGr2EntNum OBJECT-TYPE
    SYNTAX Gauge
    ACCESS not-accessible
    STATUS mandatory
    DESCRIPTION
        "The entry number is an arbitrary number. It is used
         to identify each application group entry."
    ::= { cgsccpGttAppGr2TableEntry 2 }

cgsccpGttAppGr2Mult OBJECT-TYPE
    SYNTAX CgsccpGttMultInd
--    Rsyntax INTEGER {
--        solitary(1),
--        shared(2),
--        dominant(3),
--        cost(4),
--        cgpa(5)
--        }
    ACCESS read-write
    STATUS mandatory
    DESCRIPTION
        "The multiplicity of the GTT Application Group."
    ::= { cgsccpGttAppGr2TableEntry 3 }

cgsccpGttAppGr2Type OBJECT-TYPE
    SYNTAX CgsccpGttAppType
--    Rsyntax INTEGER {
--        pc(1),
--        pcssn(2),
--        as(3)
--        }
    ACCESS read-write
    STATUS mandatory
    DESCRIPTION
        "The type of the item in the GTT Application Group."
    ::= { cgsccpGttAppGr2TableEntry 4 }

cgsccpGttAppGr2Cost OBJECT-TYPE
    SYNTAX CgsccpGttAppCost
--    Rsyntax Gauge(1..8)
    ACCESS read-write
    STATUS mandatory
    DESCRIPTION
        "The cost for the item in the GTT Application Group.
         When the cgsccpGttAppGr2Mult object has 'cost'
         value, this object is required when entry is created.
         Otherwise, this value does not apply."
    ::= { cgsccpGttAppGr2TableEntry 5 }

cgsccpGttAppGr2Weight OBJECT-TYPE
    SYNTAX Gauge(0..999)
    ACCESS read-write
    STATUS mandatory
    DESCRIPTION
        "The weighting factor used for the item in the GTT
         Application Group. When the cgsccpGttAppGr2Mult
         object has 'cgpa' value, this object is required when
         entry is created. Otherwise, this value does not
         apply and can default zero."
    DEFVAL { 0 }
    ::= { cgsccpGttAppGr2TableEntry 6 }

cgsccpGttAppGr2Pc OBJECT-TYPE
    SYNTAX CItpTcPointCode
--    Rsyntax Gauge(0..16777216)
    ACCESS read-write
    STATUS mandatory
    DESCRIPTION
        "The point code specified by the item in the GTT
         Application Group.  When the cgsccpGttAppGr2Type
         object has 'pc' or pcssn' values this object 
         is required when entry is created.  Otherwise,
         this value does not apply and can default to 
         zero."
    DEFVAL { 0 }
    ::= { cgsccpGttAppGr2TableEntry 7 }

cgsccpGttAppGr2Ssn OBJECT-TYPE
    SYNTAX CItpTcSubSystemNumber
--    Rsyntax Gauge(0|2..255)
    ACCESS read-write
    STATUS mandatory
    DESCRIPTION
        "The subsystem number (SSN) specified by the item
         in the GTT Application Group. It is valid only when
         cgsccpGttAppGr2Type is 'pcssn'. Otherwise it is zero."
    DEFVAL { 0 }
    ::= { cgsccpGttAppGr2TableEntry 8 }

cgsccpGttAppGr2Ri OBJECT-TYPE
    SYNTAX CgsccpGttRoutingInd
--    Rsyntax INTEGER {
--        ri2gt(1),
--        ri2ssn(2),
--        ssnRI2gt(3),
--        ssnRI2ssn(4),
--        replTT(5),
--        riNotAppl(6),
--        riUndef(7)
--        }
    ACCESS read-write
    STATUS mandatory
    DESCRIPTION
        "The routing indicator (RI) specified by the item
         in the GTT Application Group."
    ::= { cgsccpGttAppGr2TableEntry 9 }

cgsccpGttAppGr2RefCount OBJECT-TYPE
    SYNTAX Gauge(0..2147483647)
    ACCESS read-only
    STATUS mandatory
    DESCRIPTION
        "The number of global title addresses referring to 
         this application group."
    ::= { cgsccpGttAppGr2TableEntry 10 }

cgsccpGttAppGr2AsName OBJECT-TYPE
    SYNTAX CItpTcXuaName
--    Rsyntax OCTET STRING(SIZE(0..12))
    ACCESS read-write
    STATUS mandatory
    DESCRIPTION
        "The Application Server (AS) name specified by the item
         in the GTT Application Group. It is valid only when
         cgsccpGttAppGr2Type is 'as'. Otherwise it
         is a zero length string."
    DEFVAL { "" }
    ::= { cgsccpGttAppGr2TableEntry 11 }

cgsccpGttAppGr2NewSsn OBJECT-TYPE
    SYNTAX CItpTcSubSystemNumber
--    Rsyntax Gauge(0|2..255)
    ACCESS read-write
    STATUS mandatory
    DESCRIPTION
        "The new subsystem number (SSN) specified by the item
         in the GTT Application Group.  It is valid only when
         cgsccpGttAppGr2Type is 'as'.  Otherwise it
         is zero."
    DEFVAL { 0 }
    ::= { cgsccpGttAppGr2TableEntry 12 }

cgsccpGttAppGr2NumUsed OBJECT-TYPE
    SYNTAX Counter
    ACCESS read-only
    STATUS mandatory
    DESCRIPTION
        "The number of times this item in the GTT Application
         Group is used successfully."
    ::= { cgsccpGttAppGr2TableEntry 13 }

cgsccpGttAppGr2Network OBJECT-TYPE
    SYNTAX CItpTcNetworkName
--    Rsyntax OCTET STRING(SIZE(0..19))
    ACCESS read-write
    STATUS mandatory
    DESCRIPTION
        "The processing of global title translation may
         result in a packet being transferred from one
         network to another.  This object specifies
         the target network."
    ::= { cgsccpGttAppGr2TableEntry 14 }

cgsccpGttAppGr2RowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cgsccpGttAppGr2Table
         following the RowStatus textual convention."
    ::= { cgsccpGttAppGr2TableEntry 15 }

cgsccpGttErrorsTable OBJECT-TYPE
    SYNTAX SEQUENCE OF CgsccpGttErrorsTableEntry
    ACCESS not-accessible
    STATUS mandatory
    DESCRIPTION
        "This table is used to indicate errors in global title
         translation and will be used to provide information
         for ciscoGsccpGttErrors notification."
    ::= { cgsccpGttErrors 1 }

cgsccpGttErrorsTableEntry OBJECT-TYPE
    SYNTAX CgsccpGttErrorsTableEntry
    ACCESS not-accessible
    STATUS mandatory
    DESCRIPTION
        "All objects in this table are derived from other 
         objects in this MIB.  At the end of each 
         interval the values of these objects will be updated
         with number of errors that occurred during last 
         interval.  The length of the interval is defined by 
         the cgsccpGttErrorPeriod object."
    INDEX { cgspInstNetwork }
    ::= { cgsccpGttErrorsTable 1 }

CgsccpGttErrorsTableEntry ::= SEQUENCE {
    cgsccpGttErrorsSelectorNotFound Gauge,
    cgsccpGttErrorsIncorrectFormat Gauge,
    cgsccpGttErrorsGtaNotFound Gauge,
    cgsccpGttErrorsHopViolation Gauge,
    cgsccpGttErrorsMapNotFound Gauge,
    cgsccpGttErrorsUnequipedSS Gauge,
    cgsccpGttErrorsSccpUnavailable Gauge,
    cgsccpGttErrorsDpcUnavailable Gauge,
    cgsccpGttErrorsSsUnavailable Gauge,
    cgsccpGttErrorsDpcCongested Gauge,
    cgsccpGttErrorsSsCongested Gauge,
    cgsccpGttErrorsRouteFailure Gauge,
    cgsccpGttErrorsSccpUnqualified Gauge
    }

cgsccpGttErrorsSelectorNotFound OBJECT-TYPE
    SYNTAX Gauge
--  Units
--    packets
    ACCESS read-only
    STATUS mandatory
    DESCRIPTION
        "This counter is incremented every time a translation
         was requested for a combination of Translation Type,
         Numbering Plan and Nature of Address for which no 
         translation exists in the signalling point.  This 
         occurs when no selector is available for the 
         combination of parameters provided in the MSU.
         This counter is derived from cgsccpInstQ752T7E1
         object."
    ::= { cgsccpGttErrorsTableEntry 1 }

cgsccpGttErrorsIncorrectFormat OBJECT-TYPE
    SYNTAX Gauge
--  Units
--    packets
    ACCESS not-accessible
    STATUS mandatory
    DESCRIPTION
        "This counter is incremented every time an invalid 
         Global Title format is found while performing the
         global title translation.  This counter is derived
         from cgsccpInstInvalidGttFormat object."
    ::= { cgsccpGttErrorsTableEntry 2 }

cgsccpGttErrorsGtaNotFound OBJECT-TYPE
    SYNTAX Gauge
--  Units
--    packets
    ACCESS not-accessible
    STATUS mandatory
    DESCRIPTION
        "This counter is incremented every time a global title
         title translations was required and a selector was 
         not found. This counter is derived from 
         cgsccpGttQ752T7E2 object."
    ::= { cgsccpGttErrorsTableEntry 3 }

cgsccpGttErrorsHopViolation OBJECT-TYPE
    SYNTAX Gauge
--  Units
--    packets
    ACCESS not-accessible
    STATUS mandatory
    DESCRIPTION
        "This counter is incremented every time a hop count 
         violation is found in the MSU.  This counter is 
         derived from cgsccpInstQ752T7E13 object."
    ::= { cgsccpGttErrorsTableEntry 4 }

cgsccpGttErrorsMapNotFound OBJECT-TYPE
    SYNTAX Gauge
--  Units
--    packets
    ACCESS not-accessible
    STATUS mandatory
    DESCRIPTION
        "This counter is incremented every time a global 
         title translation is successful to a certain
         PC/SSN but it was not found in the GTT Mated 
         Application table.  This counter is derived
         from cgsccpInstMapNotFound object."
    ::= { cgsccpGttErrorsTableEntry 5 }

cgsccpGttErrorsUnequipedSS OBJECT-TYPE
    SYNTAX Gauge
--  Units
--    packets
    ACCESS not-accessible
    STATUS mandatory
    DESCRIPTION
        "This counter is incremented every time a global 
         title translation could not be performed due to an
         unequipped subsystem (SS). This counter is derived
         from cgsccpInstQ752T7E7 object."
    ::= { cgsccpGttErrorsTableEntry 6 }

cgsccpGttErrorsSccpUnavailable OBJECT-TYPE
    SYNTAX Gauge
--  Units
--    packets
    ACCESS not-accessible
    STATUS mandatory
    DESCRIPTION
        "This counter is incremented every time a SCCP is 
         unavailable at the GTT Mated Application. This 
         counter is derived from cgsccpGttMapSccpUnavail
         object."
    ::= { cgsccpGttErrorsTableEntry 7 }

cgsccpGttErrorsDpcUnavailable OBJECT-TYPE
    SYNTAX Gauge
--  Units
--    packets
    ACCESS not-accessible
    STATUS mandatory
    DESCRIPTION
        "This counter is incremented every time a point code
         is unavailable at the GTT Mated Application.
         This counter is derived from cgsccpGttMapQ752T7E3Un 
         object."
    ::= { cgsccpGttErrorsTableEntry 8 }

cgsccpGttErrorsSsUnavailable OBJECT-TYPE
    SYNTAX Gauge
--  Units
--    packets
    ACCESS not-accessible
    STATUS mandatory
    DESCRIPTION
        "This counter is incremented every time a subsystem
         is unavailable at the GTT Mated Application.  This 
         counter is derived from cgsccpGttMapQ752T7E5 object."
    ::= { cgsccpGttErrorsTableEntry 9 }

cgsccpGttErrorsDpcCongested OBJECT-TYPE
    SYNTAX Gauge
--  Units
--    packets
    ACCESS not-accessible
    STATUS mandatory
    DESCRIPTION
        "This counter is incremented every time a point code
         is congested at the GTT Mated Application.  This 
         counter is derived from cgsccpGttMapQ752T7E4 object."
    ::= { cgsccpGttErrorsTableEntry 10 }

cgsccpGttErrorsSsCongested OBJECT-TYPE
    SYNTAX Gauge
--  Units
--    packets
    ACCESS not-accessible
    STATUS mandatory
    DESCRIPTION
        "This counter is incremented every time a subsystem is 
         congested at the GTT Mated Application.  This counter
         is derived from cgsccpGttMapQ752T7E6 object."
    ::= { cgsccpGttErrorsTableEntry 11 }

cgsccpGttErrorsRouteFailure OBJECT-TYPE
    SYNTAX Gauge
--  Units
--    packets
    ACCESS not-accessible
    STATUS mandatory
    DESCRIPTION
        "This counter is incremented every time a the MTP3 layer
         failed at the GTT Mated Application.  This counter is 
         derived from cgsccpGttMapQ752T7E3Fail object."
    ::= { cgsccpGttErrorsTableEntry 12 }

cgsccpGttErrorsSccpUnqualified OBJECT-TYPE
    SYNTAX Gauge
--  Units
--    packets
    ACCESS not-accessible
    STATUS mandatory
    DESCRIPTION
        "This counter is incremented every time a global title
         translation is unsuccessful and the error type not 
         covered by other specific error types.  This counter
         is derived from cgsccpInstQ752Unqualified object."
    ::= { cgsccpGttErrorsTableEntry 13 }

ciscoGsccpGttMapStateChange TRAP-TYPE
-- Reverse mappable trap
    ENTERPRISE ciscoGsccpMIB
    VARIABLES {
        cgspEventSequenceNumber, cgspCLLICode, 
        cgsccpGttMapDisplayPC, cgsccpGttMapDisplaySS, 
        cgsccpGttMapSsStatus }
--  Status
--    mandatory
    DESCRIPTION
        "The notification generated when a mated
         application subsystem changes to a new state.
         The value of cgsccpGttMapSsStatus indicates
         the new state for the subsystem."
    ::= 1

ciscoGsccpGttLoadTable TRAP-TYPE
-- Reverse mappable trap
    ENTERPRISE ciscoGsccpMIB
    VARIABLES {
        cgspEventSequenceNumber, cgspCLLICode, 
        cgsccpInstGttConfigStatus, cgsccpInstLastURL }
--  Status
--    mandatory
    DESCRIPTION
        "This notification is generated whenever a load 
         operation is started or completes."
    ::= 2

ciscoGsccpGttErrors TRAP-TYPE
-- Reverse mappable trap
    ENTERPRISE ciscoGsccpMIB
    VARIABLES {
        cgspEventSequenceNumber, cgspCLLICode, 
        cgsccpInstErrorIndicator, cgsccpGttErrorsSelectorNotFound, 
        cgsccpGttErrorsIncorrectFormat, cgsccpGttErrorsGtaNotFound, 
        cgsccpGttErrorsHopViolation, cgsccpGttErrorsMapNotFound, 
        cgsccpGttErrorsUnequipedSS, cgsccpGttErrorsSccpUnavailable, 
        cgsccpGttErrorsDpcUnavailable, cgsccpGttErrorsSsUnavailable, 
        cgsccpGttErrorsDpcCongested, cgsccpGttErrorsSsCongested, 
        cgsccpGttErrorsRouteFailure, cgsccpGttErrorsSccpUnqualified }
--  Status
--    mandatory
    DESCRIPTION
        "This notification is generated whenever any global 
         title error is encountered in last interval specified 
         by the cgsccpGttErrorPeriod and the 
         cgsccpInstErrorIndicator will be set to true. The
         notification will also be generated when errors have
         abated. The notification is generated after the number 
         of recovery intervals as specified by the 
         cgsccpGttErrorRecoveryCount object has passed without 
         any global title errors."
    ::= 3

ciscoGsccpGlobalEntryGroup OBJECT IDENTIFIER ::= { ciscoGsccpMIBGroups 1 }
-- OBJECT-GROUP
--  Status
--    deprecated
--  Descr
--    Gateway SCCP Scalar objects.
--  objects
--    cgsccpGttTranslateSample, cgsccpGttTranslatePeriod, 
--    cgsccpGttTranslateRate, cgsccpGttMapStateNotifEnabled, 
--    cgsccpGttLoadTableNotifEnabled

ciscoGsccpInstTableEntryGroup OBJECT IDENTIFIER ::= { ciscoGsccpMIBGroups 2 }
-- OBJECT-GROUP
--  Status
--    deprecated
--  Descr
--    SCCP main objects.
--  objects
--    cgsccpInstTotalMsgs, cgsccpInstLocalMsgs, 
--    cgsccpInstTotalGttMsgs, cgsccpInstUDTMsgsSent, 
--    cgsccpInstUDTSMsgsSent, cgsccpInstUDTSMsgsAttempted, 
--    cgsccpInstUDTMsgsRcvd, cgsccpInstUDTSMsgsRcvd, 
--    cgsccpInstXUDTMsgsSent, cgsccpInstXUDTSMsgsAttempted, 
--    cgsccpInstXUDTSMsgsSent, cgsccpInstXUDTMsgsRcvd, 
--    cgsccpInstXUDTSMsgsRcvd, cgsccpInstLUDTMsgsSent, 
--    cgsccpInstLUDTSMsgsSent, cgsccpInstLUDTMsgsRcvd, 
--    cgsccpInstLUDTSMsgsRcvd, cgsccpInstCrToMtp, 
--    cgsccpInstCrefToMtp, cgsccpInstCrFromMtp, 
--    cgsccpInstCrefFromMtp, cgsccpInstRsrToMtp, 
--    cgsccpInstRsrFromMtp, cgsccpInstErrToMtp, 
--    cgsccpInstErrFromMtp, cgsccpInstQ752T7E1, 
--    cgsccpInstInvalidGttFormat, cgsccpInstQ752T7E13, 
--    cgsccpInstMapNotFound, cgsccpInstQ752T7E7, 
--    cgsccpInstGttConfigStatus, cgsccpInstConfigTS, 
--    cgsccpInstGttConfigTS, cgsccpInstLastURL, 
--    cgsccpInstConPcTableEntries, cgsccpInstMapTableEntries, 
--    cgsccpInstGtaTableEntries, cgsccpInstSelTableEntries, 
--    cgsccpInstAppGrTableEntries, cgsccpInstRowStatus

ciscoGsccpGttConPcGroup OBJECT IDENTIFIER ::= { ciscoGsccpMIBGroups 3 }
-- OBJECT-GROUP
--  Status
--    mandatory
--  Descr
--    SCCP Concerned Point Code objects.
--  objects
--    cgsccpGttConPcRowStatus

ciscoGsccpGttAppGroup OBJECT IDENTIFIER ::= { ciscoGsccpMIBGroups 4 }
-- OBJECT-GROUP
--  Status
--    deprecated
--  Descr
--    SCCP GTT Application Group objects.
--  objects
--    cgsccpGttAppGrType, cgsccpGttAppGrPc, cgsccpGttAppGrSsn, 
--    cgsccpGttAppGrRi, cgsccpGttAppGrMult, cgsccpGttAppGrRefCount, 
--    cgsccpGttAppGrAsName, cgsccpGttAppGrNewSsn, 
--    cgsccpGttAppGrNumUsed, cgsccpGttAppGrRowStatus

ciscoGsccpGttMapGroup OBJECT IDENTIFIER ::= { ciscoGsccpMIBGroups 5 }
-- OBJECT-GROUP
--  Status
--    mandatory
--  Descr
--    SCCP GTT Mated Application objects.
--  objects
--    cgsccpGttMapDisplayPC, cgsccpGttMapDisplaySS, 
--    cgsccpGttMapType, cgsccpGttMapPcStatus, cgsccpGttMapSsStatus, 
--    cgsccpGttMapMultInd, cgsccpGttMapBackupPc, 
--    cgsccpGttMapBackupSsn, cgsccpGttMapConPcList, 
--    cgsccpGttMapReRouteOnCong, cgsccpGttMapAdjacent, 
--    cgsccpGttMapLastSsUsed, cgsccpGttMapUsed, cgsccpGttMapAltUsed, 
--    cgsccpGttMapSccpUnavail, cgsccpGttMapQ752T7E3Fail, 
--    cgsccpGttMapQ752T7E3Un, cgsccpGttMapQ752T7E4, 
--    cgsccpGttMapQ752T7E5, cgsccpGttMapQ752T7E6, 
--    cgsccpGttMapRefCount, cgsccpGttMapCongStatus, 
--    cgsccpGttMapRowStatus

ciscoGsccpGttSelGroup OBJECT IDENTIFIER ::= { ciscoGsccpMIBGroups 6 }
-- OBJECT-GROUP
--  Status
--    mandatory
--  Descr
--    SCCP GTT Selector objects.
--  objects
--    cgsccpGttSelName, cgsccpGttSelNumPerf, cgsccpGttQ752T7E2, 
--    cgsccpGttSelQOS, cgsccpGttSelRefCount, 
--    cgsccpGttSelPrePrefConv, cgsccpGttSelPostPrefConv, 
--    cgsccpGttSelRowStatus

ciscoGsccpGttGtaGroup OBJECT IDENTIFIER ::= { ciscoGsccpMIBGroups 7 }
-- OBJECT-GROUP
--  Status
--    deprecated
--  Descr
--    SCCP GTT Global Title Address objects.
--  objects
--    cgsccpGttGtaSelName, cgsccpGttGtaResType, cgsccpGttGtaResPc, 
--    cgsccpGttGtaResMap, cgsccpGttGtaResAppGroup, 
--    cgsccpGttGtaTTorSSN, cgsccpGttGtaTTorSSNvalue, 
--    cgsccpGttGtaRoutingInd, cgsccpGttGtaQOS, cgsccpGttGtaAddrDisp, 
--    cgsccpGttGtaAddrLen, cgsccpGttGtaAsName, 
--    cgsccpGttGtaRowStatus

ciscoGsccpGttPrefGroup OBJECT IDENTIFIER ::= { ciscoGsccpMIBGroups 8 }
-- OBJECT-GROUP
--  Status
--    deprecated
--  Descr
--    SCCP GTT Prefix Conversion Table objects.
--  objects
--    cgsccpGttPrefOutAddr, cgsccpGttPrefTblNAI, cgsccpGttPrefTblNP, 
--    cgsccpGttPrefItemNAI, cgsccpGttPrefItemNP, 
--    cgsccpGttPrefRowStatus

ciscoGsccpGttPrefGroupRev1 OBJECT IDENTIFIER ::= { ciscoGsccpMIBGroups 10 }
-- OBJECT-GROUP
--  Status
--    mandatory
--  Descr
--    SCCP GTT Prefix Conversion Table objects.
--  objects
--    cgsccpGttPref2OutAddr, cgsccpGttPref2TblNAI, 
--    cgsccpGttPref2TblNP, cgsccpGttPref2ItemNAI, 
--    cgsccpGttPref2ItemNP, cgsccpGttPref2RowStatus

ciscoGsccpInstTableEntryGroupRev1 OBJECT IDENTIFIER ::= { ciscoGsccpMIBGroups 11 }
-- OBJECT-GROUP
--  Status
--    mandatory
--  Descr
--    SCCP main objects.
--  objects
--    cgsccpInstTotalMsgs, cgsccpInstLocalMsgs, 
--    cgsccpInstTotalGttMsgs, cgsccpInstUDTMsgsSent, 
--    cgsccpInstUDTSMsgsSent, cgsccpInstUDTSMsgsAttempted, 
--    cgsccpInstUDTMsgsRcvd, cgsccpInstUDTSMsgsRcvd, 
--    cgsccpInstXUDTMsgsSent, cgsccpInstXUDTSMsgsAttempted, 
--    cgsccpInstXUDTSMsgsSent, cgsccpInstXUDTMsgsRcvd, 
--    cgsccpInstXUDTSMsgsRcvd, cgsccpInstLUDTMsgsSent, 
--    cgsccpInstLUDTSMsgsSent, cgsccpInstLUDTMsgsRcvd, 
--    cgsccpInstLUDTSMsgsRcvd, cgsccpInstCrToMtp, 
--    cgsccpInstCrefToMtp, cgsccpInstCrFromMtp, 
--    cgsccpInstCrefFromMtp, cgsccpInstRsrToMtp, 
--    cgsccpInstRsrFromMtp, cgsccpInstErrToMtp, 
--    cgsccpInstErrFromMtp, cgsccpInstQ752T7E1, 
--    cgsccpInstInvalidGttFormat, cgsccpInstQ752T7E13, 
--    cgsccpInstMapNotFound, cgsccpInstQ752T7E7, 
--    cgsccpInstGttConfigStatus, cgsccpInstConfigTS, 
--    cgsccpInstGttConfigTS, cgsccpInstLastURL, 
--    cgsccpInstConPcTableEntries, cgsccpInstMapTableEntries, 
--    cgsccpInstGtaTableEntries, cgsccpInstSelTableEntries, 
--    cgsccpInstAppGrTableEntries, cgsccpInstRowStatus, 
--    cgsccpInstPrefTableEntries, cgsccpInstQ752Unqualified

ciscoGsccpGlobalEntryGroupRev1 OBJECT IDENTIFIER ::= { ciscoGsccpMIBGroups 12 }
-- OBJECT-GROUP
--  Status
--    mandatory
--  Descr
--    Gateway SCCP Scalar objects.
--  objects
--    cgsccpGttTranslateSample, cgsccpGttTranslatePeriod, 
--    cgsccpGttTranslateRate, cgsccpGttMapStateNotifEnabled, 
--    cgsccpGttLoadTableNotifEnabled, cgsccpGttTranslateTS

ciscoGsccpGttAppGroupRev2 OBJECT IDENTIFIER ::= { ciscoGsccpMIBGroups 13 }
-- OBJECT-GROUP
--  Status
--    deprecated
--  Descr
--    SCCP GTT Application Group objects.
--  objects
--    cgsccpGttAppGrType, cgsccpGttAppGrPc, cgsccpGttAppGrSsn, 
--    cgsccpGttAppGrRi, cgsccpGttAppGrMult, cgsccpGttAppGrRefCount, 
--    cgsccpGttAppGrAsName, cgsccpGttAppGrNewSsn, 
--    cgsccpGttAppGrNumUsed, cgsccpGttAppGrRowStatus, 
--    cgsccpGttAppGrNetwork

ciscoGsccpGttGtaGroupRev2 OBJECT IDENTIFIER ::= { ciscoGsccpMIBGroups 14 }
-- OBJECT-GROUP
--  Status
--    mandatory
--  Descr
--    SCCP GTT Global Title Address objects.
--  objects
--    cgsccpGttGtaSelName, cgsccpGttGtaResType, cgsccpGttGtaResPc, 
--    cgsccpGttGtaResMap, cgsccpGttGtaResAppGroup, 
--    cgsccpGttGtaTTorSSN, cgsccpGttGtaTTorSSNvalue, 
--    cgsccpGttGtaRoutingInd, cgsccpGttGtaQOS, cgsccpGttGtaAddrDisp, 
--    cgsccpGttGtaAddrLen, cgsccpGttGtaAsName, 
--    cgsccpGttGtaRowStatus, cgsccpGttGtaNetwork

ciscoGsccpGttAppGroupRev3 OBJECT IDENTIFIER ::= { ciscoGsccpMIBGroups 15 }
-- OBJECT-GROUP
--  Status
--    mandatory
--  Descr
--    SCCP GTT Application Group objects.
--  objects
--    cgsccpGttAppGr2Mult, cgsccpGttAppGr2Type, cgsccpGttAppGr2Cost, 
--    cgsccpGttAppGr2Weight, cgsccpGttAppGr2Pc, cgsccpGttAppGr2Ssn, 
--    cgsccpGttAppGr2Ri, cgsccpGttAppGr2RefCount, 
--    cgsccpGttAppGr2AsName, cgsccpGttAppGr2NewSsn, 
--    cgsccpGttAppGr2NumUsed, cgsccpGttAppGr2Network, 
--    cgsccpGttAppGr2RowStatus

ciscoGsccpGttErrorsGroup OBJECT IDENTIFIER ::= { ciscoGsccpMIBGroups 17 }
-- OBJECT-GROUP
--  Status
--    mandatory
--  Descr
--    SCCP GTT Application Group objects.
--  objects
--    cgsccpGttErrorPeriod, cgsccpGttErrorRecoveryCount, 
--    cgsccpInstErrorIndicator, cgsccpGttTransErrorsNotifEnabled, 
--    cgsccpGttErrorsSelectorNotFound, 
--    cgsccpGttErrorsIncorrectFormat, cgsccpGttErrorsGtaNotFound, 
--    cgsccpGttErrorsHopViolation, cgsccpGttErrorsMapNotFound, 
--    cgsccpGttErrorsUnequipedSS, cgsccpGttErrorsSccpUnavailable, 
--    cgsccpGttErrorsDpcUnavailable, cgsccpGttErrorsSsUnavailable, 
--    cgsccpGttErrorsDpcCongested, cgsccpGttErrorsSsCongested, 
--    cgsccpGttErrorsRouteFailure, cgsccpGttErrorsSccpUnqualified

ciscoGsccpGttPrefGroupSup1 OBJECT IDENTIFIER ::= { ciscoGsccpMIBGroups 18 }
-- OBJECT-GROUP
--  Status
--    mandatory
--  Descr
--    SCCP GTT additional prefix conversion objects.
--  objects
--    cgsccpGttPref2EncodingScheme

ciscoGsccpNotificationsGroup OBJECT IDENTIFIER ::= { ciscoGsccpMIBGroups 9 }
-- NOTIFICATION-GROUP
--  Status
--    mandatory
--  Descr
--    SCCP notification objects.
--  notifications
--    ciscoGsccpGttMapStateChange, ciscoGsccpGttLoadTable

ciscoGsccpNotificationsGroupSup1 OBJECT IDENTIFIER ::= { ciscoGsccpMIBGroups 16 }
-- NOTIFICATION-GROUP
--  Status
--    mandatory
--  Descr
--    SCCP Error notification objects.
--  notifications
--    ciscoGsccpGttErrors

ciscoGsccpMIBCompliance OBJECT IDENTIFIER ::= { ciscoGsccpMIBCompliances 1 }
-- MODULE-COMPLIANCE
--  Status
--    deprecated
--  Descr
--    The compliance statement for entities which implement
--    the CISCO-ITP-GSCCP-MIB.my MIB
--  Module
--    >>current<<
--   MandGroup
--    ciscoGsccpGlobalEntryGroup
--   MandGroup
--    ciscoGsccpInstTableEntryGroup
--   MandGroup
--    ciscoGsccpGttConPcGroup
--   MandGroup
--    ciscoGsccpGttAppGroup
--   MandGroup
--    ciscoGsccpGttMapGroup
--   MandGroup
--    ciscoGsccpGttSelGroup
--   MandGroup
--    ciscoGsccpGttGtaGroup
--   MandGroup
--    ciscoGsccpGttPrefGroup
--   MandGroup
--    ciscoGsccpNotificationsGroup
--   ObjVar
--    cgsccpGttTranslateSample
--   ObjVar
--    cgsccpGttTranslatePeriod
--   ObjVar
--    cgsccpInstRowStatus
--   ObjVar
--    cgsccpGttAppGrType
--   ObjVar
--    cgsccpGttAppGrPc
--   ObjVar
--    cgsccpGttAppGrSsn
--   ObjVar
--    cgsccpGttAppGrRi
--   ObjVar
--    cgsccpGttAppGrMult
--   ObjVar
--    cgsccpGttAppGrAsName
--   ObjVar
--    cgsccpGttAppGrNewSsn
--   ObjVar
--    cgsccpGttAppGrRowStatus
--   ObjVar
--    cgsccpGttMapType
--   ObjVar
--    cgsccpGttMapMultInd
--   ObjVar
--    cgsccpGttMapBackupPc
--   ObjVar
--    cgsccpGttMapBackupSsn
--   ObjVar
--    cgsccpGttMapConPcList
--   ObjVar
--    cgsccpGttMapReRouteOnCong
--   ObjVar
--    cgsccpGttMapAdjacent
--   ObjVar
--    cgsccpGttMapRowStatus
--   ObjVar
--    cgsccpGttSelName
--   ObjVar
--    cgsccpGttSelQOS
--   ObjVar
--    cgsccpGttSelPrePrefConv
--   ObjVar
--    cgsccpGttSelPostPrefConv
--   ObjVar
--    cgsccpGttSelRowStatus
--   ObjVar
--    cgsccpGttGtaSelName
--   ObjVar
--    cgsccpGttGtaResType
--   ObjVar
--    cgsccpGttGtaResPc
--   ObjVar
--    cgsccpGttGtaResMap
--   ObjVar
--    cgsccpGttGtaResAppGroup
--   ObjVar
--    cgsccpGttGtaTTorSSN
--   ObjVar
--    cgsccpGttGtaTTorSSNvalue
--   ObjVar
--    cgsccpGttGtaRoutingInd
--   ObjVar
--    cgsccpGttGtaQOS
--   ObjVar
--    cgsccpGttGtaAsName
--   ObjVar
--    cgsccpGttGtaRowStatus
--   ObjVar
--    cgsccpGttPrefOutAddr
--   ObjVar
--    cgsccpGttPrefTblNAI
--   ObjVar
--    cgsccpGttPrefTblNP
--   ObjVar
--    cgsccpGttPrefItemNAI
--   ObjVar
--    cgsccpGttPrefItemNP
--   ObjVar
--    cgsccpGttPrefRowStatus

ciscoGsccpMIBComplianceRev1 OBJECT IDENTIFIER ::= { ciscoGsccpMIBCompliances 2 }
-- MODULE-COMPLIANCE
--  Status
--    deprecated
--  Descr
--    The compliance statement for entities which implement
--    the CISCO-ITP-GSCCP-MIB.my MIB
--  Module
--    >>current<<
--   MandGroup
--    ciscoGsccpGlobalEntryGroupRev1
--   MandGroup
--    ciscoGsccpGttConPcGroup
--   MandGroup
--    ciscoGsccpGttAppGroup
--   MandGroup
--    ciscoGsccpGttMapGroup
--   MandGroup
--    ciscoGsccpGttSelGroup
--   MandGroup
--    ciscoGsccpGttGtaGroup
--   MandGroup
--    ciscoGsccpGttPrefGroupRev1
--   MandGroup
--    ciscoGsccpNotificationsGroup
--   MandGroup
--    ciscoGsccpInstTableEntryGroupRev1
--   ObjVar
--    cgsccpGttTranslateSample
--   ObjVar
--    cgsccpGttTranslatePeriod
--   ObjVar
--    cgsccpInstRowStatus
--   ObjVar
--    cgsccpGttAppGrType
--   ObjVar
--    cgsccpGttAppGrPc
--   ObjVar
--    cgsccpGttAppGrSsn
--   ObjVar
--    cgsccpGttAppGrRi
--   ObjVar
--    cgsccpGttAppGrMult
--   ObjVar
--    cgsccpGttAppGrAsName
--   ObjVar
--    cgsccpGttAppGrNewSsn
--   ObjVar
--    cgsccpGttAppGrRowStatus
--   ObjVar
--    cgsccpGttMapType
--   ObjVar
--    cgsccpGttMapMultInd
--   ObjVar
--    cgsccpGttMapBackupPc
--   ObjVar
--    cgsccpGttMapBackupSsn
--   ObjVar
--    cgsccpGttMapConPcList
--   ObjVar
--    cgsccpGttMapReRouteOnCong
--   ObjVar
--    cgsccpGttMapAdjacent
--   ObjVar
--    cgsccpGttMapRowStatus
--   ObjVar
--    cgsccpGttSelName
--   ObjVar
--    cgsccpGttSelQOS
--   ObjVar
--    cgsccpGttSelPrePrefConv
--   ObjVar
--    cgsccpGttSelPostPrefConv
--   ObjVar
--    cgsccpGttSelRowStatus
--   ObjVar
--    cgsccpGttGtaSelName
--   ObjVar
--    cgsccpGttGtaResType
--   ObjVar
--    cgsccpGttGtaResPc
--   ObjVar
--    cgsccpGttGtaResMap
--   ObjVar
--    cgsccpGttGtaResAppGroup
--   ObjVar
--    cgsccpGttGtaTTorSSN
--   ObjVar
--    cgsccpGttGtaTTorSSNvalue
--   ObjVar
--    cgsccpGttGtaRoutingInd
--   ObjVar
--    cgsccpGttGtaQOS
--   ObjVar
--    cgsccpGttGtaAsName
--   ObjVar
--    cgsccpGttGtaRowStatus
--   ObjVar
--    cgsccpGttPref2OutAddr
--   ObjVar
--    cgsccpGttPref2TblNAI
--   ObjVar
--    cgsccpGttPref2TblNP
--   ObjVar
--    cgsccpGttPref2ItemNAI
--   ObjVar
--    cgsccpGttPref2ItemNP
--   ObjVar
--    cgsccpGttPref2RowStatus

ciscoGsccpMIBComplianceRev2 OBJECT IDENTIFIER ::= { ciscoGsccpMIBCompliances 3 }
-- MODULE-COMPLIANCE
--  Status
--    deprecated
--  Descr
--    The compliance statement for entities which implement
--     the CISCO-ITP-GSCCP-MIB.my MIB
--  Module
--    >>current<<
--   MandGroup
--    ciscoGsccpGlobalEntryGroupRev1
--   MandGroup
--    ciscoGsccpGttConPcGroup
--   MandGroup
--    ciscoGsccpGttMapGroup
--   MandGroup
--    ciscoGsccpGttSelGroup
--   MandGroup
--    ciscoGsccpGttPrefGroupRev1
--   MandGroup
--    ciscoGsccpNotificationsGroup
--   MandGroup
--    ciscoGsccpInstTableEntryGroupRev1
--   MandGroup
--    ciscoGsccpGttAppGroupRev2
--   MandGroup
--    ciscoGsccpGttGtaGroupRev2
--   ObjVar
--    cgsccpGttTranslateSample
--   ObjVar
--    cgsccpGttTranslatePeriod
--   ObjVar
--    cgsccpInstRowStatus
--   ObjVar
--    cgsccpGttAppGrType
--   ObjVar
--    cgsccpGttAppGrPc
--   ObjVar
--    cgsccpGttAppGrSsn
--   ObjVar
--    cgsccpGttAppGrRi
--   ObjVar
--    cgsccpGttAppGrMult
--   ObjVar
--    cgsccpGttAppGrAsName
--   ObjVar
--    cgsccpGttAppGrNewSsn
--   ObjVar
--    cgsccpGttAppGrRowStatus
--   ObjVar
--    cgsccpGttMapType
--   ObjVar
--    cgsccpGttMapMultInd
--   ObjVar
--    cgsccpGttMapBackupPc
--   ObjVar
--    cgsccpGttMapBackupSsn
--   ObjVar
--    cgsccpGttMapConPcList
--   ObjVar
--    cgsccpGttMapReRouteOnCong
--   ObjVar
--    cgsccpGttMapAdjacent
--   ObjVar
--    cgsccpGttMapRowStatus
--   ObjVar
--    cgsccpGttSelName
--   ObjVar
--    cgsccpGttSelQOS
--   ObjVar
--    cgsccpGttSelPrePrefConv
--   ObjVar
--    cgsccpGttSelPostPrefConv
--   ObjVar
--    cgsccpGttSelRowStatus
--   ObjVar
--    cgsccpGttGtaSelName
--   ObjVar
--    cgsccpGttGtaResType
--   ObjVar
--    cgsccpGttGtaResPc
--   ObjVar
--    cgsccpGttGtaResMap
--   ObjVar
--    cgsccpGttGtaResAppGroup
--   ObjVar
--    cgsccpGttGtaTTorSSN
--   ObjVar
--    cgsccpGttGtaTTorSSNvalue
--   ObjVar
--    cgsccpGttGtaRoutingInd
--   ObjVar
--    cgsccpGttGtaQOS
--   ObjVar
--    cgsccpGttGtaAsName
--   ObjVar
--    cgsccpGttGtaRowStatus
--   ObjVar
--    cgsccpGttPref2OutAddr
--   ObjVar
--    cgsccpGttPref2TblNAI
--   ObjVar
--    cgsccpGttPref2TblNP
--   ObjVar
--    cgsccpGttPref2ItemNAI
--   ObjVar
--    cgsccpGttPref2ItemNP
--   ObjVar
--    cgsccpGttPref2RowStatus

ciscoGsccpMIBComplianceRev3 OBJECT IDENTIFIER ::= { ciscoGsccpMIBCompliances 4 }
-- MODULE-COMPLIANCE
--  Status
--    deprecated
--  Descr
--    The compliance statement for entities which implement
--     the CISCO-ITP-GSCCP-MIB.my MIB
--  Module
--    >>current<<
--   MandGroup
--    ciscoGsccpGlobalEntryGroupRev1
--   MandGroup
--    ciscoGsccpGttConPcGroup
--   MandGroup
--    ciscoGsccpGttMapGroup
--   MandGroup
--    ciscoGsccpGttSelGroup
--   MandGroup
--    ciscoGsccpGttPrefGroupRev1
--   MandGroup
--    ciscoGsccpNotificationsGroup
--   MandGroup
--    ciscoGsccpInstTableEntryGroupRev1
--   MandGroup
--    ciscoGsccpGttGtaGroupRev2
--   MandGroup
--    ciscoGsccpGttAppGroupRev3
--   ObjVar
--    cgsccpGttTranslateSample
--   ObjVar
--    cgsccpGttTranslatePeriod
--   ObjVar
--    cgsccpInstRowStatus
--   ObjVar
--    cgsccpGttAppGr2Mult
--   ObjVar
--    cgsccpGttAppGr2Type
--   ObjVar
--    cgsccpGttAppGr2Cost
--   ObjVar
--    cgsccpGttAppGr2Weight
--   ObjVar
--    cgsccpGttAppGr2Pc
--   ObjVar
--    cgsccpGttAppGr2Ssn
--   ObjVar
--    cgsccpGttAppGr2Ri
--   ObjVar
--    cgsccpGttAppGr2AsName
--   ObjVar
--    cgsccpGttAppGr2NewSsn
--   ObjVar
--    cgsccpGttAppGr2Network
--   ObjVar
--    cgsccpGttAppGr2RowStatus
--   ObjVar
--    cgsccpGttMapType
--   ObjVar
--    cgsccpGttMapMultInd
--   ObjVar
--    cgsccpGttMapBackupPc
--   ObjVar
--    cgsccpGttMapBackupSsn
--   ObjVar
--    cgsccpGttMapConPcList
--   ObjVar
--    cgsccpGttMapReRouteOnCong
--   ObjVar
--    cgsccpGttMapAdjacent
--   ObjVar
--    cgsccpGttMapRowStatus
--   ObjVar
--    cgsccpGttSelName
--   ObjVar
--    cgsccpGttSelQOS
--   ObjVar
--    cgsccpGttSelPrePrefConv
--   ObjVar
--    cgsccpGttSelPostPrefConv
--   ObjVar
--    cgsccpGttSelRowStatus
--   ObjVar
--    cgsccpGttGtaSelName
--   ObjVar
--    cgsccpGttGtaResType
--   ObjVar
--    cgsccpGttGtaResPc
--   ObjVar
--    cgsccpGttGtaResMap
--   ObjVar
--    cgsccpGttGtaResAppGroup
--   ObjVar
--    cgsccpGttGtaTTorSSN
--   ObjVar
--    cgsccpGttGtaTTorSSNvalue
--   ObjVar
--    cgsccpGttGtaRoutingInd
--   ObjVar
--    cgsccpGttGtaQOS
--   ObjVar
--    cgsccpGttGtaAsName
--   ObjVar
--    cgsccpGttGtaRowStatus
--   ObjVar
--    cgsccpGttPref2OutAddr
--   ObjVar
--    cgsccpGttPref2TblNAI
--   ObjVar
--    cgsccpGttPref2TblNP
--   ObjVar
--    cgsccpGttPref2ItemNAI
--   ObjVar
--    cgsccpGttPref2ItemNP
--   ObjVar
--    cgsccpGttPref2RowStatus

ciscoGsccpMIBComplianceRev4 OBJECT IDENTIFIER ::= { ciscoGsccpMIBCompliances 5 }
-- MODULE-COMPLIANCE
--  Status
--    deprecated
--  Descr
--    The compliance statement for entities which implement
--     the CISCO-ITP-GSCCP-MIB.my MIB
--  Module
--    >>current<<
--   MandGroup
--    ciscoGsccpGlobalEntryGroupRev1
--   MandGroup
--    ciscoGsccpGttConPcGroup
--   MandGroup
--    ciscoGsccpGttMapGroup
--   MandGroup
--    ciscoGsccpGttSelGroup
--   MandGroup
--    ciscoGsccpGttPrefGroupRev1
--   MandGroup
--    ciscoGsccpNotificationsGroup
--   MandGroup
--    ciscoGsccpInstTableEntryGroupRev1
--   MandGroup
--    ciscoGsccpGttGtaGroupRev2
--   MandGroup
--    ciscoGsccpGttAppGroupRev3
--   MandGroup
--    ciscoGsccpNotificationsGroupSup1
--   MandGroup
--    ciscoGsccpGttErrorsGroup
--   ObjVar
--    cgsccpGttTranslateSample
--   ObjVar
--    cgsccpGttTranslatePeriod
--   ObjVar
--    cgsccpInstRowStatus
--   ObjVar
--    cgsccpGttAppGr2Mult
--   ObjVar
--    cgsccpGttAppGr2Type
--   ObjVar
--    cgsccpGttAppGr2Cost
--   ObjVar
--    cgsccpGttAppGr2Weight
--   ObjVar
--    cgsccpGttAppGr2Pc
--   ObjVar
--    cgsccpGttAppGr2Ssn
--   ObjVar
--    cgsccpGttAppGr2Ri
--   ObjVar
--    cgsccpGttAppGr2AsName
--   ObjVar
--    cgsccpGttAppGr2NewSsn
--   ObjVar
--    cgsccpGttAppGr2Network
--   ObjVar
--    cgsccpGttAppGr2RowStatus
--   ObjVar
--    cgsccpGttMapType
--   ObjVar
--    cgsccpGttMapMultInd
--   ObjVar
--    cgsccpGttMapBackupPc
--   ObjVar
--    cgsccpGttMapBackupSsn
--   ObjVar
--    cgsccpGttMapConPcList
--   ObjVar
--    cgsccpGttMapReRouteOnCong
--   ObjVar
--    cgsccpGttMapAdjacent
--   ObjVar
--    cgsccpGttMapRowStatus
--   ObjVar
--    cgsccpGttSelName
--   ObjVar
--    cgsccpGttSelQOS
--   ObjVar
--    cgsccpGttSelPrePrefConv
--   ObjVar
--    cgsccpGttSelPostPrefConv
--   ObjVar
--    cgsccpGttSelRowStatus
--   ObjVar
--    cgsccpGttGtaSelName
--   ObjVar
--    cgsccpGttGtaResType
--   ObjVar
--    cgsccpGttGtaResPc
--   ObjVar
--    cgsccpGttGtaResMap
--   ObjVar
--    cgsccpGttGtaResAppGroup
--   ObjVar
--    cgsccpGttGtaTTorSSN
--   ObjVar
--    cgsccpGttGtaTTorSSNvalue
--   ObjVar
--    cgsccpGttGtaRoutingInd
--   ObjVar
--    cgsccpGttGtaQOS
--   ObjVar
--    cgsccpGttGtaAsName
--   ObjVar
--    cgsccpGttGtaRowStatus
--   ObjVar
--    cgsccpGttPref2OutAddr
--   ObjVar
--    cgsccpGttPref2TblNAI
--   ObjVar
--    cgsccpGttPref2TblNP
--   ObjVar
--    cgsccpGttPref2ItemNAI
--   ObjVar
--    cgsccpGttPref2ItemNP
--   ObjVar
--    cgsccpGttPref2RowStatus

ciscoGsccpMIBComplianceRev5 OBJECT IDENTIFIER ::= { ciscoGsccpMIBCompliances 6 }
-- MODULE-COMPLIANCE
--  Status
--    mandatory
--  Descr
--    The compliance statement for entities which implement
--     the CISCO-ITP-GSCCP-MIB.my MIB
--  Module
--    >>current<<
--   MandGroup
--    ciscoGsccpGlobalEntryGroupRev1
--   MandGroup
--    ciscoGsccpGttConPcGroup
--   MandGroup
--    ciscoGsccpGttMapGroup
--   MandGroup
--    ciscoGsccpGttSelGroup
--   MandGroup
--    ciscoGsccpGttPrefGroupRev1
--   MandGroup
--    ciscoGsccpNotificationsGroup
--   MandGroup
--    ciscoGsccpInstTableEntryGroupRev1
--   MandGroup
--    ciscoGsccpGttGtaGroupRev2
--   MandGroup
--    ciscoGsccpGttAppGroupRev3
--   MandGroup
--    ciscoGsccpNotificationsGroupSup1
--   MandGroup
--    ciscoGsccpGttErrorsGroup
--   MandGroup
--    ciscoGsccpGttPrefGroupSup1
--   ObjVar
--    cgsccpGttTranslateSample
--   ObjVar
--    cgsccpGttTranslatePeriod
--   ObjVar
--    cgsccpInstRowStatus
--   ObjVar
--    cgsccpGttAppGr2Mult
--   ObjVar
--    cgsccpGttAppGr2Type
--   ObjVar
--    cgsccpGttAppGr2Cost
--   ObjVar
--    cgsccpGttAppGr2Weight
--   ObjVar
--    cgsccpGttAppGr2Pc
--   ObjVar
--    cgsccpGttAppGr2Ssn
--   ObjVar
--    cgsccpGttAppGr2Ri
--   ObjVar
--    cgsccpGttAppGr2AsName
--   ObjVar
--    cgsccpGttAppGr2NewSsn
--   ObjVar
--    cgsccpGttAppGr2Network
--   ObjVar
--    cgsccpGttAppGr2RowStatus
--   ObjVar
--    cgsccpGttMapType
--   ObjVar
--    cgsccpGttMapMultInd
--   ObjVar
--    cgsccpGttMapBackupPc
--   ObjVar
--    cgsccpGttMapBackupSsn
--   ObjVar
--    cgsccpGttMapConPcList
--   ObjVar
--    cgsccpGttMapReRouteOnCong
--   ObjVar
--    cgsccpGttMapAdjacent
--   ObjVar
--    cgsccpGttMapRowStatus
--   ObjVar
--    cgsccpGttSelName
--   ObjVar
--    cgsccpGttSelQOS
--   ObjVar
--    cgsccpGttSelPrePrefConv
--   ObjVar
--    cgsccpGttSelPostPrefConv
--   ObjVar
--    cgsccpGttSelRowStatus
--   ObjVar
--    cgsccpGttGtaSelName
--   ObjVar
--    cgsccpGttGtaResType
--   ObjVar
--    cgsccpGttGtaResPc
--   ObjVar
--    cgsccpGttGtaResMap
--   ObjVar
--    cgsccpGttGtaResAppGroup
--   ObjVar
--    cgsccpGttGtaTTorSSN
--   ObjVar
--    cgsccpGttGtaTTorSSNvalue
--   ObjVar
--    cgsccpGttGtaRoutingInd
--   ObjVar
--    cgsccpGttGtaQOS
--   ObjVar
--    cgsccpGttGtaAsName
--   ObjVar
--    cgsccpGttGtaRowStatus
--   ObjVar
--    cgsccpGttPref2OutAddr
--   ObjVar
--    cgsccpGttPref2TblNAI
--   ObjVar
--    cgsccpGttPref2TblNP
--   ObjVar
--    cgsccpGttPref2ItemNAI
--   ObjVar
--    cgsccpGttPref2ItemNP
--   ObjVar
--    cgsccpGttPref2RowStatus
--   ObjVar
--    cgsccpGttPref2EncodingScheme


END
