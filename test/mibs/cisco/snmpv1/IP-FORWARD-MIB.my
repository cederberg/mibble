-- MIB file created 15-Feb-2002 13:55:28, by
--   SMICng version 2.2.11-beta(PRO)(Solaris), January 20, 2001. Enterprise key cisco.com

IP-FORWARD-MIB DEFINITIONS ::= BEGIN

-- From file: "IP-FORWARD-MIB.my"
-- Compile options "4 7 F H N W 03 06 0B 0G 0N 0T"

IMPORTS
    RowStatus
            FROM SNMPv2-TC-v1
    ip
            FROM RFC1213-MIB
    Gauge, IpAddress
            FROM RFC1155-SMI
    OBJECT-TYPE
            FROM RFC-1212;

ipForward OBJECT IDENTIFIER ::= { ip 24 }
-- MODULE-IDENTITY
--  LastUpdated
--    9609190000Z
--  OrgName
--    IETF OSPF Working Group
--  ContactInfo
--            Fred Baker
--     Postal: Cisco Systems
--             519 Lado Drive
--             Santa Barbara, California 93111
--    
--     Phone:  +1 805 681 0115
--     Email:  fred@cisco.com
--     
--  Descr
--    The MIB module for the display of CIDR multipath IP Routes.
--  RevDate
--    9609190000Z
--  RevDescr
--    Revisions made by the OSPF WG.

ipForwardConformance OBJECT IDENTIFIER ::= { ipForward 5 }
ipForwardGroups OBJECT IDENTIFIER ::= { ipForwardConformance 1 }
ipForwardCompliances OBJECT IDENTIFIER ::= { ipForwardConformance 2 }

ipCidrRouteNumber OBJECT-TYPE
    SYNTAX Gauge
    ACCESS read-only
    STATUS mandatory
    DESCRIPTION
        "The number of current ipCidrRouteTable entries
        that are not invalid."
    ::= { ipForward 3 }

ipCidrRouteTable OBJECT-TYPE
    SYNTAX SEQUENCE OF IpCidrRouteEntry
    ACCESS not-accessible
    STATUS mandatory
    DESCRIPTION
        "This entity's IP Routing table."
    REFERENCE
        "RFC 1213 Section 6.6, The IP Group"
    ::= { ipForward 4 }

ipCidrRouteEntry OBJECT-TYPE
    SYNTAX IpCidrRouteEntry
    ACCESS not-accessible
    STATUS mandatory
    DESCRIPTION
        "A particular route to  a  particular  destina-
        tion, under a particular policy."
    INDEX { ipCidrRouteDest, ipCidrRouteMask, ipCidrRouteTos, ipCidrRouteNextHop }
    ::= { ipCidrRouteTable 1 }

IpCidrRouteEntry ::= SEQUENCE {
    ipCidrRouteDest IpAddress,
    ipCidrRouteMask IpAddress,
    ipCidrRouteTos INTEGER,
    ipCidrRouteNextHop IpAddress,
    ipCidrRouteIfIndex INTEGER,
    ipCidrRouteType INTEGER,
    ipCidrRouteProto INTEGER,
    ipCidrRouteAge INTEGER,
    ipCidrRouteInfo OBJECT IDENTIFIER,
    ipCidrRouteNextHopAS INTEGER,
    ipCidrRouteMetric1 INTEGER,
    ipCidrRouteMetric2 INTEGER,
    ipCidrRouteMetric3 INTEGER,
    ipCidrRouteMetric4 INTEGER,
    ipCidrRouteMetric5 INTEGER,
    ipCidrRouteStatus RowStatus
    }

ipCidrRouteDest OBJECT-TYPE
    SYNTAX IpAddress
    ACCESS read-only
    STATUS mandatory
    DESCRIPTION
        "The destination IP address of this route.
        
        This object may not take a Multicast (Class  D)
        address value.
        
        Any assignment (implicit or  otherwise)  of  an
        instance  of  this  object to a value x must be
        rejected if the bitwise logical-AND of  x  with
        the  value of the corresponding instance of the
        ipCidrRouteMask object is not equal to x."
    ::= { ipCidrRouteEntry 1 }

ipCidrRouteMask OBJECT-TYPE
    SYNTAX IpAddress
    ACCESS read-only
    STATUS mandatory
    DESCRIPTION
        "Indicate the mask to be logical-ANDed with the
        destination  address  before  being compared to
        the value  in  the  ipCidrRouteDest  field.   For
        those  systems  that  do  not support arbitrary
        subnet masks, an agent constructs the value  of
        the  ipCidrRouteMask  by  reference to the IP Ad-
        dress Class.
        
        Any assignment (implicit or  otherwise)  of  an
        instance  of  this  object to a value x must be
        rejected if the bitwise logical-AND of  x  with
        the  value of the corresponding instance of the
        ipCidrRouteDest object is not equal to ipCidrRoute-
        Dest."
    ::= { ipCidrRouteEntry 2 }

ipCidrRouteTos OBJECT-TYPE
    SYNTAX INTEGER(0..2147483647)
    ACCESS read-only
    STATUS mandatory
    DESCRIPTION
        "The policy specifier is the IP TOS Field.  The encoding
        of IP TOS is as specified  by  the  following convention.
        Zero indicates the default path if no more  specific
        policy applies.
        
        +-----+-----+-----+-----+-----+-----+-----+-----+
        |                 |                       |     |
        |   PRECEDENCE    |    TYPE OF SERVICE    |  0  |
        |                 |                       |     |
        +-----+-----+-----+-----+-----+-----+-----+-----+
        
                 IP TOS                IP TOS
            Field     Policy      Field     Policy
            Contents    Code      Contents    Code
            0 0 0 0  ==>   0      0 0 0 1  ==>   2
            0 0 1 0  ==>   4      0 0 1 1  ==>   6
            0 1 0 0  ==>   8      0 1 0 1  ==>  10
            0 1 1 0  ==>  12      0 1 1 1  ==>  14
            1 0 0 0  ==>  16      1 0 0 1  ==>  18
            1 0 1 0  ==>  20      1 0 1 1  ==>  22
            1 1 0 0  ==>  24      1 1 0 1  ==>  26
            1 1 1 0  ==>  28      1 1 1 1  ==>  30"
    ::= { ipCidrRouteEntry 3 }

ipCidrRouteNextHop OBJECT-TYPE
    SYNTAX IpAddress
    ACCESS read-only
    STATUS mandatory
    DESCRIPTION
        "On remote routes, the address of the next sys-
        tem en route; Otherwise, 0.0.0.0."
    ::= { ipCidrRouteEntry 4 }

ipCidrRouteIfIndex OBJECT-TYPE
    SYNTAX INTEGER
    ACCESS read-write
    STATUS mandatory
    DESCRIPTION
        "The ifIndex value which identifies  the  local
        interface  through  which  the next hop of this
        route should be reached."
    DEFVAL { 0 }
    ::= { ipCidrRouteEntry 5 }

ipCidrRouteType OBJECT-TYPE
    SYNTAX INTEGER {
        other(1),
        reject(2),
        local(3),
        remote(4)
        }
    ACCESS read-write
    STATUS mandatory
    DESCRIPTION
        "The type of route.  Note that local(3)  refers
        to  a route for which the next hop is the final
        destination; remote(4) refers to  a  route  for
        which  the  next  hop is not the final destina-
        tion.
        
        Routes which do not result in traffic forwarding or
        rejection should not be displayed even if the
        implementation keeps them stored internally.
        
        
        reject (2) refers to a route which, if matched, discards
        the message as unreachable. This is used in some
        protocols as a means of correctly aggregating routes."
    ::= { ipCidrRouteEntry 6 }

ipCidrRouteProto OBJECT-TYPE
    SYNTAX INTEGER {
        other(1),
        local(2),
        netmgmt(3),
        icmp(4),
        egp(5),
        ggp(6),
        hello(7),
        rip(8),
        isIs(9),
        esIs(10),
        ciscoIgrp(11),
        bbnSpfIgp(12),
        ospf(13),
        bgp(14),
        idpr(15),
        ciscoEigrp(16)
        }
    ACCESS read-only
    STATUS mandatory
    DESCRIPTION
        "The routing mechanism via which this route was
        learned.  Inclusion of values for gateway rout-
        ing protocols is not  intended  to  imply  that
        hosts should support those protocols."
    ::= { ipCidrRouteEntry 7 }

ipCidrRouteAge OBJECT-TYPE
    SYNTAX INTEGER
    ACCESS read-only
    STATUS mandatory
    DESCRIPTION
        "The number of seconds  since  this  route  was
        last  updated  or  otherwise  determined  to be
        correct.  Note that no semantics of  `too  old'
        can  be implied except through knowledge of the
        routing  protocol  by  which  the   route   was
        learned."
    DEFVAL { 0 }
    ::= { ipCidrRouteEntry 8 }

ipCidrRouteInfo OBJECT-TYPE
    SYNTAX OBJECT IDENTIFIER
    ACCESS read-write
    STATUS mandatory
    DESCRIPTION
        "A reference to MIB definitions specific to the
        particular  routing protocol which is responsi-
        ble for this route, as determined by the  value
        specified  in the route's ipCidrRouteProto value.
        If this information is not present,  its  value
        should be set to the OBJECT IDENTIFIER { 0 0 },
        which is a syntactically valid object  identif-
        ier, and any implementation conforming to ASN.1
        and the Basic Encoding Rules must  be  able  to
        generate and recognize this value."
    ::= { ipCidrRouteEntry 9 }

ipCidrRouteNextHopAS OBJECT-TYPE
    SYNTAX INTEGER
    ACCESS read-write
    STATUS mandatory
    DESCRIPTION
        "The Autonomous System Number of the Next  Hop.
        The  semantics of this object are determined by
        the routing-protocol specified in  the  route's
        ipCidrRouteProto  value. When  this object is
        unknown or not relevant its value should be set
        to zero."
    DEFVAL { 0 }
    ::= { ipCidrRouteEntry 10 }

ipCidrRouteMetric1 OBJECT-TYPE
    SYNTAX INTEGER
    ACCESS read-write
    STATUS mandatory
    DESCRIPTION
        "The primary routing  metric  for  this  route.
        The  semantics of this metric are determined by
        the routing-protocol specified in  the  route's
        ipCidrRouteProto  value.   If  this metric is not
        used, its value should be set to -1."
    DEFVAL { -1 }
    ::= { ipCidrRouteEntry 11 }

ipCidrRouteMetric2 OBJECT-TYPE
    SYNTAX INTEGER
    ACCESS read-write
    STATUS mandatory
    DESCRIPTION
        "An alternate routing metric  for  this  route.
        The  semantics of this metric are determined by
        the routing-protocol specified in  the  route's
        ipCidrRouteProto  value.   If  this metric is not
        used, its value should be set to -1."
    DEFVAL { -1 }
    ::= { ipCidrRouteEntry 12 }

ipCidrRouteMetric3 OBJECT-TYPE
    SYNTAX INTEGER
    ACCESS read-write
    STATUS mandatory
    DESCRIPTION
        "An alternate routing metric  for  this  route.
        The  semantics of this metric are determined by
        the routing-protocol specified in  the  route's
        ipCidrRouteProto  value.   If  this metric is not
        used, its value should be set to -1."
    DEFVAL { -1 }
    ::= { ipCidrRouteEntry 13 }

ipCidrRouteMetric4 OBJECT-TYPE
    SYNTAX INTEGER
    ACCESS read-write
    STATUS mandatory
    DESCRIPTION
        "An alternate routing metric  for  this  route.
        The  semantics of this metric are determined by
        the routing-protocol specified in  the  route's
        ipCidrRouteProto  value.   If  this metric is not
        used, its value should be set to -1."
    DEFVAL { -1 }
    ::= { ipCidrRouteEntry 14 }

ipCidrRouteMetric5 OBJECT-TYPE
    SYNTAX INTEGER
    ACCESS read-write
    STATUS mandatory
    DESCRIPTION
        "An alternate routing metric  for  this  route.
        The  semantics of this metric are determined by
        the routing-protocol specified in  the  route's
        ipCidrRouteProto  value.   If  this metric is not
        used, its value should be set to -1."
    DEFVAL { -1 }
    ::= { ipCidrRouteEntry 15 }

ipCidrRouteStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The row status variable, used according to
        row installation and removal conventions."
    ::= { ipCidrRouteEntry 16 }

ipForwardNumber OBJECT-TYPE
    SYNTAX Gauge
    ACCESS read-only
    STATUS obsolete
    DESCRIPTION
        "The number of current  ipForwardTable  entries
        that are not invalid."
    ::= { ipForward 1 }

ipForwardTable OBJECT-TYPE
    SYNTAX SEQUENCE OF IpForwardEntry
    ACCESS not-accessible
    STATUS obsolete
    DESCRIPTION
        "This entity's IP Routing table."
    REFERENCE
        "RFC 1213 Section 6.6, The IP Group"
    ::= { ipForward 2 }

ipForwardEntry OBJECT-TYPE
    SYNTAX IpForwardEntry
    ACCESS not-accessible
    STATUS obsolete
    DESCRIPTION
        "A particular route to  a  particular  destina-
        tion, under a particular policy."
    INDEX { ipForwardDest, ipForwardProto, ipForwardPolicy, ipForwardNextHop }
    ::= { ipForwardTable 1 }

IpForwardEntry ::= SEQUENCE {
    ipForwardDest IpAddress,
    ipForwardMask IpAddress,
    ipForwardPolicy INTEGER,
    ipForwardNextHop IpAddress,
    ipForwardIfIndex INTEGER,
    ipForwardType INTEGER,
    ipForwardProto INTEGER,
    ipForwardAge INTEGER,
    ipForwardInfo OBJECT IDENTIFIER,
    ipForwardNextHopAS INTEGER,
    ipForwardMetric1 INTEGER,
    ipForwardMetric2 INTEGER,
    ipForwardMetric3 INTEGER,
    ipForwardMetric4 INTEGER,
    ipForwardMetric5 INTEGER
    }

ipForwardDest OBJECT-TYPE
    SYNTAX IpAddress
    ACCESS read-only
    STATUS obsolete
    DESCRIPTION
        "The destination IP address of this route.   An
        entry  with  a value of 0.0.0.0 is considered a
        default route.
        
        This object may not take a Multicast (Class  D)
        address value.
        
        Any assignment (implicit or  otherwise)  of  an
        instance  of  this  object to a value x must be
        rejected if the bitwise logical-AND of  x  with
        the  value of the corresponding instance of the
        ipForwardMask object is not equal to x."
    ::= { ipForwardEntry 1 }

ipForwardMask OBJECT-TYPE
    SYNTAX IpAddress
    ACCESS read-write
    STATUS obsolete
    DESCRIPTION
        "Indicate the mask to be logical-ANDed with the
        destination  address  before  being compared to
        the value  in  the  ipForwardDest  field.   For
        those  systems  that  do  not support arbitrary
        subnet masks, an agent constructs the value  of
        the  ipForwardMask  by  reference to the IP Ad-
        dress Class.
        
        Any assignment (implicit or  otherwise)  of  an
        instance  of  this  object to a value x must be
        rejected if the bitwise logical-AND of  x  with
        the  value of the corresponding instance of the
        ipForwardDest object is not equal to ipForward-
        Dest."
    DEFVAL { '00000000'H }
    ::= { ipForwardEntry 2 }

ipForwardPolicy OBJECT-TYPE
    SYNTAX INTEGER(0..2147483647)
    ACCESS read-only
    STATUS obsolete
    DESCRIPTION
        "The general set of conditions that would cause
        the  selection  of  one multipath route (set of
        next hops for a given destination) is  referred
        to as 'policy'.
        
        Unless the mechanism indicated by ipForwardPro-
        to specifies otherwise, the policy specifier is
        the IP TOS Field.  The encoding of IP TOS is as
         specified  by  the  following convention.  Zero
        indicates the default path if no more  specific
        policy applies.
        
        +-----+-----+-----+-----+-----+-----+-----+-----+
        |                 |                       |     |
        |   PRECEDENCE    |    TYPE OF SERVICE    |  0  |
        |                 |                       |     |
        +-----+-----+-----+-----+-----+-----+-----+-----+
        
                 IP TOS                IP TOS
            Field     Policy      Field     Policy
            Contents    Code      Contents    Code
            0 0 0 0  ==>   0      0 0 0 1  ==>   2
            0 0 1 0  ==>   4      0 0 1 1  ==>   6
            0 1 0 0  ==>   8      0 1 0 1  ==>  10
            0 1 1 0  ==>  12      0 1 1 1  ==>  14
            1 0 0 0  ==>  16      1 0 0 1  ==>  18
            1 0 1 0  ==>  20      1 0 1 1  ==>  22
            1 1 0 0  ==>  24      1 1 0 1  ==>  26
            1 1 1 0  ==>  28      1 1 1 1  ==>  30
        
        Protocols defining 'policy' otherwise must  ei-
        ther define a set of values which are valid for
        this  object  or  must  implement  an  integer-
        instanced  policy table for which this object's
        value acts as an index."
    ::= { ipForwardEntry 3 }

ipForwardNextHop OBJECT-TYPE
    SYNTAX IpAddress
    ACCESS read-only
    STATUS obsolete
    DESCRIPTION
        "On remote routes, the address of the next sys-
        tem en route; Otherwise, 0.0.0.0."
    ::= { ipForwardEntry 4 }

ipForwardIfIndex OBJECT-TYPE
    SYNTAX INTEGER
    ACCESS read-write
    STATUS obsolete
    DESCRIPTION
        "The ifIndex value which identifies  the  local
        interface  through  which  the next hop of this
        route should be reached."
    DEFVAL { 0 }
    ::= { ipForwardEntry 5 }

ipForwardType OBJECT-TYPE
    SYNTAX INTEGER {
        other(1),
        invalid(2),
        local(3),
        remote(4)
        }
    ACCESS read-write
    STATUS obsolete
    DESCRIPTION
        "The type of route.  Note that local(3)  refers
        to  a route for which the next hop is the final
        destination; remote(4) refers to  a  route  for
        which  the  next  hop is not the final destina-
        tion.
        
        Setting this object to the value invalid(2) has
        the  effect  of  invalidating the corresponding
        entry in the ipForwardTable object.   That  is,
        it  effectively  disassociates  the destination
        identified with said entry from the route iden-
        tified    with    said   entry.    It   is   an
        implementation-specific matter  as  to  whether
        the agent removes an invalidated entry from the
        table.  Accordingly, management  stations  must
        be prepared to receive tabular information from
        agents that corresponds to entries not current-
        ly  in  use.  Proper interpretation of such en-
        tries requires examination of the relevant  ip-
        ForwardType object."
    DEFVAL { invalid }
    ::= { ipForwardEntry 6 }

ipForwardProto OBJECT-TYPE
    SYNTAX INTEGER {
        other(1),
        local(2),
        netmgmt(3),
        icmp(4),
        egp(5),
        ggp(6),
        hello(7),
        rip(8),
        is-is(9),
        es-is(10),
        ciscoIgrp(11),
        bbnSpfIgp(12),
        ospf(13),
        bgp(14),
        idpr(15)
        }
    ACCESS read-only
    STATUS obsolete
    DESCRIPTION
        "The routing mechanism via which this route was
        learned.  Inclusion of values for gateway rout-
        ing protocols is not  intended  to  imply  that
        hosts should support those protocols."
    ::= { ipForwardEntry 7 }

ipForwardAge OBJECT-TYPE
    SYNTAX INTEGER
    ACCESS read-only
    STATUS obsolete
    DESCRIPTION
        "The number of seconds  since  this  route  was
        last  updated  or  otherwise  determined  to be
        correct.  Note that no semantics of  `too  old'
        can  be implied except through knowledge of the
        routing  protocol  by  which  the   route   was
        learned."
    DEFVAL { 0 }
    ::= { ipForwardEntry 8 }

ipForwardInfo OBJECT-TYPE
    SYNTAX OBJECT IDENTIFIER
    ACCESS read-write
    STATUS obsolete
    DESCRIPTION
        "A reference to MIB definitions specific to the
        particular  routing protocol which is responsi-
        ble for this route, as determined by the  value
        specified  in the route's ipForwardProto value.
        If this information is not present,  its  value
        should be set to the OBJECT IDENTIFIER { 0 0 },
        which is a syntactically valid object  identif-
        ier, and any implementation conforming to ASN.1
        and the Basic Encoding Rules must  be  able  to
        generate and recognize this value."
    ::= { ipForwardEntry 9 }

ipForwardNextHopAS OBJECT-TYPE
    SYNTAX INTEGER
    ACCESS read-write
    STATUS obsolete
    DESCRIPTION
        "The Autonomous System Number of the Next  Hop.
        When  this  is  unknown  or not relevant to the
        protocol indicated by ipForwardProto, zero."
    DEFVAL { 0 }
    ::= { ipForwardEntry 10 }

ipForwardMetric1 OBJECT-TYPE
    SYNTAX INTEGER
    ACCESS read-write
    STATUS obsolete
    DESCRIPTION
        "The primary routing  metric  for  this  route.
        The  semantics of this metric are determined by
        the routing-protocol specified in  the  route's
        ipForwardProto  value.   If  this metric is not
        used, its value should be set to -1."
    DEFVAL { -1 }
    ::= { ipForwardEntry 11 }

ipForwardMetric2 OBJECT-TYPE
    SYNTAX INTEGER
    ACCESS read-write
    STATUS obsolete
    DESCRIPTION
        "An alternate routing metric  for  this  route.
        The  semantics of this metric are determined by
        the routing-protocol specified in  the  route's
        ipForwardProto  value.   If  this metric is not
        used, its value should be set to -1."
    DEFVAL { -1 }
    ::= { ipForwardEntry 12 }

ipForwardMetric3 OBJECT-TYPE
    SYNTAX INTEGER
    ACCESS read-write
    STATUS obsolete
    DESCRIPTION
        "An alternate routing metric  for  this  route.
        The  semantics of this metric are determined by
        the routing-protocol specified in  the  route's
        ipForwardProto  value.   If  this metric is not
        used, its value should be set to -1."
    DEFVAL { -1 }
    ::= { ipForwardEntry 13 }

ipForwardMetric4 OBJECT-TYPE
    SYNTAX INTEGER
    ACCESS read-write
    STATUS obsolete
    DESCRIPTION
        "An alternate routing metric  for  this  route.
        The  semantics of this metric are determined by
        the routing-protocol specified in  the  route's
        ipForwardProto  value.   If  this metric is not
        used, its value should be set to -1."
    DEFVAL { -1 }
    ::= { ipForwardEntry 14 }

ipForwardMetric5 OBJECT-TYPE
    SYNTAX INTEGER
    ACCESS read-write
    STATUS obsolete
    DESCRIPTION
        "An alternate routing metric  for  this  route.
        The  semantics of this metric are determined by
        the routing-protocol specified in  the  route's
        ipForwardProto  value.   If  this metric is not
        used, its value should be set to -1."
    DEFVAL { -1 }
    ::= { ipForwardEntry 15 }

ipForwardCidrRouteGroup OBJECT IDENTIFIER ::= { ipForwardGroups 3 }
-- OBJECT-GROUP
--  Status
--    mandatory
--  Descr
--    The CIDR Route Table.
--  objects
--    ipCidrRouteNumber, ipCidrRouteDest, ipCidrRouteMask, 
--    ipCidrRouteTos, ipCidrRouteNextHop, ipCidrRouteIfIndex, 
--    ipCidrRouteType, ipCidrRouteProto, ipCidrRouteAge, 
--    ipCidrRouteInfo, ipCidrRouteNextHopAS, ipCidrRouteMetric1, 
--    ipCidrRouteMetric2, ipCidrRouteMetric3, ipCidrRouteMetric4, 
--    ipCidrRouteMetric5, ipCidrRouteStatus

ipForwardMultiPathGroup OBJECT IDENTIFIER ::= { ipForwardGroups 2 }
-- OBJECT-GROUP
--  Status
--    obsolete
--  Descr
--    IP Multipath Route Table.
--  objects
--    ipForwardNumber, ipForwardDest, ipForwardMask, 
--    ipForwardPolicy, ipForwardNextHop, ipForwardIfIndex, 
--    ipForwardType, ipForwardProto, ipForwardAge, ipForwardInfo, 
--    ipForwardNextHopAS, ipForwardMetric1, ipForwardMetric2, 
--    ipForwardMetric3, ipForwardMetric4, ipForwardMetric5

ipForwardCompliance OBJECT IDENTIFIER ::= { ipForwardCompliances 1 }
-- MODULE-COMPLIANCE
--  Status
--    mandatory
--  Descr
--    The compliance statement for SNMPv2 entities
--    which implement the ipForward MIB.
--  Module
--    >>current<<
--   MandGroup
--    ipForwardCidrRouteGroup

ipForwardOldCompliance OBJECT IDENTIFIER ::= { ipForwardCompliances 2 }
-- MODULE-COMPLIANCE
--  Status
--    obsolete
--  Descr
--    The compliance statement for SNMP entities
--    which implement the ipForward MIB.
--  Module
--    >>current<<
--   MandGroup
--    ipForwardMultiPathGroup


END
