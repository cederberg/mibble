-- MIB created 5/02/100 19:14:49, by
--   SMIC (the next generation) version 1.6.29, November 22, 1994.

CISCO-WAN-RSRC-PART-MIB DEFINITIONS ::= BEGIN

-- From file: "CISCO-WAN-RSRC-PART-MIB.my"

IMPORTS
    OBJECT-TYPE
            FROM RFC-1212
    Unsigned32
            FROM CISCO-TC
    TruthValue, RowStatus
            FROM SNMPv2-TC-v1
    ifIndex
            FROM IF-MIB
    ciscoMgmt
            FROM CISCO-SMI;

ciscoWANRsrcPartMIB OBJECT IDENTIFIER ::= { ciscoMgmt 125 }
-- MODULE-IDENTITY
--  LastUpdated
--    9910120000Z
--  OrgName
--    Cisco Systems, Inc.
--  ContactInfo
--    Cisco Systems
--     Customer Service
--    
--    Postal: 170 W Tasman Drive
--     San Jose, CA  95134
--     USA
--    
--    Tel: +1 800 553-NETS
--    
--    E-mail: cs-wanatm@cisco.com
--  Descr
--    The MIB module to manage resource partition objects. A resource partion 
--     is configured on a virtual interface (ifType value atmVirtual(149)) or 
--     atm interface (ifType value atm(37)). 
--     An administrator can partition connection related resources like VPI,
--     VCI ranges, bandwidth and total amount of available connection entries
--     in the switch through these MIB tables.
--    
--     Terminolgies used:
--     VSI       - Virtual Switch Interface, a hardware-independent switch
--         control protocol. This allows a Switch to be
--         controlled by a multiple controllers such as PNNI, MPLS.
--         These control planes can be internal or external to the
--         switch.The VSI interface defines the messages and associated
--         functions which allow communication between the controller
--         and the switch.This interface is expected to support all
--         types of connections (voice,data,frame relay,ATM) for PVCs,
--         SPVCs and SVCs.
--    
--     VSI Master - software component which requests connections and receives
--          switch generic information. This controls one or more VSI
--          Slaves. This may run on the switch or a dedicated controller
--          platform. This is the master module.It performs the interface
--          to the higher layer networking software and handles all VSI
--          related functions.
--    
--     Controller - Software ( and possibly hardware) which manages topology
--          and network resources and performs VSI Master function.
--          This performs source routing for ent-to-end SVCs, including
--          general call acceptance GCAC,setup calls with other
--          controllers.
--          PNNI and MPLS are examples of controllers.

ciscoWANRsrcPartMIBObjects OBJECT IDENTIFIER ::= { ciscoWANRsrcPartMIB 1 }
cwRsrcPartConfGrp OBJECT IDENTIFIER ::= { ciscoWANRsrcPartMIBObjects 1 }
cwRsrcPartMIBConformance OBJECT IDENTIFIER ::= { ciscoWANRsrcPartMIB 3 }
cwRsrcPartMIBCompliances OBJECT IDENTIFIER ::= { cwRsrcPartMIBConformance 1 }
cwRsrcPartMIBGroups OBJECT IDENTIFIER ::= { cwRsrcPartMIBConformance 2 }

cwRsrcPartConfTable OBJECT-TYPE
    SYNTAX SEQUENCE OF CwRsrcPartConfEntry
    ACCESS not-accessible
    STATUS mandatory
    DESCRIPTION
        "This table is for configuring resource partition parameters.
         A resource partition is configured on an interface whose ifType
         is atmVirtual(149) or atm(37). An entry can be added,deleted or 
         modified. Entries in this table can be modified through the 
         commands provided by the CLI also."
    ::= { cwRsrcPartConfGrp 1 }

cwRsrcPartConfEntry OBJECT-TYPE
    SYNTAX CwRsrcPartConfEntry
    ACCESS not-accessible
    STATUS mandatory
    DESCRIPTION
        "An entry for a resource partition. A resource partition 
         has to be created before connections can be added to the 
         interface.
        In the following objects, ingress direction  means, from network to 
         switch, and egress direction means, from switch to network."
    INDEX { ifIndex, cwRsrcPartID }
    ::= { cwRsrcPartConfTable 1 }

CwRsrcPartConfEntry ::= SEQUENCE {
    cwRsrcPartID Unsigned32,
    cwRsrcPartController Unsigned32,
    cwRsrcPartEgrGuarPctBwConf Unsigned32,
    cwRsrcPartEgrMaxPctBwConf Unsigned32,
    cwRsrcPartIngGuarPctBwConf Unsigned32,
    cwRsrcPartIngMaxPctBwConf Unsigned32,
    cwRsrcPartEgrPctBwUsed Unsigned32,
    cwRsrcPartIngPctBwUsed Unsigned32,
    cwRsrcPartEgrPctBwAvail Unsigned32,
    cwRsrcPartIngPctBwAvail Unsigned32,
    cwRsrcPartVpiLo Unsigned32,
    cwRsrcPartVpiHigh Unsigned32,
    cwRsrcPartVciLo Unsigned32,
    cwRsrcPartVciHigh Unsigned32,
    cwRsrcPartGuarCon Unsigned32,
    cwRsrcPartMaxCon Unsigned32,
    cwRsrcPartUsedCon Unsigned32,
    cwRsrcPartAvailCon Unsigned32,
    cwRsrcPartRowStatus RowStatus
    }

cwRsrcPartID OBJECT-TYPE
    SYNTAX Unsigned32(1..255)
--    Rsyntax Gauge32(1..255)
    ACCESS not-accessible
    STATUS mandatory
    DESCRIPTION
        "This is resource partition identifier. One interface can have multiple
        resource partitions on it."
    ::= { cwRsrcPartConfEntry 1 }

cwRsrcPartController OBJECT-TYPE
    SYNTAX Unsigned32(1..255)
--    Rsyntax Gauge32(1..255)
    ACCESS read-write
    STATUS mandatory
    DESCRIPTION
        "This is controller identifier. Once a resource partition is added
         the controller identified by this identifier
         can access resources configured for this partition."
    ::= { cwRsrcPartConfEntry 2 }

cwRsrcPartEgrGuarPctBwConf OBJECT-TYPE
    SYNTAX Unsigned32(0..1000000)
--    Rsyntax Gauge32(0..1000000)
--  Units
--    0.0001 percentage
    ACCESS read-write
    STATUS mandatory
    DESCRIPTION
        "The guaranteed percentage bandwidth reserved for the 
         resource partition in egress direction.
         The sum of all resource partition guaranteed 
         bandwidths cannot exceed 100% of interface's guaranteed bandwidth."
    DEFVAL { 0 }
    ::= { cwRsrcPartConfEntry 3 }

cwRsrcPartEgrMaxPctBwConf OBJECT-TYPE
    SYNTAX Unsigned32(0..1000000)
--    Rsyntax Gauge32(0..1000000)
--  Units
--    0.0001 percentage
    ACCESS read-write
    STATUS mandatory
    DESCRIPTION
        "The maximum percentage bandwidth for the resource partition 
         in egress direction. This is not the guaranteed bandwidth. If
         bandwidth is available, the resource partition will be allocated 
         bandwidth up to this value."
    DEFVAL { 0 }
    ::= { cwRsrcPartConfEntry 4 }

cwRsrcPartIngGuarPctBwConf OBJECT-TYPE
    SYNTAX Unsigned32(0..1000000)
--    Rsyntax Gauge32(0..1000000)
--  Units
--    0.0001 percentage
    ACCESS read-write
    STATUS mandatory
    DESCRIPTION
        "The guaranteed percentage bandwidth reserved for the 
         resource partition in ingress direction.
         The sum of all resource partition guaranteed
         bandwidths cannot exceed 100% of the interface's guaranteed bandwidth."
    DEFVAL { 0 }
    ::= { cwRsrcPartConfEntry 5 }

cwRsrcPartIngMaxPctBwConf OBJECT-TYPE
    SYNTAX Unsigned32(0..1000000)
--    Rsyntax Gauge32(0..1000000)
--  Units
--    0.0001 percentage
    ACCESS read-write
    STATUS mandatory
    DESCRIPTION
        " The maximum percentage bandwidth allocated for the resource 
          partition in ingress direction. 
          This is not the guaranteed bandwidth. If bandwidth
          is available, the resource partition will be allocated 
          bandwidth up to this value."
    DEFVAL { 0 }
    ::= { cwRsrcPartConfEntry 6 }

cwRsrcPartEgrPctBwUsed OBJECT-TYPE
    SYNTAX Unsigned32(0..1000000)
--    Rsyntax Gauge32(0..1000000)
--  Units
--    0.0001 percentage
    ACCESS read-only
    STATUS mandatory
    DESCRIPTION
        " This is the percentage bandwidth used by the resource
          partition in egress direction."
    ::= { cwRsrcPartConfEntry 7 }

cwRsrcPartIngPctBwUsed OBJECT-TYPE
    SYNTAX Unsigned32(0..1000000)
--    Rsyntax Gauge32(0..1000000)
--  Units
--    0.0001 percentage
    ACCESS read-only
    STATUS mandatory
    DESCRIPTION
        " This is the percentage bandwidth used by the resource
          partition in ingress direction."
    ::= { cwRsrcPartConfEntry 8 }

cwRsrcPartEgrPctBwAvail OBJECT-TYPE
    SYNTAX Unsigned32(0..1000000)
--    Rsyntax Gauge32(0..1000000)
--  Units
--    0.0001 percentage
    ACCESS read-only
    STATUS mandatory
    DESCRIPTION
        " This is the percentage bandwidth available on the resource
          partition in egress direction."
    ::= { cwRsrcPartConfEntry 9 }

cwRsrcPartIngPctBwAvail OBJECT-TYPE
    SYNTAX Unsigned32(0..1000000)
--    Rsyntax Gauge32(0..1000000)
--  Units
--    0.0001 percentage
    ACCESS read-only
    STATUS mandatory
    DESCRIPTION
        " This is the percentage bandwidth available on the resource
          partition in ingress direction."
    ::= { cwRsrcPartConfEntry 10 }

cwRsrcPartVpiLo OBJECT-TYPE
    SYNTAX Unsigned32(0..4095)
--    Rsyntax Gauge32(0..4095)
    ACCESS read-write
    STATUS mandatory
    DESCRIPTION
        "The beginning of the VPI range for this partition. Connections
         provisioned on this partition must  have a VPI greater than or
         equal to this value."
    ::= { cwRsrcPartConfEntry 11 }

cwRsrcPartVpiHigh OBJECT-TYPE
    SYNTAX Unsigned32(0..4095)
--    Rsyntax Gauge32(0..4095)
    ACCESS read-write
    STATUS mandatory
    DESCRIPTION
        "The end of the VPI range for this partition.  Connections
         provisioned on this partition must have a VPI less than or
         equal to this value."
    ::= { cwRsrcPartConfEntry 12 }

cwRsrcPartVciLo OBJECT-TYPE
    SYNTAX Unsigned32(0..65535)
--    Rsyntax Gauge32(0..65535)
    ACCESS read-write
    STATUS mandatory
    DESCRIPTION
        "The beginning of the VCI range  for this partition. Connections
         provisioned on this partition must  have VCI greater than or
         equal to this VCI."
    ::= { cwRsrcPartConfEntry 13 }

cwRsrcPartVciHigh OBJECT-TYPE
    SYNTAX Unsigned32(0..65535)
--    Rsyntax Gauge32(0..65535)
    ACCESS read-write
    STATUS mandatory
    DESCRIPTION
        "The end of the VCI range reserved for this partition. Connections
         provisioned on this partition must have a VCI less than or equal
         to this VCI."
    ::= { cwRsrcPartConfEntry 14 }

cwRsrcPartGuarCon OBJECT-TYPE
    SYNTAX Unsigned32(0..131072)
--    Rsyntax Gauge32(0..131072)
    ACCESS read-write
    STATUS mandatory
    DESCRIPTION
        "The guaranteed number of connections that can be
         configured on this partition."
    DEFVAL { 0 }
    ::= { cwRsrcPartConfEntry 15 }

cwRsrcPartMaxCon OBJECT-TYPE
    SYNTAX Unsigned32(0..131072)
--    Rsyntax Gauge32(0..131072)
    ACCESS read-write
    STATUS mandatory
    DESCRIPTION
        "The maximum number of connections that can be configured on
         this partition."
    ::= { cwRsrcPartConfEntry 16 }

cwRsrcPartUsedCon OBJECT-TYPE
    SYNTAX Unsigned32(0..131072)
--    Rsyntax Gauge32(0..131072)
    ACCESS read-only
    STATUS mandatory
    DESCRIPTION
        "This is the number of connections currently in use on this partition."
    ::= { cwRsrcPartConfEntry 17 }

cwRsrcPartAvailCon OBJECT-TYPE
    SYNTAX Unsigned32(0..131072)
--    Rsyntax Gauge32(0..131072)
    ACCESS read-only
    STATUS mandatory
    DESCRIPTION
        "This is the number of connections available, that can be 
         added on this partition."
    ::= { cwRsrcPartConfEntry 18 }

cwRsrcPartRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This will add, delete or modify the partition. Resource partition
         can be created by setting this object to createAndGo(4).
        Row may be deleted by setting this object to destroy(6)."
    ::= { cwRsrcPartConfEntry 19 }

cwRsrcPartIlmiTable OBJECT-TYPE
    SYNTAX SEQUENCE OF CwRsrcPartIlmiEntry
    ACCESS not-accessible
    STATUS mandatory
    DESCRIPTION
        "This is the Ilmi configuration table. When a row is created in
        cwRsrcPartConfTable, a corresponding row is automatically created
         in this table, with the default values for Ilmi objects, i.e,with 
        Ilmi signalling disabled."
    ::= { cwRsrcPartConfGrp 2 }

cwRsrcPartIlmiEntry OBJECT-TYPE
    SYNTAX CwRsrcPartIlmiEntry
    ACCESS not-accessible
    STATUS mandatory
    DESCRIPTION
        "An entry in this table is created automatically when a resource 
         partition is created. By default, Ilmi is disabled on active resource   
         partitions. Ilmi can be enabled by setting 'cwRsrcPartIlmiEnabled' to
        'true'. An entry will be deleted from this table when a corresponding
         resource partition entry is deleted from cwRsrcPartConfTable."
    INDEX { ifIndex, cwRsrcPartID }
    ::= { cwRsrcPartIlmiTable 1 }

CwRsrcPartIlmiEntry ::= SEQUENCE {
    cwRsrcPartIlmiEnabled TruthValue,
    cwRsrcPartSignallingVpi INTEGER,
    cwRsrcPartSignallingVci INTEGER,
    cwRsrcPartIlmiTrapEnable TruthValue,
    cwRsrcPartIlmiEstablishConPollIntvl Unsigned32,
    cwRsrcPartIlmiCheckConPollIntvl Unsigned32,
    cwRsrcPartIlmiConPollInactFactor Unsigned32
    }

cwRsrcPartIlmiEnabled OBJECT-TYPE
    SYNTAX TruthValue
--    Rsyntax INTEGER {
--        true(1),
--        false(2)
--        }
    ACCESS read-write
    STATUS mandatory
    DESCRIPTION
        "By setting the value of this object to 'true', Ilmi signalling is
         enabled on the resource partition."
    DEFVAL { false }
    ::= { cwRsrcPartIlmiEntry 1 }

cwRsrcPartSignallingVpi OBJECT-TYPE
    SYNTAX INTEGER(0..255)
    ACCESS read-write
    STATUS mandatory
    DESCRIPTION
        "Indicates the VPI on which signalling cells arrive on this resource
         partition."
    DEFVAL { 0 }
    ::= { cwRsrcPartIlmiEntry 2 }

cwRsrcPartSignallingVci OBJECT-TYPE
    SYNTAX INTEGER(0..65535)
    ACCESS read-write
    STATUS mandatory
    DESCRIPTION
        "Indicates the VCI on which signalling cells arrive on this resource
         partition."
    DEFVAL { 16 }
    ::= { cwRsrcPartIlmiEntry 3 }

cwRsrcPartIlmiTrapEnable OBJECT-TYPE
    SYNTAX TruthValue
--    Rsyntax INTEGER {
--        true(1),
--        false(2)
--        }
    ACCESS read-write
    STATUS mandatory
    DESCRIPTION
        "Ilmi trap generation can be enabled or disabled using this object."
    ::= { cwRsrcPartIlmiEntry 4 }

cwRsrcPartIlmiEstablishConPollIntvl OBJECT-TYPE
    SYNTAX Unsigned32(1..65535)
--    Rsyntax Gauge32(1..65535)
--  Units
--    seconds
    ACCESS read-write
    STATUS mandatory
    DESCRIPTION
        "The amount of time S between successive transmissions
         of ILMI messages on this interface for the purpose of
         detecting establishment of ILMI connectivity."
    REFERENCE
        "ATM Forum ILMI 4.0 Section 8.3.1"
    DEFVAL { 1 }
    ::= { cwRsrcPartIlmiEntry 5 }

cwRsrcPartIlmiCheckConPollIntvl OBJECT-TYPE
    SYNTAX Unsigned32(0..65535)
--    Rsyntax Gauge32(0..65535)
--  Units
--    seconds
    ACCESS read-write
    STATUS mandatory
    DESCRIPTION
        "The amount of time T between successive transmissions
         of ILMI messages on this interface for the purpose of
         detecting loss of ILMI connectivity.  The distinguished
         value zero disables ILMI connectivity procedures on
         this interface."
    REFERENCE
        "ATM Forum ILMI 4.0 Section 8.3.1"
    DEFVAL { 5 }
    ::= { cwRsrcPartIlmiEntry 6 }

cwRsrcPartIlmiConPollInactFactor OBJECT-TYPE
    SYNTAX Unsigned32(0..65535)
--    Rsyntax Gauge32(0..65535)
    ACCESS read-write
    STATUS mandatory
    DESCRIPTION
        "The number K of consecutive polls on this interface
        for which no ILMI response message is received before
        ILMI connectivity is declared lost."
    REFERENCE
        "ATM Forum ILMI 4.0 Section 8.3.1"
    DEFVAL { 4 }
    ::= { cwRsrcPartIlmiEntry 7 }

cwRsrcPartCtlrConfTable OBJECT-TYPE
    SYNTAX SEQUENCE OF CwRsrcPartCtlrConfEntry
    ACCESS not-accessible
    STATUS mandatory
    DESCRIPTION
        "This table is for configuring additional controllers to
         manage a resource partition."
    ::= { cwRsrcPartConfGrp 3 }

cwRsrcPartCtlrConfEntry OBJECT-TYPE
    SYNTAX CwRsrcPartCtlrConfEntry
    ACCESS not-accessible
    STATUS mandatory
    DESCRIPTION
        "An entry for additional controllers to control an existing
         resource partition. The resource partition, identified by indices
         ifIndex and cwRsrcPartID, must exist in the cwRsrcPartConfTable.
         An entry from this table is deleted if the cwRsrcPartID associated
         entry from cwRsrcPartConfTable is deleted."
    INDEX { ifIndex, cwRsrcPartID, cwRsrcPartCtlrController }
    ::= { cwRsrcPartCtlrConfTable 1 }

CwRsrcPartCtlrConfEntry ::= SEQUENCE {
    cwRsrcPartCtlrController Unsigned32,
    cwRsrcPartCtlrRowStatus RowStatus
    }

cwRsrcPartCtlrController OBJECT-TYPE
    SYNTAX Unsigned32(1..255)
--    Rsyntax Gauge32(1..255)
    ACCESS not-accessible
    STATUS mandatory
    DESCRIPTION
        "This is controller identifier. One resource partition can be
         controlled by multiple controllers.User may want to do this to
         configure redundant controllers."
    ::= { cwRsrcPartCtlrConfEntry 1 }

cwRsrcPartCtlrRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This is used to  create a row in the cwRsrcPartCtlrConfTable.
         A redundant controller is added by  setting this object to 
         createAndGo(4).
         Row may be deleted by setting this object to destroy(6)."
    ::= { cwRsrcPartCtlrConfEntry 2 }

cwRsrcPartMIBGroup OBJECT IDENTIFIER ::= { cwRsrcPartMIBGroups 1 }
-- OBJECT-GROUP
--  Status
--    mandatory
--  Descr
--    These are objects related to Resource partition group.
--  objects
--    cwRsrcPartController, cwRsrcPartEgrGuarPctBwConf, 
--    cwRsrcPartEgrMaxPctBwConf, cwRsrcPartIngGuarPctBwConf, 
--    cwRsrcPartIngMaxPctBwConf, cwRsrcPartEgrPctBwAvail, 
--    cwRsrcPartIngPctBwAvail, cwRsrcPartEgrPctBwUsed, 
--    cwRsrcPartIngPctBwUsed, cwRsrcPartVpiLo, cwRsrcPartVpiHigh, 
--    cwRsrcPartVciLo, cwRsrcPartVciHigh, cwRsrcPartGuarCon, 
--    cwRsrcPartMaxCon, cwRsrcPartUsedCon, cwRsrcPartAvailCon, 
--    cwRsrcPartRowStatus

cwRsrcPartIlmiMIBGroup OBJECT IDENTIFIER ::= { cwRsrcPartMIBGroups 2 }
-- OBJECT-GROUP
--  Status
--    mandatory
--  Descr
--    These are objects related to Ilmi configuration on a 
--     Resource partition.
--  objects
--    cwRsrcPartIlmiEnabled, cwRsrcPartSignallingVpi, 
--    cwRsrcPartSignallingVci, cwRsrcPartIlmiTrapEnable, 
--    cwRsrcPartIlmiEstablishConPollIntvl, 
--    cwRsrcPartIlmiCheckConPollIntvl, 
--    cwRsrcPartIlmiConPollInactFactor

cwRsrcPartMappingGroup OBJECT IDENTIFIER ::= { cwRsrcPartMIBGroups 3 }
-- OBJECT-GROUP
--  Status
--    mandatory
--  Descr
--    These are objects used to configure redundant controllers
--     for resource partitions.
--  objects
--    cwRsrcPartCtlrRowStatus

cwRsrcPartMIBCompliance OBJECT IDENTIFIER ::= { cwRsrcPartMIBCompliances 1 }
-- MODULE-COMPLIANCE
--  Status
--    mandatory
--  Descr
--    The Compliance statement for Resource partition 
--     management group.
--  Module
--    >>current<<
--   MandGroup
--    cwRsrcPartMIBGroup
--   OptGroup
--    cwRsrcPartIlmiMIBGroup
--   OptGroup
--    cwRsrcPartMappingGroup


END
