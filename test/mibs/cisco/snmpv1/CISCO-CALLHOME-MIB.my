-- MIB file created 12-Apr-2006 09:57:07, by
--   SMICng version 2.2.11-beta(PRO)(Solaris), January 20, 2001. Enterprise key cisco.com

CISCO-CALLHOME-MIB DEFINITIONS ::= BEGIN

-- From file: "CISCO-CALLHOME-MIB.my"
-- Compile options "4 7 F H N O W 03 06 0B 0G 0N 0T"

IMPORTS
    TruthValue, RowStatus, TimeStamp
            FROM SNMPv2-TC-v1
    SnmpAdminString
            FROM SNMP-FRAMEWORK-MIB
    InetAddressType, InetAddress
            FROM INET-ADDRESS-MIB
    SyslogSeverity
            FROM CISCO-SYSLOG-MIB
    ciscoMgmt
            FROM CISCO-SMI
    Counter, Gauge
            FROM RFC1155-SMI
    OBJECT-TYPE
            FROM RFC-1212
    TRAP-TYPE
            FROM RFC-1215;

ciscoCallHomeMIB OBJECT IDENTIFIER ::= { ciscoMgmt 300 }
-- MODULE-IDENTITY
--  LastUpdated
--    200603300000Z
--  OrgName
--    Cisco Systems Inc.
--  ContactInfo
--         Cisco Systems
--          Customer Service
--    Postal: 170 W Tasman Drive
--          San Jose, CA  95134
--          USA
--    Tel: +1 800 553 -NETS
--    E-mail: cs-san@cisco.com, cs-lan-switch-snmp@cisco.com
--  Descr
--    The MIB module for the management of Call Home feature
--    within the frame  work of Cisco's Call Home 
--    architecture.
--    Customers deploying solutions to run mission critical
--    applications such as storage solutions demand very high
--    availability and Serviceability from their products
--    and/or support partners.
--    To meet these requirements, a feature called 
--    'CallHome' is provided which allows the system
--    experiencing Hardware/Software problems to 
--    automatically send the relevant failure information 
--    back to the Support Center at the Support Partners for 
--    troubleshooting or to get replacement hardware 
--    dispatched. This feature also provides advanced
--    features that allow storage systems to send 
--    performance, accounting and system health information 
--    in addition to just the fault information.
--  RevDate
--    200603300000Z
--  RevDescr
--    Add ccmUserDefCmdGroup.
--  RevDate
--    200408020000Z
--  RevDescr
--    Added new compliance section 'chMIBCompliance3'.
--  RevDate
--    200402110000Z
--  RevDescr
--    New Table 'callHomeSwInventoryTable' has been added 
--     to provide the callhome inventory information about 
--     the software services. 
--     New objects 'ccmPeriodicSwInventoryMsgEnable', 
--     'ccmPeriodicSwInventoryTimeFrame' and
--     'ccmMsgThrottlingEnable' has been added.
--  RevDate
--    200402090000Z
--  RevDescr
--    Max size of 'callHomeDestProfileName' has been
--     changed to 31 chars.
--  RevDate
--    200310300000Z
--  RevDescr
--    New object 'callHomeDestProfileAlertGroups' has been 
--    added to the callHomeDestProfileTable.
--    Row creation support has been added in the 
--    callHomeDestProfileTable. 
--    New Table 'callHomeAlertGroupTypeTable' has been added.
--  RevDate
--    200305200000Z
--  RevDescr
--    New object 'callHomeDestProfileMsgLevel' has been 
--    added to the callHomeDestProfileTable.
--  RevDate
--    200210280000Z
--  RevDescr
--    Initial version of this MIB module.

ccmCallHomeNotifications OBJECT IDENTIFIER ::= { ciscoCallHomeMIB 0 }
ciscoCallHomeMIBObjects OBJECT IDENTIFIER ::= { ciscoCallHomeMIB 1 }
chMIBConformance OBJECT IDENTIFIER ::= { ciscoCallHomeMIB 2 }
ccmCallHomeConfiguration OBJECT IDENTIFIER ::= { ciscoCallHomeMIBObjects 1 }
ccmCallHomeStats OBJECT IDENTIFIER ::= { ciscoCallHomeMIBObjects 2 }
ccmCallHomeAlertGroupCfg OBJECT IDENTIFIER ::= { ccmCallHomeConfiguration 30 }
chMIBCompliances OBJECT IDENTIFIER ::= { chMIBConformance 1 }
chMIBGroups     OBJECT IDENTIFIER ::= { chMIBConformance 2 }

CallHomeAlert ::= INTEGER {
        noOp(1),
        test(2),
        inventory(3)
        }
-- TEXTUAL-CONVENTION
--  Status
--    mandatory
--  Descr
--    The type of the CallHome alert. 
--        noOp (1)      - no alert             
--        test (2)      - alert name 'Test'
--        inventory (3) - alert name 'Inventory'
--    .

CallHomeMsgFormat ::= INTEGER {
        xml(1),
        fullText(2),
        shortText(3)
        }
-- TEXTUAL-CONVENTION
--  Status
--    mandatory
--  Descr
--    CallHome Message format. 
--        xml (1)       - XML (Extensible Markup Language) 
--                      - encoded.            
--        fullText (2)  - Plain text without any encoding.
--        shortText (3) - Short text without any encoding
--    
--     The context of the CallHome message depends on the 
--     message. In general, all the CallHome message is sent 
--     with following information : 
--    
--    'Subject : System Notification from '
--    'TimeStamp :' 
--    'Message Name :' 
--    'Message Type :' 
--    'Level :'  
--    'Message Device ID :'  
--    'Customer ID :' (optional) 
--    'Contract ID :' (optional) 
--    'Site ID :'     (optional) 
--    'Server ID :'  
--    'Message Description :' 
--    'Device Name :' 
--    'Contact Name :'  
--    'Contact email :'  
--    'Contact Phone :' (optional) 
--    'Street Address :'  (optional) 
--    'Model Name :' 
--    'Serial Number :' 
--    'Part Number :' 
--    'Chassis Hardware Version :' 
--    'Supervisor Software Version :' 
--    
--    Following information are required only if a hardware 
--    event caused the CallHome message : 
--    'Affected FRU' 
--    'Affected FRU Serial Number' 
--    'Affected FRU Slot :'  
--    'Affected FRU Hardware Version :' 
--    'Affected FRU Software Version :' 
--    
--    Following is required for all the messages : 
--    'Command Output :'
--    
--    The command output may depend on the implementation and
--    severity of the CallHome message. But at minimum, 
--    following information which are contained in the output
--    of the CLI commands must be included.
--    - Hardware model
--    - software version
--    - context information explaining the state of the device.
--    - uptime
--    - brief inventory information
--    
--    The exact format depends on the format type chosen.
--    For 'xml', the above information is encoded in the XML
--    format. For 'fullText', above information is sent out in
--    plain text. For 'shortText', only following information 
--    is provided in plain text:
--       'Subject : System Notification from  '
--       'Device Id : ' 
--       'TimeStamp : ' 
--       'Error Message : ' 
--       'Severity Level :'  
--    .
--  Refer
--    For more information on the XML, refer to RFC3023.

CallHomeTransportMethod ::= INTEGER {
        email(1),
        ftp(2),
        http(3)
        }
-- TEXTUAL-CONVENTION
--  Status
--    mandatory
--  Descr
--    CallHome transport mechanism used to deliver the alert 
--    messages.
--       email (1) - via email
--       ftp (2),  - via ftp
--       http (3)  - via http
--    .

CallHomeMsgLevel ::= INTEGER {
        debug(1),
        normal(2),
        notification(3),
        warning(4),
        minor(5),
        major(6),
        critical(7),
        fatal(8),
        disaster(9),
        catastrophic(10)
        }
-- TEXTUAL-CONVENTION
--  Status
--    mandatory
--  Descr
--    This object contains the severity level for use as a
--    threshold for filtering the alerts sent to a destination 
--    profile. 
--    It ranges from 1 to 10, with 10 being highest severity.

AlertGroupList ::= OCTET STRING(SIZE(0..8))
-- TEXTUAL-CONVENTION
--  Status
--    mandatory
--  Descr
--    AlertGroups are a pre-defined set of call-home alerts.
--    Users can specify these alert groups for a destination
--    profile, to choose the call-home alerts messages to be
--    sent out to the destination. This object represents 
--    the list of alert groups (alert group types)
--    configured for a destination profile.
--    
--    Each 'bit' within the value of an object of this type,
--    specifies a configured alertgroup type.
--    Bit position '0' ( most significant bit) in the value 
--    of this object is reserved.
--    
--    The value of each 'bit' (set/reset) represents whether 
--    an alert group type is configured or not for a 
--    particular destination profile.
--    
--    Bit position 1, represents whether the 
--    'callHomeAlertGroupName' corresponding to the 
--    'callHomeAlertGroupTypeIndex' 1 in the 
--    'callHomeAlertGroupTypeTable' is configured or
--    not for a particular destination profile.
--    
--    Bit position 2, represents whether the 
--    'callHomeAlertGroupName' corresponding to the 
--    'callHomeAlertGroupTypeIndex' 2 in the 
--    'callHomeAlertGroupTypeTable' is configured or
--    not for a particular destination profile.
--    
--    If there is no entry in the 'alertGroupTypeTable',
--    with 'alertGroupTypeIndex' 'n', then
--    bit position 'n' in the value of this object is
--    irrelevant. 
--    
--    If the length of an object of this type is less
--    than 8 bytes, then the alert group types which are 
--    not represented are not considered to be part of this
--    list, i.e., effectively, the string is extended to
--    be of length 8 bytes by appending bytes
--    containing x'00'. Note that this means that the
--    zero length string represents the 'list is empty'
--    value.

callHomeEnable OBJECT-TYPE
    SYNTAX TruthValue
--    Rsyntax INTEGER {
--        true(1),
--        false(2)
--        }
    ACCESS read-write
    STATUS mandatory
    DESCRIPTION
        "This object enables/disables the CallHome infrastructure 
        on the local device."
    ::= { ccmCallHomeConfiguration 1 }

sysContactPhoneNumber OBJECT-TYPE
    SYNTAX SnmpAdminString(SIZE(0|12|13..17))
--    Rsyntax OCTET STRING(SIZE(0|12|13..17))
    ACCESS read-write
    STATUS mandatory
    DESCRIPTION
        "The phone number of the contact person for this managed 
         node. The phone number must start with '+' and contains 
         only numeric characters except for space and '-'.
         Some valid phone numbers are 
            +44 20 8332 9091
            +45 44886556
            +81-46-215-4678
            +1-650-327-2600
         A set operation on this object with a invalid format will
         result in an error."
    ::= { ccmCallHomeConfiguration 2 }

sysContactEmailAddress OBJECT-TYPE
    SYNTAX SnmpAdminString
--    Rsyntax OCTET STRING(SIZE(0..255))
    ACCESS read-write
    STATUS mandatory
    DESCRIPTION
        "The email address of the contact person for this managed
        node. The format of this object is an an e-mail address
        which conforms to RFC822 and RFC1123 'addr-spec'
        syntax.
        Some valid Email Addresses are
                       raj@helpme.com,
                       bob@service.com,
                       mtom@abc.caview.ca.us
        
        A set operation on this object with a invalid format will
        result in an error."
    ::= { ccmCallHomeConfiguration 3 }

sysStreetAddress OBJECT-TYPE
    SYNTAX SnmpAdminString
--    Rsyntax OCTET STRING(SIZE(0..255))
    ACCESS read-write
    STATUS mandatory
    DESCRIPTION
        "The mailing address of this managed node."
    ::= { ccmCallHomeConfiguration 4 }

callHomeCustomerId OBJECT-TYPE
    SYNTAX SnmpAdminString
--    Rsyntax OCTET STRING(SIZE(0..255))
    ACCESS read-write
    STATUS mandatory
    DESCRIPTION
        "A string, in whatever format is appropriate, to identify
        the customer."
    ::= { ccmCallHomeConfiguration 5 }

callHomeContractId OBJECT-TYPE
    SYNTAX SnmpAdminString
--    Rsyntax OCTET STRING(SIZE(0..255))
    ACCESS read-write
    STATUS mandatory
    DESCRIPTION
        "A string, in whatever format is appropriate, to identify 
        the support contract between the customer and support 
        partner."
    ::= { ccmCallHomeConfiguration 6 }

callHomeSiteId OBJECT-TYPE
    SYNTAX SnmpAdminString
--    Rsyntax OCTET STRING(SIZE(0..255))
    ACCESS read-write
    STATUS mandatory
    DESCRIPTION
        "A location identifier of this device."
    ::= { ccmCallHomeConfiguration 7 }

callHomeDeviceServicePriority OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "The service priority of the device.
        This determines how fast the device has to be serviced."
    DEFVAL { debug }
    ::= { ccmCallHomeConfiguration 8 }

callHomeAlertAction OBJECT-TYPE
    SYNTAX CallHomeAlert
--    Rsyntax INTEGER {
--        noOp(1),
--        test(2),
--        inventory(3)
--        }
    ACCESS read-write
    STATUS mandatory
    DESCRIPTION
        "This object acts as a trigger by which the generation of
        a particular type of alert can be verified.  Specifically,
        setting this object to a type of alert triggers the
        sending of a callhome message for the specified type
        so that the call home backend is activated.
        
        No action is taken if this object is set to 'noOp'.
        The value of the object when read is always 'noOp'."
    ::= { ccmCallHomeConfiguration 9 }

callHomeAlertActionStatus OBJECT-TYPE
    SYNTAX INTEGER {
        unknown(1),
        successful(2),
        inprogress(3),
        failed(4)
        }
    ACCESS read-only
    STATUS mandatory
    DESCRIPTION
        "This object provides the status of the last callhome action 
        invocation. 
           unknown (1)     - unknown
           successful (2)  - successful 
           inprogress (3)  - action in progress
           failed (4)      - failed
        
        If the value of this object is 'failed', then the 
        callHomeAlertActionFailureCause provides the cause for the 
        failure.
        
        Management stations could read value of this object after a 
        successful set to the callHomeAlertAction object to find
        out the result of the test."
    ::= { ccmCallHomeConfiguration 10 }

callHomeAlertActionFailureCause OBJECT-TYPE
    SYNTAX SnmpAdminString
--    Rsyntax OCTET STRING(SIZE(0..255))
    ACCESS read-only
    STATUS mandatory
    DESCRIPTION
        "This object provides the failure cause for the last 
        callhome test invocation. 
        
        Note that this object is valid only if value of 
        callHomeAlertActionStatus is 'failed'."
    ::= { ccmCallHomeConfiguration 11 }

callHomeDestProfileTable OBJECT-TYPE
    SYNTAX SEQUENCE OF CallHomeDestProfileEntry
    ACCESS not-accessible
    STATUS mandatory
    DESCRIPTION
        "This table contains destination profiles.
        The CallHome feature requires the destination profiles to be
        setup to be able to send the CallHome messages to 
        destinations configured.
        By default there will be 3 entries in this table with 
        callHomeDestProfileName 'xml', 'full_txt' and 'short_txt'.
        User can't delete these 3 entries, but can modify the
        values of callHomeDestProfileMaxMsgSize and 
        callHomeDestProfileMsgLevel in these entries. However, the
        user can create/delete/modify entries with other 
        callHome profile names."
    ::= { ccmCallHomeConfiguration 12 }

callHomeDestProfileEntry OBJECT-TYPE
    SYNTAX CallHomeDestProfileEntry
    ACCESS not-accessible
    STATUS mandatory
    DESCRIPTION
        "An entry containing information about a CallHome 
        destination."
    INDEX { callHomeDestProfileName }
    ::= { callHomeDestProfileTable 1 }

CallHomeDestProfileEntry ::= SEQUENCE {
    callHomeDestProfileName SnmpAdminString,
    callHomeDestProfileMsgFormat CallHomeMsgFormat,
    callHomeDestProfileMaxMsgSize Gauge,
    callHomeDestProfileTrnsprtMthd CallHomeTransportMethod,
    callHomeDestProfileStatus RowStatus,
    callHomeDestProfileMsgLevel CallHomeMsgLevel,
    callHomeDestProfileAlertGroups AlertGroupList
    }

callHomeDestProfileName OBJECT-TYPE
    SYNTAX SnmpAdminString(SIZE(1..31))
--    Rsyntax OCTET STRING(SIZE(1..31))
    ACCESS not-accessible
    STATUS mandatory
    DESCRIPTION
        "Name of the destination profile."
    ::= { callHomeDestProfileEntry 1 }

callHomeDestProfileMsgFormat OBJECT-TYPE
    SYNTAX CallHomeMsgFormat
--    Rsyntax INTEGER {
--        xml(1),
--        fullText(2),
--        shortText(3)
--        }
    ACCESS read-write
    STATUS mandatory
    DESCRIPTION
        "The CallHome format used with profile while sending
        the message."
    DEFVAL { xml }
    ::= { callHomeDestProfileEntry 2 }

callHomeDestProfileMaxMsgSize OBJECT-TYPE
    SYNTAX Gauge(0..1000000)
--  Units
--    bytes
    ACCESS read-write
    STATUS mandatory
    DESCRIPTION
        "Maximum message size that can be sent to destination
        pointed to by this destination profile.
        If the 'callHomeDestProfileMsgFormat' is set to 
        'xml' or 'full_txt' then the default value for this 
        object is '500,000'.
        If the ''callHomeDestProfileMsgFormat' is 'short_txt'
        then the default value for this object is '4000'.   
        
        A value of 0 for this object indicates no limitation
        on maximum message size that can be sent to destination
        pointed to by this destination profile."
    ::= { callHomeDestProfileEntry 3 }

callHomeDestProfileTrnsprtMthd OBJECT-TYPE
    SYNTAX CallHomeTransportMethod
--    Rsyntax INTEGER {
--        email(1),
--        ftp(2),
--        http(3)
--        }
    ACCESS read-write
    STATUS mandatory
    DESCRIPTION
        "CallHome transport method used to deliver the alert 
        messages."
    DEFVAL { email }
    ::= { callHomeDestProfileEntry 4 }

callHomeDestProfileStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Status of this row."
    ::= { callHomeDestProfileEntry 5 }

callHomeDestProfileMsgLevel OBJECT-TYPE
    SYNTAX CallHomeMsgLevel
--    Rsyntax INTEGER {
--        debug(1),
--        normal(2),
--        notification(3),
--        warning(4),
--        minor(5),
--        major(6),
--        critical(7),
--        fatal(8),
--        disaster(9),
--        catastrophic(10)
--        }
    ACCESS read-write
    STATUS mandatory
    DESCRIPTION
        "This object contains the threshold level, used for 
        filtering alert messages sent to a destination. 
        Callhome alert message with severity level lower than 
        the configured threshold level would not be sent. 
        The default threshold level is debug (1), which means 
        all the alert messages will be sent."
    DEFVAL { debug }
    ::= { callHomeDestProfileEntry 6 }

callHomeDestProfileAlertGroups OBJECT-TYPE
    SYNTAX AlertGroupList
--    Rsyntax OCTET STRING(SIZE(0..8))
    ACCESS read-write
    STATUS mandatory
    DESCRIPTION
        "This object represent the list of configured alert 
        groups for this destination profile.
        User can modify the configured alert groups, by 
        Setting/Resetting the appropriate bits in this 
        object. Resetting all the bits to '0' means no alert
        group is configured, hence no alert would be sent 
        to the destination profile. 
        
        If the existing value of this object has all bits
        'set' , corresponding to all the 
        'callhomeAlertGroupTypeIndex' in the
        'callHomeAlertGroupTypeTable', then the user can
        either 'reset all' or 'set all' of the above 
        configured bits. User can't choose to modify only
        few bits in this case.
            
        However if the existing value of this object,
        has not have 'all bits set' corresponding 
        to the all 'callHomeAlertGroupTypeIndex' in the 
        'callHomeAlertGroupTypeTable', then user can
        choose to modify only few or all the bits."
    ::= { callHomeDestProfileEntry 7 }

callHomeEmailAddrTblMaxEntries OBJECT-TYPE
    SYNTAX Gauge(0..65535)
    ACCESS read-only
    STATUS mandatory
    DESCRIPTION
        "The maximum number of entries that the agent supports in 
        the callHomeDestEmailAddressTable."
    ::= { ccmCallHomeConfiguration 13 }

callHomeDestEmailAddressTable OBJECT-TYPE
    SYNTAX SEQUENCE OF CallHomeDestEmailAddressEntry
    ACCESS not-accessible
    STATUS mandatory
    DESCRIPTION
        "This table contains email addresses for the destination 
        profiles. Each destination profile could contain one or more
        email addresses associated with it."
    ::= { ccmCallHomeConfiguration 14 }

callHomeDestEmailAddressEntry OBJECT-TYPE
    SYNTAX CallHomeDestEmailAddressEntry
    ACCESS not-accessible
    STATUS mandatory
    DESCRIPTION
        "An entry containing information about a CallHome 
        destination email address.
        
        An entry cannot made 'active' until corresponding instance 
        of 'callHomeDestEmailAddress' is created.
        
        Also, 'callHomeDestEmailAddress' cannot be modified when 
        'callHomeDestEmailAddressStatus' is 'active'.
        To modify 'callHomeDestEmailAddress', the entry must be 
        deleted and re-created with the new value of it."
    INDEX { callHomeDestProfileName, callHomeDestEmailAddressIndex }
    ::= { callHomeDestEmailAddressTable 1 }

CallHomeDestEmailAddressEntry ::= SEQUENCE {
    callHomeDestEmailAddressIndex Gauge,
    callHomeDestEmailAddress SnmpAdminString,
    callHomeDestEmailAddressStatus RowStatus
    }

callHomeDestEmailAddressIndex OBJECT-TYPE
    SYNTAX Gauge(1..65535)
    ACCESS not-accessible
    STATUS mandatory
    DESCRIPTION
        "An arbitrary integer value, greater than zero, and less 
        than and equal to callHomeEmailAddrTblMaxEntries, which 
        identifies an Email address. 
        These integer values should be non-volatile."
    ::= { callHomeDestEmailAddressEntry 1 }

callHomeDestEmailAddress OBJECT-TYPE
    SYNTAX SnmpAdminString
--    Rsyntax OCTET STRING(SIZE(0..255))
    ACCESS read-write
    STATUS mandatory
    DESCRIPTION
        "The email address associated this destination profile. The 
        format of this object is an an e-mail address which conforms
        to RFC822 and RFC1123 'addr-spec' syntax. Some examples are
                       raj@helpme.com,
                       bob@service.com,
                       mtom@abc.caview.ca.us.
        A set operation on this object with a invalid format will
        result in an error."
    ::= { callHomeDestEmailAddressEntry 2 }

callHomeDestEmailAddressStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Status of this row."
    ::= { callHomeDestEmailAddressEntry 3 }

callHomeEmailFrom OBJECT-TYPE
    SYNTAX SnmpAdminString
--    Rsyntax OCTET STRING(SIZE(0..255))
    ACCESS read-write
    STATUS mandatory
    DESCRIPTION
        "The email address that is to be used in the 'From' field 
        when sending the email using SMTP. The format of this object
        is an e-mail address which conforms to RFC822 and RFC1123 
        'addr-spec' syntax.
        Some examples are
                       raj@helpme.com,
                       bob@service.com,
                       mtom@abc.caview.ca.us.
        A set operation on this object with a invalid format will
        result in an error."
    REFERENCE
        "RFC 2821 - Simple Mail Transfer Protocol and 
        RFC822 - Standard for the Format of Arpa Internet Text 
        Messages."
    ::= { ccmCallHomeConfiguration 15 }

callHomeEmailReplyTo OBJECT-TYPE
    SYNTAX SnmpAdminString
--    Rsyntax OCTET STRING(SIZE(0..255))
    ACCESS read-write
    STATUS mandatory
    DESCRIPTION
        "The email address that is to be used in the 'Reply-To' 
        field when sending the email using SMTP. The format of 
        this object is an e-mail address which conforms to RFC822 
        and RFC1123 'addr-spec' syntax.
        Some examples are
                       raj@helpme.com,
                       bob@service.com,
                       mtom@abc.caview.ca.us.
        A set operation on this object with a invalid format will
        result in an error."
    REFERENCE
        "RFC 2821 - Simple Mail Transfer Protocol and 
        RFC822 - Standard for the Format of Arpa Internet Text 
        Messages."
    ::= { ccmCallHomeConfiguration 16 }

callHomeEmailMsgDispNotification OBJECT-TYPE
    SYNTAX SnmpAdminString
--    Rsyntax OCTET STRING(SIZE(0..255))
    ACCESS read-write
    STATUS mandatory
    DESCRIPTION
        "The email address to which the Message Disposition 
        Notification (also called 'Return Receipt') sent when the 
        email sent from this device is read by the receiver. The 
        format of this object is an an e-mail address which conforms
        to RFC822 and RFC1123 'addr-spec' syntax.
        Some examples are
                       raj@helpme.com,
                       bob@service.com,
                       mtom@abc.caview.ca.us.
        A set operation on this object with a invalid format will
        result in an error."
    REFERENCE
        "RFC 2298 - An Extensible Message Format
        for Message Disposition Notifications."
    ::= { ccmCallHomeConfiguration 17 }

callHomeSmtpServerAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-write
    STATUS mandatory
    DESCRIPTION
        "Address Type of the SMTP server."
    ::= { ccmCallHomeConfiguration 18 }

callHomeSmtpServerAddr OBJECT-TYPE
    SYNTAX InetAddress
--    Rsyntax OCTET STRING(SIZE(0..255))
    ACCESS read-write
    STATUS mandatory
    DESCRIPTION
        "Address of the SMTP server."
    REFERENCE
        "RFC 2821 - Simple Mail Transfer Protocol."
    ::= { ccmCallHomeConfiguration 19 }

callHomeSmtpServerPort OBJECT-TYPE
    SYNTAX Gauge(1..65535)
    ACCESS read-write
    STATUS mandatory
    DESCRIPTION
        "Port of the SMTP server."
    REFERENCE
        "RFC 2821 - Simple Mail Transfer Protocol."
    DEFVAL { 25 }
    ::= { ccmCallHomeConfiguration 20 }

ccmSmtpServersTblMaxEntries OBJECT-TYPE
    SYNTAX Gauge(0..65535)
    ACCESS read-only
    STATUS mandatory
    DESCRIPTION
        "Indicates the maximum number of SMTP servers supported by
        this device.  A value of zero indicates no limitation on
        the number of SMTP servers."
    ::= { ccmCallHomeConfiguration 21 }

ccmSmtpServersTable OBJECT-TYPE
    SYNTAX SEQUENCE OF CcmSmtpServersEntry
    ACCESS not-accessible
    STATUS mandatory
    DESCRIPTION
        "This table contains entries that identify lists of
        SMTP servers that may be used by system to send out
        e-mail notification to addresses configured in
        callHomeDestEmailAddressTable.
        
        The maximum number of entries that can be created for
        for this table is limited by the scalar object
        ccmSmtpServersTblMaxEntries.
        
        The device sequentially tries all the entries in this
        table until it successfully sends out an email notification."
    ::= { ccmCallHomeConfiguration 22 }

ccmSmtpServersEntry OBJECT-TYPE
    SYNTAX CcmSmtpServersEntry
    ACCESS not-accessible
    STATUS mandatory
    DESCRIPTION
        "An entry containing information about a SMTP server.
        
        An entry cannot made 'active' until corresponding instance
        of all objects in the same conceptual row are created.
        
        Any object in the entry can not be modified if the value
        of ccmSmtpServersStatus is 'active'."
    INDEX { ccmSmtpServersAddrType, ccmSmtpServersAddr }
    ::= { ccmSmtpServersTable 1 }

CcmSmtpServersEntry ::= SEQUENCE {
    ccmSmtpServersAddrType InetAddressType,
    ccmSmtpServersAddr InetAddress,
    ccmSmtpServersPort Gauge,
    ccmSmtpServersStatus RowStatus
    }

ccmSmtpServersAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS not-accessible
    STATUS mandatory
    DESCRIPTION
        "Address Type of the SMTP server."
    ::= { ccmSmtpServersEntry 1 }

ccmSmtpServersAddr OBJECT-TYPE
    SYNTAX InetAddress
--    Rsyntax OCTET STRING(SIZE(0..255))
    ACCESS not-accessible
    STATUS mandatory
    DESCRIPTION
        "Address of the SMTP server."
    REFERENCE
        "RFC 2821 - Simple Mail Transfer Protocol."
    ::= { ccmSmtpServersEntry 2 }

ccmSmtpServersPort OBJECT-TYPE
    SYNTAX Gauge(1..65535)
    ACCESS read-write
    STATUS mandatory
    DESCRIPTION
        "Port of the SMTP server."
    REFERENCE
        "RFC 2821 - Simple Mail Transfer Protocol."
    DEFVAL { 25 }
    ::= { ccmSmtpServersEntry 3 }

ccmSmtpServersStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status object used to manage the rows in this table."
    ::= { ccmSmtpServersEntry 4 }

callHomeLastAlertSent OBJECT-TYPE
    SYNTAX TimeStamp
--    Rsyntax TimeTicks
    ACCESS read-only
    STATUS mandatory
    DESCRIPTION
        "The value of sysUpTime when the last CallHome alert
        was sent."
    ::= { ccmCallHomeStats 1 }

callHomeAlerts OBJECT-TYPE
    SYNTAX Counter
    ACCESS read-only
    STATUS mandatory
    DESCRIPTION
        "The number of  CallHome alerts sent."
    ::= { ccmCallHomeStats 2 }

ccmSysLogSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Different devices implementing this mib may use
        different criteria for issuing call home alerts.
        
        For the devices that issue call home alerts based on
        severity level of the syslog messages generated on
        the device, this object determines syslog severity
        levels beyond which a call home alert message will be
        issued.
        
        Any syslog message with a severity value greater than
        the value set for this object will be ignored by the agent.
        Note: severity numeric values increase as their
        severity decreases, e.g. error(4) is more severe
        than debug(8).
        
        For the devices that do not issue call home alerts based
        on syslog severity levels this object has no effect."
    ::= { ccmCallHomeConfiguration 23 }

ccmEnableSmtpServerNotif OBJECT-TYPE
    SYNTAX TruthValue
--    Rsyntax INTEGER {
--        true(1),
--        false(2)
--        }
    ACCESS read-write
    STATUS mandatory
    DESCRIPTION
        "This variable indicates whether the system produces
        the ccmSmtpServerFailNotif.
        
        A false value for this object will prevent
        ccmSmtpServerFailNotif notification being generated
        by the device."
    ::= { ccmCallHomeConfiguration 24 }

callHomeAlertGroupTypeTable OBJECT-TYPE
    SYNTAX SEQUENCE OF CallHomeAlertGroupTypeEntry
    ACCESS not-accessible
    STATUS mandatory
    DESCRIPTION
        "This table contains information about all the 
        alert groups types supported in the system. 
        Whenever the system opts not to support a
        particular alert group type, the corresponding 
        entry in this table will be removed, and a
        'ccmAlertGroupTypeDeletedNotif' will be sent.
        Whenever the system opts to support a new
        alert group type,  a new entry into this table 
        will be added, and a 
        'ccmAlertGroupTypeAddedNotif' will be sent."
    ::= { ccmCallHomeConfiguration 25 }

callHomeAlertGroupTypeEntry OBJECT-TYPE
    SYNTAX CallHomeAlertGroupTypeEntry
    ACCESS not-accessible
    STATUS mandatory
    DESCRIPTION
        "An entry containing information about a
        particular callHome alert group type 
        in the system."
    INDEX { callHomeAlertGroupTypeIndex }
    ::= { callHomeAlertGroupTypeTable 1 }

CallHomeAlertGroupTypeEntry ::= SEQUENCE {
    callHomeAlertGroupTypeIndex Gauge,
    callHomeAlertGroupName SnmpAdminString
    }

callHomeAlertGroupTypeIndex OBJECT-TYPE
    SYNTAX Gauge(1..256)
    ACCESS not-accessible
    STATUS mandatory
    DESCRIPTION
        "This object represent the index corresponds 
        to the particular alert group type configured 
        in the system."
    ::= { callHomeAlertGroupTypeEntry 1 }

callHomeAlertGroupName OBJECT-TYPE
    SYNTAX SnmpAdminString(SIZE(0..255))
--    Rsyntax OCTET STRING(SIZE(0..255))
    ACCESS read-only
    STATUS mandatory
    DESCRIPTION
        "This object represents the name of 
        alert group configured in the system."
    ::= { callHomeAlertGroupTypeEntry 2 }

callHomeSwInventoryTable OBJECT-TYPE
    SYNTAX SEQUENCE OF CallHomeSwInventoryEntry
    ACCESS not-accessible
    STATUS mandatory
    DESCRIPTION
        "This table contains inventory information about all the
        software services currently enabled in the system.
        When a software service is disabled from the system, all
        the entries corresponds to that software service will be
        deleted automatically from the table."
    ::= { ccmCallHomeConfiguration 26 }

callHomeSwInventoryEntry OBJECT-TYPE
    SYNTAX CallHomeSwInventoryEntry
    ACCESS not-accessible
    STATUS mandatory
    DESCRIPTION
        "An entry containing information about the name value
        pair for a particular software service enabled in the
        system."
    INDEX { callHomeSwServiceName, callHomeInventoryNVPairIndex }
    ::= { callHomeSwInventoryTable 1 }

CallHomeSwInventoryEntry ::= SEQUENCE {
    callHomeSwServiceName SnmpAdminString,
    callHomeInventoryNVPairIndex Gauge,
    callHomeInventoryInfoName OCTET STRING,
    callHomeInventoryInfoValue OCTET STRING
    }

callHomeSwServiceName OBJECT-TYPE
    SYNTAX SnmpAdminString(SIZE(1..32))
--    Rsyntax OCTET STRING(SIZE(1..32))
    ACCESS not-accessible
    STATUS mandatory
    DESCRIPTION
        "This object represents the name of software service
        enabled in the system."
    ::= { callHomeSwInventoryEntry 1 }

callHomeInventoryNVPairIndex OBJECT-TYPE
    SYNTAX Gauge(1..256)
    ACCESS not-accessible
    STATUS mandatory
    DESCRIPTION
        "This object represents the index corresponds to the name
        value pair for a particular software service enabled in
        the system. 
        The name value pair is a 'tuple' of (inventory info-name, 
        and inventory info-value) and this object uniquely 
        identifies a value of the tuple, for a particular
        software service enabled in the system."
    ::= { callHomeSwInventoryEntry 2 }

callHomeInventoryInfoName OBJECT-TYPE
    SYNTAX OCTET STRING(SIZE(1..1024))
    ACCESS read-only
    STATUS mandatory
    DESCRIPTION
        "This object represents the name of a feature , for a
        particular software service enabled in the system.
        For example, the value of this object could be
        'number of VSAN' for the software service 'vsan_manager'."
    ::= { callHomeSwInventoryEntry 3 }

callHomeInventoryInfoValue OBJECT-TYPE
    SYNTAX OCTET STRING(SIZE(1..1024))
    ACCESS read-only
    STATUS mandatory
    DESCRIPTION
        "This object represents the value for the feature name
        specified in the corresponding instance of
        'callHomeInventroyInfoName' object.
        For example, the value of this object could be '10' for
        the corresponding instance of 'callHomeInventroyInfoName'
        object with value 'number of VSAN'."
    ::= { callHomeSwInventoryEntry 4 }

ccmPeriodicSwInventoryMsgEnable OBJECT-TYPE
    SYNTAX TruthValue
--    Rsyntax INTEGER {
--        true(1),
--        false(2)
--        }
    ACCESS read-write
    STATUS mandatory
    DESCRIPTION
        "This object enables/disables the sending of periodic
        software inventory callhome message on the system."
    DEFVAL { true }
    ::= { ccmCallHomeConfiguration 27 }

ccmPeriodicSwInventoryTimeFrame OBJECT-TYPE
    SYNTAX Gauge(1..30)
--  Units
--    days
    ACCESS read-write
    STATUS mandatory
    DESCRIPTION
        "This object represents the time frame for sending the
         periodic software inventory callhome message, if the
         periodic software inventory is enabled on the system
         ie., the value of 'ccmPeriodicSwInventoryMsgEnable'
         object  is set to 'true'."
    DEFVAL { 7 }
    ::= { ccmCallHomeConfiguration 28 }

ccmMsgThrottlingEnable OBJECT-TYPE
    SYNTAX TruthValue
--    Rsyntax INTEGER {
--        true(1),
--        false(2)
--        }
    ACCESS read-write
    STATUS mandatory
    DESCRIPTION
        "This object enables/disables the message throttling 
        mechanism implemented on the system.
        
        The message throttling mechanism limits the number
        of callhome messages for a alert type, sent with in  
        a time frame. The maximum number of callhome alert
        messages that can be sent out for a particular alert 
        type is '30' in a time frame of 2 hours.
        
        That means, if the number of message sent exceeds the 
        maximum limit (30), with in the given time frame 
        (2 hours) then any further messages for that alert type 
        will be discarded within that time frame. 
        
        Only 30 messages for each alert type will be sent until 
        2 hours from the time the first message was sent. In case 
        2 hours has already elapsed since the first such message 
        was sent, then time frame and the count for the number of 
        messages will be reset to '0'."
    DEFVAL { true }
    ::= { ccmCallHomeConfiguration 29 }

callHomeUserDefMaxCmds OBJECT-TYPE
    SYNTAX Gauge(0..65535)
    ACCESS read-only
    STATUS mandatory
    DESCRIPTION
        "The maximum number of CLI commands that the system supports
        in the callHomeUserDefCmdTable for a particular alert
        group type represented by the
        callHomeAlertGroupTypeIndex object.
        
        A value of zero for this object indicates that the number of CLI
        commands system supports for a particular alert gorup type
        is only limited by resources available on system."
    ::= { ccmCallHomeAlertGroupCfg 5 }

callHomeUserDefCmdTable OBJECT-TYPE
    SYNTAX SEQUENCE OF CallHomeUserDefCmdEntry
    ACCESS not-accessible
    STATUS mandatory
    DESCRIPTION
        "Callhome alert messages are sent with output of some
        pre-defined commands run in the system.
        
        This table provides an option for the user to specify
        a CLI(Command Line Interface) command or set of CLI
        commands to be executed when some important failures
        occur in the system, and whose output should be sent
        with the callhome alert messages. The user should
        associate these commands with an alert group type.
        
        Whenever an alert message is to be sent, the callhome
        server would find out if any commands are specified by
        the user for the alert group associated with the
        alert message, and attach the output of those
        commands in the callhome alert message.
        
        This table contains information about all the user
        specified CLI commands for the alert groups types
        supported in the system.
        
        GLOSSARY :
        CLI - Command Line Interface provided by the system."
    ::= { ccmCallHomeAlertGroupCfg 6 }

callHomeUserDefCmdEntry OBJECT-TYPE
    SYNTAX CallHomeUserDefCmdEntry
    ACCESS not-accessible
    STATUS mandatory
    DESCRIPTION
        "An entry containing information about a user specified
        CLI command for a callHome alert group type in
        the system.
        
        The index object 'callHomeAlertGroupTypeIndex' represents
        the alert group type to which the user specified CLI
        command should be associated.
        
        User can not configure any CLI commands for a
        callHomeAlertGroupTypeIndex, whose corresponding
        instance callHomeAlertGroupName object is configured
        with value 'Cisco-TAC'."
    INDEX { callHomeAlertGroupTypeIndex, callHomeUserDefCmdIndex }
    ::= { callHomeUserDefCmdTable 1 }

CallHomeUserDefCmdEntry ::= SEQUENCE {
    callHomeUserDefCmdIndex Gauge,
    callHomeUserDefCmdName SnmpAdminString,
    callHomeUserDefCmdRowStatus RowStatus
    }

callHomeUserDefCmdIndex OBJECT-TYPE
    SYNTAX Gauge
    ACCESS not-accessible
    STATUS mandatory
    DESCRIPTION
        "An arbitrary integer identifying the user specified
        CLI command for a particular callHomeAlertGroupTypeIndex."
    ::= { callHomeUserDefCmdEntry 1 }

callHomeUserDefCmdName OBJECT-TYPE
    SYNTAX SnmpAdminString(SIZE(1..255))
--    Rsyntax OCTET STRING(SIZE(1..255))
    ACCESS read-write
    STATUS mandatory
    DESCRIPTION
        "This object represents a CLI command to be executed
        and whose output should be sent with the callhome
        alert message.
        The implementation of this object does not do any
        syntax or semantic validation of the CLI command
        specified as a value of the object.
        
        The value of this object can not be modified
        when the value of the corresponding instance of
        'callHomeUserDefCmdRowStatus' is 'active'.
        To modify the value this object the corresponding
        entry must be deleted and re-created with new
        value for this object."
    ::= { callHomeUserDefCmdEntry 2 }

callHomeUserDefCmdRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "Status of this row."
    ::= { callHomeUserDefCmdEntry 3 }

ccmSmtpServerFailNotif TRAP-TYPE
-- Reverse mappable trap
    ENTERPRISE ciscoCallHomeMIB
    VARIABLES {
        ccmSmtpServersPort }
--  Status
--    mandatory
    DESCRIPTION
        "A ccmSmtpServerFailNotif is sent if the device fails on
        sending an e-mail notification to SMTP server in
        ccmSmtpServersTable."
    ::= 1

ccmAlertGroupTypeAddedNotif TRAP-TYPE
-- Reverse mappable trap
    ENTERPRISE ciscoCallHomeMIB
    VARIABLES {
        callHomeAlertGroupName }
--  Status
--    mandatory
    DESCRIPTION
        "A ccmAlertGroupTypeAddedNotif is sent, when 
        a new entry corresponds to the 
        'callHomealertGroupName' object in this 
        notification is added into the 
        callHomeAlertGroupTypeTable."
    ::= 2

ccmAlertGroupTypeDeletedNotif TRAP-TYPE
-- Reverse mappable trap
    ENTERPRISE ciscoCallHomeMIB
    VARIABLES {
        callHomeAlertGroupName }
--  Status
--    mandatory
    DESCRIPTION
        "A ccmAlertGroupTypeAddedNotif is sent, when an
        entry corresponds to 'callHomeAlertGroupName'
        object in this notification is deleted 
        from the callHomeAlertGroupTypeTable."
    ::= 3

chSystemInformationGroup OBJECT IDENTIFIER ::= { chMIBGroups 1 }
-- OBJECT-GROUP
--  Status
--    mandatory
--  Descr
--    A collection of objects for displaying and
--    configuring system information pertaining to
--    CallHome.
--  objects
--    sysContactPhoneNumber, sysContactEmailAddress, 
--    sysStreetAddress, callHomeCustomerId, callHomeContractId, 
--    callHomeSiteId, callHomeDeviceServicePriority

chConfigurationGroup OBJECT IDENTIFIER ::= { chMIBGroups 2 }
-- OBJECT-GROUP
--  Status
--    deprecated
--  Descr
--    A collection of objects for displaying and
--    configuring CallHome parameters.
--  objects
--    callHomeEnable, callHomeAlertAction, 
--    callHomeAlertActionStatus, callHomeAlertActionFailureCause, 
--    callHomeDestProfileMsgFormat, callHomeDestProfileMaxMsgSize, 
--    callHomeDestProfileTrnsprtMthd, callHomeDestProfileStatus, 
--    callHomeEmailAddrTblMaxEntries, callHomeDestEmailAddress, 
--    callHomeDestEmailAddressStatus, callHomeEmailFrom, 
--    callHomeEmailReplyTo

chEmailMsgDispGroup OBJECT IDENTIFIER ::= { chMIBGroups 3 }
-- OBJECT-GROUP
--  Status
--    mandatory
--  Descr
--    A collection of object(s) for displaying and
--    configuring e-mail address to which the
--    e-mail disposition notification should be sent.
--  objects
--    callHomeEmailMsgDispNotification

chSingleSmtpServerGroup OBJECT IDENTIFIER ::= { chMIBGroups 4 }
-- OBJECT-GROUP
--  Status
--    mandatory
--  Descr
--    A collection of objects for displaying and
--    configuring CallHome SMTP server on the devices which
--    support only one SMTP server.
--  objects
--    callHomeSmtpServerAddrType, callHomeSmtpServerAddr, 
--    callHomeSmtpServerPort

chMultipleSmtpServersGroup OBJECT IDENTIFIER ::= { chMIBGroups 5 }
-- OBJECT-GROUP
--  Status
--    mandatory
--  Descr
--    A collection of objects for displaying and
--    configuring CallHome SMTP server on the devices which
--    support on one SMTP server.
--  objects
--    ccmSmtpServersTblMaxEntries, ccmSmtpServersPort, 
--    ccmSmtpServersStatus

chStatisticsGroup OBJECT IDENTIFIER ::= { chMIBGroups 6 }
-- OBJECT-GROUP
--  Status
--    mandatory
--  Descr
--    A collection of objects for displaying 
--    CallHome statistics.
--  objects
--    callHomeLastAlertSent, callHomeAlerts

ccmSysLogSeverityGroup OBJECT IDENTIFIER ::= { chMIBGroups 7 }
-- OBJECT-GROUP
--  Status
--    mandatory
--  Descr
--    A collection of object(s) for displaying and
--    configuring CallHome syslog severity based on which
--    call home alerts may be issued.
--  objects
--    ccmSysLogSeverity

ccmMIBNotificationsConfigGroup OBJECT IDENTIFIER ::= { chMIBGroups 8 }
-- OBJECT-GROUP
--  Status
--    mandatory
--  Descr
--    A collection of objects for displaying and
--    configuring CallHome notifications.
--  objects
--    ccmEnableSmtpServerNotif

chConfigurationGroup1 OBJECT IDENTIFIER ::= { chMIBGroups 10 }
-- OBJECT-GROUP
--  Status
--    deprecated
--  Descr
--    A collection of objects for displaying and
--    configuring CallHome parameters.
--  objects
--    callHomeEnable, callHomeAlertAction, 
--    callHomeAlertActionStatus, callHomeAlertActionFailureCause, 
--    callHomeDestProfileMsgFormat, callHomeDestProfileMaxMsgSize, 
--    callHomeDestProfileTrnsprtMthd, callHomeDestProfileStatus, 
--    callHomeDestProfileMsgLevel, callHomeDestProfileAlertGroups, 
--    callHomeEmailAddrTblMaxEntries, callHomeDestEmailAddress, 
--    callHomeDestEmailAddressStatus, callHomeEmailFrom, 
--    callHomeEmailReplyTo, callHomeAlertGroupName

chConfigurationGroup2 OBJECT IDENTIFIER ::= { chMIBGroups 12 }
-- OBJECT-GROUP
--  Status
--    mandatory
--  Descr
--    A collection of objects for displaying and
--    configuring CallHome parameters.
--  objects
--    callHomeEnable, callHomeAlertAction, 
--    callHomeAlertActionStatus, callHomeAlertActionFailureCause, 
--    callHomeDestProfileMsgFormat, callHomeDestProfileMaxMsgSize, 
--    callHomeDestProfileTrnsprtMthd, callHomeDestProfileStatus, 
--    callHomeDestProfileMsgLevel, callHomeDestProfileAlertGroups, 
--    callHomeEmailAddrTblMaxEntries, callHomeDestEmailAddress, 
--    callHomeDestEmailAddressStatus, callHomeEmailFrom, 
--    callHomeEmailReplyTo, callHomeAlertGroupName, 
--    ccmMsgThrottlingEnable

chSwInventoryInfoGroup OBJECT IDENTIFIER ::= { chMIBGroups 13 }
-- OBJECT-GROUP
--  Status
--    deprecated
--  Descr
--    A collection of objects for displaying and
--    configuring software inventory information.
--  objects
--    callHomeInventoryInfoName, callHomeInventoryInfoValue, 
--    ccmPeriodicSwInventoryMsgEnable, 
--    ccmPeriodicSwInventoryTimeFrame

chPeriodicSwInventoryInfoGroup OBJECT IDENTIFIER ::= { chMIBGroups 14 }
-- OBJECT-GROUP
--  Status
--    mandatory
--  Descr
--    A collection of objects for configuring 
--    periodic software inventory information.
--  objects
--    ccmPeriodicSwInventoryMsgEnable, 
--    ccmPeriodicSwInventoryTimeFrame

chSwInventoryInfoGroup1 OBJECT IDENTIFIER ::= { chMIBGroups 15 }
-- OBJECT-GROUP
--  Status
--    mandatory
--  Descr
--    A collection of objects for displaying 
--    software inventory information.
--  objects
--    callHomeInventoryInfoName, callHomeInventoryInfoValue

ccmUserDefCmdGroup OBJECT IDENTIFIER ::= { chMIBGroups 16 }
-- OBJECT-GROUP
--  Status
--    mandatory
--  Descr
--    A collection of objects for configuring user defined
--    commands for the callhome alert group types.
--  objects
--    callHomeUserDefMaxCmds, callHomeUserDefCmdName, 
--    callHomeUserDefCmdRowStatus

ccmMIBNotificationsGroup OBJECT IDENTIFIER ::= { chMIBGroups 9 }
-- NOTIFICATION-GROUP
--  Status
--    deprecated
--  Descr
--    A collection of notifications.
--  notifications
--    ccmSmtpServerFailNotif

ccmMIBNotificationsGroup1 OBJECT IDENTIFIER ::= { chMIBGroups 11 }
-- NOTIFICATION-GROUP
--  Status
--    mandatory
--  Descr
--    A collection of notifications.
--  notifications
--    ccmSmtpServerFailNotif, ccmAlertGroupTypeAddedNotif, 
--    ccmAlertGroupTypeDeletedNotif

chMIBCompliance OBJECT IDENTIFIER ::= { chMIBCompliances 1 }
-- MODULE-COMPLIANCE
--  Status
--    deprecated
--  Descr
--    The compliance statement for entities which 
--    implement the CallHome feature.
--    
--    OBJECT ccmSmtpServersAddrType 
--    SYNTAX  INTEGER { ipv4(1) }
--    DESCRIPTION
--            An implementation is only required to 
--            support IPv4 addresses.
--    
--    OBJECT callHomeDestProfileName
--    SYNTAX  SnmpAdminString (SIZE (1..11))
--    DESCRIPTION
--            An implementation is only required to
--            support a profile name of size 1 to 11
--            octets.
--  Module
--    >>current<<
--   MandGroup
--    chConfigurationGroup
--   MandGroup
--    chStatisticsGroup
--   OptGroup
--    chSystemInformationGroup
--   OptGroup
--    chEmailMsgDispGroup
--   OptGroup
--    chSingleSmtpServerGroup
--   OptGroup
--    chMultipleSmtpServersGroup
--   OptGroup
--    ccmSysLogSeverityGroup
--   OptGroup
--    ccmMIBNotificationsConfigGroup
--   OptGroup
--    ccmMIBNotificationsGroup
--   ObjVar
--    callHomeDestProfileTrnsprtMthd
--   ObjVar
--    callHomeDestProfileMsgFormat
--   ObjVar
--    callHomeDestProfileStatus
--   ObjVar
--    callHomeDestEmailAddress
--   ObjVar
--    callHomeDestEmailAddressStatus
--   ObjVar
--    ccmSmtpServersPort
--   ObjVar
--    ccmSmtpServersStatus
--   ObjVar
--    callHomeEmailFrom
--   ObjVar
--    callHomeEmailReplyTo
--   ObjVar
--    callHomeEmailMsgDispNotification

chMIBCompliance1 OBJECT IDENTIFIER ::= { chMIBCompliances 2 }
-- MODULE-COMPLIANCE
--  Status
--    deprecated
--  Descr
--    The compliance statement for entities which 
--    implement the CallHome feature.
--    
--    OBJECT ccmSmtpServersAddrType 
--    SYNTAX  INTEGER { ipv4(1) }
--    DESCRIPTION
--            An implementation is only required to 
--            support IPv4 addresses.
--    
--    OBJECT callHomeDestProfileName
--    SYNTAX  SnmpAdminString (SIZE (1..31))
--    DESCRIPTION
--            An implementation is only required to
--            support a profile name of size 1 to 31
--            octets.
--  Module
--    >>current<<
--   MandGroup
--    chConfigurationGroup1
--   MandGroup
--    chStatisticsGroup
--   OptGroup
--    chSystemInformationGroup
--   OptGroup
--    chEmailMsgDispGroup
--   OptGroup
--    chSingleSmtpServerGroup
--   OptGroup
--    chMultipleSmtpServersGroup
--   OptGroup
--    ccmSysLogSeverityGroup
--   OptGroup
--    ccmMIBNotificationsConfigGroup
--   OptGroup
--    ccmMIBNotificationsGroup1
--   ObjVar
--    callHomeDestProfileTrnsprtMthd
--   ObjVar
--    callHomeDestProfileMsgFormat
--   ObjVar
--    callHomeDestProfileStatus
--   ObjVar
--    callHomeDestEmailAddress
--   ObjVar
--    callHomeDestEmailAddressStatus
--   ObjVar
--    ccmSmtpServersPort
--   ObjVar
--    ccmSmtpServersStatus
--   ObjVar
--    callHomeEmailFrom
--   ObjVar
--    callHomeEmailReplyTo
--   ObjVar
--    callHomeEmailMsgDispNotification

chMIBCompliance2 OBJECT IDENTIFIER ::= { chMIBCompliances 3 }
-- MODULE-COMPLIANCE
--  Status
--    deprecated
--  Descr
--    The compliance statement for entities which 
--    implement the CallHome feature.
--    
--    OBJECT ccmSmtpServersAddrType 
--    SYNTAX  INTEGER { ipv4(1) }
--    DESCRIPTION
--            An implementation is only required to 
--            support IPv4 addresses.
--    
--    OBJECT callHomeDestProfileName
--    SYNTAX  SnmpAdminString (SIZE (1..31))
--    DESCRIPTION
--            An implementation is only required to
--            support a profile name of size 1 to 31
--            octets.
--  Module
--    >>current<<
--   MandGroup
--    chConfigurationGroup2
--   MandGroup
--    chStatisticsGroup
--   MandGroup
--    chSwInventoryInfoGroup
--   OptGroup
--    chSystemInformationGroup
--   OptGroup
--    chEmailMsgDispGroup
--   OptGroup
--    chSingleSmtpServerGroup
--   OptGroup
--    chMultipleSmtpServersGroup
--   OptGroup
--    ccmSysLogSeverityGroup
--   OptGroup
--    ccmMIBNotificationsConfigGroup
--   OptGroup
--    ccmMIBNotificationsGroup1
--   ObjVar
--    callHomeDestProfileTrnsprtMthd
--   ObjVar
--    callHomeDestProfileMsgFormat
--   ObjVar
--    callHomeDestProfileStatus
--   ObjVar
--    callHomeDestEmailAddress
--   ObjVar
--    callHomeDestEmailAddressStatus
--   ObjVar
--    ccmSmtpServersPort
--   ObjVar
--    ccmSmtpServersStatus
--   ObjVar
--    callHomeEmailFrom
--   ObjVar
--    callHomeEmailReplyTo
--   ObjVar
--    callHomeEmailMsgDispNotification

chMIBCompliance3 OBJECT IDENTIFIER ::= { chMIBCompliances 4 }
-- MODULE-COMPLIANCE
--  Status
--    mandatory
--  Descr
--    The compliance statement for entities which 
--    implement the CallHome feature.
--    
--    OBJECT ccmSmtpServersAddrType 
--    SYNTAX  INTEGER { ipv4(1) }
--    DESCRIPTION
--            An implementation is only required to 
--            support IPv4 addresses.
--    
--    OBJECT callHomeDestProfileName
--    SYNTAX  SnmpAdminString (SIZE (1..31))
--    DESCRIPTION
--            An implementation is only required to
--            support a profile name of size 1 to 31
--            octets.
--  Module
--    >>current<<
--   MandGroup
--    chConfigurationGroup2
--   MandGroup
--    chStatisticsGroup
--   OptGroup
--    chSystemInformationGroup
--   OptGroup
--    chEmailMsgDispGroup
--   OptGroup
--    chSwInventoryInfoGroup1
--   OptGroup
--    chPeriodicSwInventoryInfoGroup
--   OptGroup
--    chSingleSmtpServerGroup
--   OptGroup
--    chMultipleSmtpServersGroup
--   OptGroup
--    ccmSysLogSeverityGroup
--   OptGroup
--    ccmMIBNotificationsConfigGroup
--   OptGroup
--    ccmMIBNotificationsGroup1
--   ObjVar
--    callHomeDestProfileTrnsprtMthd
--   ObjVar
--    callHomeDestProfileMsgFormat
--   ObjVar
--    callHomeDestProfileStatus
--   ObjVar
--    callHomeDestEmailAddress
--   ObjVar
--    callHomeDestEmailAddressStatus
--   ObjVar
--    ccmSmtpServersPort
--   ObjVar
--    ccmSmtpServersStatus
--   ObjVar
--    callHomeEmailFrom
--   ObjVar
--    callHomeEmailReplyTo
--   ObjVar
--    callHomeEmailMsgDispNotification


END
