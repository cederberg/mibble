-- MIB file created 20-Jan-2006 17:53:16, by
--   SMICng version 2.2.11-beta(PRO)(Solaris), January 20, 2001. Enterprise key cisco.com

CISCO-PPPOE-MIB DEFINITIONS ::= BEGIN

-- From file: "CISCO-PPPOE-MIB.my"
-- Compile options "4 7 F H N O W 03 06 0B 0G 0N 0T"

IMPORTS
    ciscoMgmt
            FROM CISCO-SMI
    TruthValue
            FROM SNMPv2-TC-v1
    ifIndex
            FROM IF-MIB
    atmVclVpi, atmVclVci
--?? may need import of ifIndex from RFC1213-MIB
            FROM ATM-MIB
    Counter, Gauge
            FROM RFC1155-SMI
    OBJECT-TYPE
            FROM RFC-1212
    TRAP-TYPE
            FROM RFC-1215;

ciscoPppoeMIB OBJECT IDENTIFIER ::= { ciscoMgmt 194 }
-- MODULE-IDENTITY
--  LastUpdated
--    200512210000Z
--  OrgName
--    Cisco Systems, Inc.
--  ContactInfo
--                Cisco Systems 
--                 Customer Service 
--    
--     Postal:     170 W Tasman Drive 
--                 San Jose, CA 95134 
--                 USA 
--    
--        Tel:     +1 800 553-NETS 
--    
--     E-mail:     cs-atm@cisco.com
--  Descr
--    Cisco PPPoE sessions management MIB Module.
--  RevDate
--    200512210000Z
--  RevDescr
--    Updated the imports such that Unsigned32 is imported from 
--    SNMPv2-SMI instead of CISCO-TC.
--  RevDate
--    200102200000Z
--  RevDescr
--    Initial version of this MIB module.

ciscoPppoeMIBObjects OBJECT IDENTIFIER ::= { ciscoPppoeMIB 1 }
cPppoeSystemSessionInfo OBJECT IDENTIFIER ::= { ciscoPppoeMIBObjects 1 }
cPppoeVcCfgInfo OBJECT IDENTIFIER ::= { ciscoPppoeMIBObjects 2 }
cPppoeVcSessionsInfo OBJECT IDENTIFIER ::= { ciscoPppoeMIBObjects 3 }
ciscoPppoeMIBNotificationPrefix OBJECT IDENTIFIER ::= { ciscoPppoeMIB 2 }
ciscoPppoeMIBNotification OBJECT IDENTIFIER ::= { ciscoPppoeMIBNotificationPrefix 0 }
ciscoPppoeMIBConformance OBJECT IDENTIFIER ::= { ciscoPppoeMIB 3 }
ciscoPppoeMIBCompliances OBJECT IDENTIFIER ::= { ciscoPppoeMIBConformance 1 }
ciscoPppoeMIBGroups OBJECT IDENTIFIER ::= { ciscoPppoeMIBConformance 2 }

cPppoeSystemCurrSessions OBJECT-TYPE
    SYNTAX Gauge
--  Units
--    sessions
    ACCESS read-only
    STATUS mandatory
    DESCRIPTION
        "The current number of active PPPoE sessions within 
         this system."
    ::= { cPppoeSystemSessionInfo 1 }

cPppoeSystemHighWaterSessions OBJECT-TYPE
    SYNTAX Gauge
--  Units
--    sessions
    ACCESS read-only
    STATUS mandatory
    DESCRIPTION
        "The high water mark of the established PPPoE 
         sessions since the system was initialized."
    ::= { cPppoeSystemSessionInfo 2 }

cPppoeSystemMaxAllowedSessions OBJECT-TYPE
    SYNTAX Gauge
--  Units
--    sessions
    ACCESS read-write
    STATUS mandatory
    DESCRIPTION
        "Maximum number of allowed PPPoE sessions within 
         the system."
    ::= { cPppoeSystemSessionInfo 3 }

cPppoeSystemThresholdSessions OBJECT-TYPE
    SYNTAX Gauge
--  Units
--    sessions
    ACCESS read-write
    STATUS mandatory
    DESCRIPTION
        "Threshold value of the established PPPoE sessions 
         within the system. Default value is equal to 
         cPppoeSystemMaxSessionsConfigurable"
    ::= { cPppoeSystemSessionInfo 4 }

cPppoeSystemExceededSessionErrors OBJECT-TYPE
    SYNTAX Counter
    ACCESS read-only
    STATUS mandatory
    DESCRIPTION
        "The accumulated number of errors for 
         establishing PPPoE session in the system due 
         to the cPppoeSystemCurrSessions value exceeds 
         the cPppoeSystemMaxAllowedSessions value."
    ::= { cPppoeSystemSessionInfo 5 }

cPppoeVcCfgTable OBJECT-TYPE
    SYNTAX SEQUENCE OF CPppoeVcCfgEntry
    ACCESS not-accessible
    STATUS mandatory
    DESCRIPTION
        "The table contains the PPPoE protocol related 
         configuration for the VCLs(ATM Interface 
         Virtual Channel Link)."
    ::= { cPppoeVcCfgInfo 1 }

cPppoeVcCfgEntry OBJECT-TYPE
    SYNTAX CPppoeVcCfgEntry
    ACCESS not-accessible
    STATUS mandatory
    DESCRIPTION
        "An entry containing additional PPPoE protocol 
         configuration related management information 
         applicable to a particular VCL."
    INDEX { ifIndex, atmVclVpi, atmVclVci }
-- Augments atmVclEntry FROM ATM-MIB
    ::= { cPppoeVcCfgTable 1 }

CPppoeVcCfgEntry ::= SEQUENCE {
    cPppoeVcEnable TruthValue
    }

cPppoeVcEnable OBJECT-TYPE
    SYNTAX TruthValue
--    Rsyntax INTEGER {
--        true(1),
--        false(2)
--        }
    ACCESS read-write
    STATUS mandatory
    DESCRIPTION
        "This object specifies whether the PPPoE protocol 
         should be enabled for this VCL. If the value of 
         this object is `false`, PPPoE protocol is 
         disabled; otherwise the PPPoE protocol is 
         enabled."
    DEFVAL { false }
    ::= { cPppoeVcCfgEntry 1 }

cPppoeVcSessionsTable OBJECT-TYPE
    SYNTAX SEQUENCE OF CPppoeVcSessionsEntry
    ACCESS not-accessible
    STATUS mandatory
    DESCRIPTION
        "Table of configuration and statistics about the 
         number of PPPoE sessions on a list of VCLs(ATM 
         Interface Virtual Channel Link)."
    ::= { cPppoeVcSessionsInfo 1 }

cPppoeVcSessionsEntry OBJECT-TYPE
    SYNTAX CPppoeVcSessionsEntry
    ACCESS not-accessible
    STATUS mandatory
    DESCRIPTION
        "An entry in the table containing PPPoE session 
         related information on a VCL. The entry of this 
         table is created when the value of cPppoeVcEnable 
         object is set to `true` for the entry associated 
         VCL. The entry of this table is deleted when the 
         of cPppoeVcEnable object set to `false` or the 
         the entry associated VCL is deleted from 
         atmVclTable."
    INDEX { ifIndex, atmVclVpi, atmVclVci }
    ::= { cPppoeVcSessionsTable 1 }

CPppoeVcSessionsEntry ::= SEQUENCE {
    cPppoeVcCurrSessions Gauge,
    cPppoeVcHighWaterSessions Gauge,
    cPppoeVcMaxAllowedSessions Gauge,
    cPppoeVcThresholdSessions Gauge,
    cPppoeVcExceededSessionErrors Counter
    }

cPppoeVcCurrSessions OBJECT-TYPE
    SYNTAX Gauge
--  Units
--    sessions
    ACCESS read-only
    STATUS mandatory
    DESCRIPTION
        "The current number of active PPPoE sessions on 
         the VCL."
    ::= { cPppoeVcSessionsEntry 1 }

cPppoeVcHighWaterSessions OBJECT-TYPE
    SYNTAX Gauge
--  Units
--    sessions
    ACCESS read-only
    STATUS mandatory
    DESCRIPTION
        "The high water mark of the established PPPoE 
         sessions on the VCL."
    ::= { cPppoeVcSessionsEntry 2 }

cPppoeVcMaxAllowedSessions OBJECT-TYPE
    SYNTAX Gauge
--  Units
--    sessions
    ACCESS read-write
    STATUS mandatory
    DESCRIPTION
        "The maximum number of allowed PPPoE sessions on 
         the VCL."
    ::= { cPppoeVcSessionsEntry 3 }

cPppoeVcThresholdSessions OBJECT-TYPE
    SYNTAX Gauge
--  Units
--    sessions
    ACCESS read-write
    STATUS mandatory
    DESCRIPTION
        "The Threshold value of the established PPPoE 
         sessions on the VCL. Default value is equal to 
         cPppoeVcMaxAllowedSessions."
    ::= { cPppoeVcSessionsEntry 4 }

cPppoeVcExceededSessionErrors OBJECT-TYPE
    SYNTAX Counter
--  Units
--    attempts
    ACCESS read-only
    STATUS mandatory
    DESCRIPTION
        "The accumulated number of errors for 
         establishing PPPoE session in the VC 
         due to the cPppoeVcCurrSessions value 
         exceeds the cPppoeVcMaxAllowedSessions 
         value."
    ::= { cPppoeVcSessionsEntry 5 }

cPppoeSystemSessionThresholdTrap TRAP-TYPE
-- Reverse mappable trap
    ENTERPRISE ciscoPppoeMIBNotificationPrefix
    VARIABLES {
        cPppoeSystemCurrSessions, cPppoeSystemMaxAllowedSessions, 
        cPppoeSystemThresholdSessions }
--  Status
--    mandatory
    DESCRIPTION
        "A notification indicating that number of active 
         sessions on the system exceeded system sessions 
         threshold value. System sessions threshold value 
         is indicated by cPppoeSystemThresholdSessions. 
        
         An  agent  must  not  generate  more  than  one 
         cPppoeSessionThresholdTrap `trap-event` in a 
         N second period,  where a  `trap-event` is  the 
         transmission of a single trap  PDU to a  list of 
         trap destinations. If additional `the number of 
         PPPoE  sessions  exceeds  threshold`  condition 
         occur within the N  second `throttling` period, 
         then these  trap-events should be suppressed by 
         the agent. An NMS should periodically check the 
         value of  cPppoeCurrSessions to  detect  any 
         missed cPppoeVcSessionThresholdTrap trap-events, 
         e.g. due to throttling or transmission loss. 
         Where N is the `throttling` period of trap-event. 
         Default value of the N is equal to 30 seconds"
    ::= 1

cPppoeVcSessionThresholdTrap TRAP-TYPE
-- Reverse mappable trap
    ENTERPRISE ciscoPppoeMIBNotificationPrefix
    VARIABLES {
        cPppoeVcCurrSessions, cPppoeVcMaxAllowedSessions, 
        cPppoeVcThresholdSessions }
--  Status
--    mandatory
    DESCRIPTION
        "A notification indicating that number of active 
         sessions on the  VC  exceeded vc sessions 
         threshold value. VC sessions threshold value is 
         indicated by cPppoeVcThresholdSessions. 
        
         An  agent  must  not  generate  more  than  one 
         cPppoeVcSessionThresholdTrap `trap-event` in a 
         N second period,  where a  `trap-event` is  the 
         transmission of a single trap  PDU to a  list of 
         trap destinations. If additional `the number of 
         PPPoE  sessions  exceeds  threshold`  condition 
         occur within the N  second `throttling` period, 
         then these  trap-events should be suppressed by 
         the agent. An NMS should periodically check the 
         value of  cPppoeVcCurrSessions to  detect  any 
         missed cPppoeVcSessionThresholdTrap trap-events, 
         e.g. due to throttling or transmission loss. 
         Where N is the `throttling` period of trap-event. 
         Default value of the N is equal to 30 seconds."
    ::= 2

cPppoeSystemGroup OBJECT IDENTIFIER ::= { ciscoPppoeMIBGroups 1 }
-- OBJECT-GROUP
--  Status
--    mandatory
--  Descr
--    A collection of objects providing information about the 
--     PPPoE sessions on a system.
--  objects
--    cPppoeSystemCurrSessions, cPppoeSystemHighWaterSessions, 
--    cPppoeSystemMaxAllowedSessions, cPppoeSystemThresholdSessions, 
--    cPppoeSystemExceededSessionErrors

cPppoeVcCfgGroup OBJECT IDENTIFIER ::= { ciscoPppoeMIBGroups 2 }
-- OBJECT-GROUP
--  Status
--    mandatory
--  Descr
--    A collection of objects specifying PPPoE protocol 
--     related configuration on the VCL.
--  objects
--    cPppoeVcEnable

cPppoeVcSessionsGroup OBJECT IDENTIFIER ::= { ciscoPppoeMIBGroups 3 }
-- OBJECT-GROUP
--  Status
--    mandatory
--  Descr
--    A collection of objects providing information about the 
--     number of sessions on the VCL.
--  objects
--    cPppoeVcCurrSessions, cPppoeVcHighWaterSessions, 
--    cPppoeVcMaxAllowedSessions, cPppoeVcThresholdSessions, 
--    cPppoeVcExceededSessionErrors

cPppoeNotificationsGroup OBJECT IDENTIFIER ::= { ciscoPppoeMIBGroups 4 }
-- NOTIFICATION-GROUP
--  Status
--    mandatory
--  Descr
--    The collection of notifications used to indicate 
--     high PPPoE session volume information(e.g, the 
--     number of current PPPoE sessions exceeds threshold 
--     setting for the system or a VCL).
--  notifications
--    cPppoeSystemSessionThresholdTrap, 
--    cPppoeVcSessionThresholdTrap

ciscoPppoeMIBBasicCompliance OBJECT IDENTIFIER ::= { ciscoPppoeMIBCompliances 1 }
-- MODULE-COMPLIANCE
--  Status
--    mandatory
--  Descr
--    The compliance statement for entities which implement 
--     the Cisco PPPoE MIB. 
--  Module
--    >>current<<
--   MandGroup
--    cPppoeSystemGroup
--   MandGroup
--    cPppoeVcCfgGroup
--   MandGroup
--    cPppoeVcSessionsGroup
--   MandGroup
--    cPppoeNotificationsGroup


END
