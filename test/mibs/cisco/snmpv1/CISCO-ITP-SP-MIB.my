-- MIB file created 12-Apr-2002 12:08:46, by
--   SMICng version 2.2.11-beta(PRO)(Solaris), January 20, 2001. Enterprise key cisco.com

CISCO-ITP-SP-MIB DEFINITIONS ::= BEGIN

-- From file: "CISCO-ITP-SP-MIB.my"
-- Compile options "4 7 F H N W 03 06 0B 0G 0N 0T"

IMPORTS
    SnmpAdminString
            FROM SNMP-FRAMEWORK-MIB
    InetAddressType, InetAddress
            FROM INET-ADDRESS-MIB
    InterfaceIndexOrZero
            FROM IF-MIB
    RowStatus, TimeStamp, TruthValue
            FROM SNMPv2-TC-v1
    CItpTcAclId, CItpTcCLLI, CItpTcDisplayPC, CItpTcLinksetId, 
    CItpTcLinkSLC, CItpTcLinkType, CItpTcNetworkIndicator, 
    CItpTcPointCode, CItpTcPointCodeType, CItpTcQos, 
    CItpTcRouteTableName, CItpTcSs7Variant, CItpTcTimerMtp2T01, 
    CItpTcTimerMtp2T02, CItpTcTimerMtp2T03, CItpTcTimerMtp2T04E, 
    CItpTcTimerMtp2T04N, CItpTcTimerMtp2T05, CItpTcTimerMtp2T06, 
    CItpTcTimerMtp2T07, CItpTcTimerMtp3T01, CItpTcTimerMtp3T02, 
    CItpTcTimerMtp3T03, CItpTcTimerMtp3T04, CItpTcTimerMtp3T05, 
    CItpTcTimerMtp3T06, CItpTcTimerMtp3T07, CItpTcTimerMtp3T08, 
    CItpTcTimerMtp3T10, CItpTcTimerMtp3T11, CItpTcTimerMtp3T12, 
    CItpTcTimerMtp3T13, CItpTcTimerMtp3T14, CItpTcTimerMtp3T15, 
    CItpTcTimerMtp3T16, CItpTcTimerMtp3T17, CItpTcTimerMtp3T18, 
    CItpTcTimerMtp3T19, CItpTcTimerMtp3T20, CItpTcTimerMtp3T21, 
    CItpTcTimerMtp3T22, CItpTcTimerMtp3T23, CItpTcTimerMtp3T24, 
    CItpTcTimerMtp3T25, CItpTcTimerMtp3T26, CItpTcTimerMtp3T27, 
    CItpTcTimerMtp3T28, CItpTcTimerMtp3T29, CItpTcTimerMtp3T30, 
    CItpTcTimerMtp3T31, CItpTcTimerMtp3T32, CItpTcTimerMtp3T33, 
    CItpTcTimerMtp3T34, CItpTcTimerLinkTest, CItpTcTimerLinkMessage, 
    CItpTcTimerLinkActRetry
            FROM CISCO-ITP-TC-MIB
    ciscoMgmt
            FROM CISCO-SMI
    Counter, Gauge, TimeTicks
            FROM RFC1155-SMI
    OBJECT-TYPE
            FROM RFC-1212
    TRAP-TYPE
            FROM RFC-1215;

ciscoItpSpMIB OBJECT IDENTIFIER ::= { ciscoMgmt 232 }
-- MODULE-IDENTITY
--  LastUpdated
--    200203070000Z
--  OrgName
--    Cisco Systems, Inc.
--  ContactInfo
--           Cisco Systems, Inc
--            Customer Service
--    
--    Postal: 170 W. Tasman Drive
--            San Jose, CA  95134
--            USA
--    
--       Tel: +1 800 553-NETS
--    
--    E-mail: cs-ss7@cisco.com
--  Descr
--    The MIB for managing Signalling Points and its 
--     associated messages transported over Signalling 
--     System  No. 7 (SS7) Network via Cisco IP Transfer
--     Point.  
--     
--     The Cisco IP Transfer Point (ITP) is a hardware 
--     and software solution that transports SS7 traffic 
--     using IP. Each ITP node provides function similar
--     to SS7 Signalling point.   
--     
--     The relevant ITU documents describing this technology
--     is the ITU Q series, including ITU Q.700: Introduction
--     to CCITT Signalling System No. 7 and ITU Q.701 
--     Functional description of the message transfer part
--     (MTP) of Signalling System No. 7. 
--     
--     This MIB models the SP as follows:
--     
--     The SP is associated with one or more point codes.
--     Each pointcode is associated with:
--       an SS7 variant, timers, and linksets.
--     
--     Linksets contain:
--       destination point code 
--       linkset byte/packet statistics,
--       accounting information per Destination Point 
--       Code(DPC) and Originating Point Code (OPC) 
--       violation accounting information per DPC and OPC
--       links,  reference to incoming and outgoing ACL
--       reference to a routing table for each SS7 packet type
--     
--     Links contain:
--       timers, and byte/packet statistics.
--     
--     The figure below provides a diagrammatic representation
--     of the relationships. Each box may be replicated
--     providing multiple instances of the object. 
--     
--     '===>' indicates that the object to the left contains
--     a reference to the object to the right.
--     
--     '###>' indicates that the object to the left contains
--     an instance of the object to the right.
--     
--     The down arrow indicates that the object being pointed
--     to contains snmp indices of the objects above it.
--     
--     
--       ________________
--      |                |
--      |      Sp        |###> point code, timers
--      |________________|
--              |
--              V
--       ________________
--      |                |
--      |                |===> Accounting
--      |    Linkset     |===> Violation Accounting
--      |                |===> Incoming ACL
--      |                |===> Outgoing ACL
--      |________________|===> Routing Tables.
--              |
--              V
--       ________________
--      |     Link       |###> timers
--      |________________|===> statistics
--    
--    
--    Abbreviations:
--    AERM  - Alignment Error Rate Monitor
--    CLLI  - Common Language Location Codes 
--    HSL   - High Speed Link (ATM based)
--    LLSC  - link set control 
--    LSAC  - Signalling link activity control
--    LSDA  - Signalling data link allocation 
--    LSLA  - Signalling link activation 
--    LSLD  - Signalling link deactivation 
--    LSLR  - Signalling link restoration 
--    LSSU  - Link Status Signal Unit
--    LSTA  - Signalling terminal allocation 
--    MTP   - Message Transport Protocol
--    MTP2  - Layer 2 of Message Transport Protocol
--    MTP3  - Layer 3 of Message Transport Protocol
--    PC    - Point Code
--    RTN   - RouteTableName
--    SCTP  - Stream Transmission Protocol(RFC 2960)
--    SIB   - Status Indicator Busy
--    SP    - Signalling Point
--    SS7   -  System  No. 7 (SS7) Network
--    SUERM - Signal Unit Error Rate Monitor 
--    TCBC  - Changeback control
--    TCOC  - Changeover control
--    TCRC  - Controlled rerouting control
--    TFRC  - Forced rerouting control
--    TLAC  - Link availability control
--    TPRC  - Signalling point restart control
--    TRCC  - Signalling route set congestion control
--    TSFC  - Signalling traffic flow control
--    TSRC  - Signalling routing control 
--  RevDate
--    200203070000Z
--  RevDescr
--    Added support for notification on link utilization.
--     Textual conventions:
--        CItpSpSampleInterval
--        CItpSpPercentThreshold 
--        CItpSpLinkUtilization
--        CItpSpLinkCapacity
--        CItpSpLinkUtilizationState
--     
--     Scalars:
--        cItpSpUtilSampleInterval    
--        cItpSpUtilThreshold 
--        cItpSpUtilAbateDelta 
--        
--     Linkset table:
--        cItpSpLinksetPlanCapacity - deprecated.  
--        
--     Link table:
--        cItpSpLinkPlanCapacityRcvd
--        cItpSpLinkUtilThresholdRcvd
--        cItpSpLinkUtilizationRcvd
--        cItpSpLinkUtilStateRcvd
--        cItpSpLinkL2BytesRcvd  
--        cItpSpLinkPlanCapacitySent
--        cItpSpLinkUtilThresholdSent
--        cItpSpLinkUtilizationSent
--        cItpSpLinkUtilStateSent
--        cItpSpLinkL2BytesSent
--        
--        
--     Notification enable:   
--        cItpSpLinkUtilNotifEnabled
--        
--     Notification:   
--        cItpSpLinkRcvdUtilChange
--        cItpSpLinkSentUtilChange
--  RevDate
--    200201230000Z
--  RevDescr
--    Modified the following objects:
--       cItpSpLinkType:  Added new high speed link type
--          to textual convention CItpTcLinkType. 
--          
--       cItpSpVariant:  Added new China SS7 variant       
--          to textual convention CItpTcSs7Variant. 
--       Add new enumerate 
--       
--     Added the following objects:
--       cItpSpDistSccpUnseq
--       cItpSpSummaryRoutingException
--       cItpSpLinksetVariant 
--       cItpSpLinkDroppedPkts   
--       cItpSpLinkTransmittedLssu 
--       cItpSpLinkReceivedLssu 
--       cItpSpLinkProtocolDetails
--       cItpSpLinkLsacState
--       cItpSpLinkTsrcState
--       cItpSpLinkTcocState
--       cItpSpLinkTcocLocalBSNT    
--       cItpSpLinkTcocRemoteBSNT    
--       cItpSpLinkTcbcState
--       cItpSpLinkReceivedSIB           
--       cItpSpLinkTransmittedSIB         
--       cItpSpLinkMtp2ExpiredT01  
--       cItpSpLinkMtp2ExpiredT02  
--       cItpSpLinkMtp2ExpiredT03  
--       cItpSpLinkMtp2ExpiredT04 
--       cItpSpLinkMtp2ExpiredT05  
--       cItpSpLinkMtp2ExpiredT06  
--       cItpSpLinkMtp2ExpiredT07  
--       cItpSpLinkOMAERMCount     
--       cItpSpLinkOMAERMFailCount 
--       cItpSpLinkOMSURMCount     
--       cItpSpLinkOMSURMFailCount
--  RevDate
--    200108290000Z
--  RevDescr
--    Initial version of this MIB module.

cItpSpMIBNotifs OBJECT IDENTIFIER ::= { ciscoItpSpMIB 0 }
cItpSpMIBObjects OBJECT IDENTIFIER ::= { ciscoItpSpMIB 1 }
cItpSpMIBConformance OBJECT IDENTIFIER ::= { ciscoItpSpMIB 2 }
cItpSpScalars   OBJECT IDENTIFIER ::= { cItpSpMIBObjects 1 }
cItpSpPointCode OBJECT IDENTIFIER ::= { cItpSpMIBObjects 2 }
cItpSpLinkset   OBJECT IDENTIFIER ::= { cItpSpMIBObjects 3 }
cItpSpLink      OBJECT IDENTIFIER ::= { cItpSpMIBObjects 4 }
cItpSpNotificationsEnable OBJECT IDENTIFIER ::= { cItpSpMIBObjects 5 }
cItpSpNotifications OBJECT IDENTIFIER ::= { cItpSpMIBNotifs 0 }
cItpSpMIBCompliances OBJECT IDENTIFIER ::= { cItpSpMIBConformance 1 }
cItpSpMIBGroups OBJECT IDENTIFIER ::= { cItpSpMIBConformance 2 }

CItpSpSequenceNumber ::= Gauge(0..65535)
-- TEXTUAL-CONVENTION
--  Status
--    mandatory
--  Descr
--    This textual convention defines all of the allowed
--     values for a sequence of integers used by the 
--     SS7 protocol to transmit and acknowledge packets.
--     The range is specified from 0 to maximum allowed 
--     value for extended sequence numbers.  The actual 
--     range will depend on the type of link and   
--     the variant.  The value will increase and then wrap
--     to the zero value. The following are examples of 
--     valid sequences.
--     0..126,127,0..
--     0..254,255,0..
--     0..32766,32767,0..
--     0..65534,65535,0..

CItpSpSampleInterval ::= Gauge(60..3600)
-- TEXTUAL-CONVENTION
--  Status
--    mandatory
--  Descr
--    This textual convention defines the allowed values
--     for a sample interval.  This value is specified in
--     seconds and ranges from 1 minute to 1 hour.

CItpSpPercentThreshold ::= Gauge(0..100)
-- TEXTUAL-CONVENTION
--  Status
--    mandatory
--  Descr
--    This textual convention defines the allowed values
--     for a thresholds specified as percentage of 
--     link utilization.  A value of zero indicates that
--     this specific threshold is to be ignored.

CItpSpLinkUtilization ::= Gauge(0..999)
-- TEXTUAL-CONVENTION
--  Status
--    mandatory
--  Descr
--    This textual convention defines a range of 
--     percentages that represent the utilization of 
--     a link. Any value over 999 will be represented
--     as 999.
--     
--     For SS7 links based on IP/SCTP the link capacity 
--     is not directly related to the interface speed used
--     to transmit packets.  This is different from serial
--     and HSL links.  The capacity of these types of 
--     links depend on the amount of resources available
--     in the IP cloud.  The IP cloud must be provisioned
--     to support traffic for all SS7 links. In order to 
--     monitor link utilization on IP/SCTP based SS7 links
--     a planned capacity must be specified.  If this value
--     is incorrectly estimated or traffic exceeds this 
--     expected value link utilization may exceed 100
--     percent.  This is possible because the IP cloud
--     may be provisioned with additional capacity or 
--     may discard less important traffic based on Qos
--     parameters.
--     
--     When a SS7 link has not be configured for link 
--     utilization monitoring this value object will
--     have a value of zero.

CItpSpLinkCapacity ::= Gauge(0|56000..2147483647)
-- TEXTUAL-CONVENTION
--  Status
--    mandatory
--  Descr
--    This textual convention defines the planned 
--     capacity of a SS7 link in bit per second. 
--     
--     If the link type is serial or HSL the link capacity
--     can be obtained from information in the IF-MIB. 
--     
--     If the link type is sctp/ip a value of zero 
--     indicates that link utilization should not 
--     be calculated for this SS7 link.

CItpSpLinkUtilizationState ::= INTEGER {
        --?? enum value of zero may cause problems
        unMonitored(0),
        underThreshold(1),
        overThreshold(2)
        }
-- TEXTUAL-CONVENTION
--  Status
--    mandatory
--  Descr
--    Link Utilization State as follows:
--       'unMonitored(0)'    - traffic for a specified direction 
--                             is not being monitored.
--       'underThreshold(1)' - traffic for a specified direction
--           on a link is below the specified threshold.
--                 
--       'overThreshold(2)'  - traffic for a specified direction 
--           on a link is above to or exceeds the specified 
--           threshold.

cItpSpVariant OBJECT-TYPE
    SYNTAX CItpTcSs7Variant
--    Rsyntax INTEGER {
--        ansi(1),
--        itu(2),
--        china(3)
--        }
    ACCESS read-write
    STATUS mandatory
    DESCRIPTION
        "The SS7 variant implemented in this SP."
    ::= { cItpSpScalars 1 }

cItpSpCLLICode OBJECT-TYPE
    SYNTAX CItpTcCLLI
--    Rsyntax OCTET STRING(SIZE(0..11))
    ACCESS read-write
    STATUS mandatory
    DESCRIPTION
        "Common Language Location Codes (CLLI Codes)."
    ::= { cItpSpScalars 2 }

cItpSpDisplayName OBJECT-TYPE
    SYNTAX SnmpAdminString(SIZE(0..30))
--    Rsyntax OCTET STRING(SIZE(0..30))
    ACCESS read-write
    STATUS mandatory
    DESCRIPTION
        "A short identifier for the Signalling point.
         This value can be set by system administrator
         or defaults to the local point code formatted
         as an ASCII string."
    ::= { cItpSpScalars 3 }

cItpSpDescription OBJECT-TYPE
    SYNTAX SnmpAdminString(SIZE(0..254))
--    Rsyntax OCTET STRING(SIZE(0..254))
    ACCESS read-write
    STATUS mandatory
    DESCRIPTION
        "A textual description for the Signalling point."
    ::= { cItpSpScalars 4 }

cItpSpMtp2T01 OBJECT-TYPE
    SYNTAX CItpTcTimerMtp2T01
--    Rsyntax Gauge(5000..150000)
--  Units
--    milliseconds
    ACCESS read-write
    STATUS mandatory
    DESCRIPTION
        "Alignment ready timer."
    ::= { cItpSpScalars 5 }

cItpSpMtp2T02 OBJECT-TYPE
    SYNTAX CItpTcTimerMtp2T02
--    Rsyntax Gauge(0|5000..150000)
--  Units
--    milliseconds
    ACCESS read-write
    STATUS mandatory
    DESCRIPTION
        "Not aligned timer."
    ::= { cItpSpScalars 6 }

cItpSpMtp2T03 OBJECT-TYPE
    SYNTAX CItpTcTimerMtp2T03
--    Rsyntax Gauge(0|1000..14000)
--  Units
--    milliseconds
    ACCESS read-write
    STATUS mandatory
    DESCRIPTION
        "Aligned timer."
    ::= { cItpSpScalars 7 }

cItpSpMtp2T04E OBJECT-TYPE
    SYNTAX CItpTcTimerMtp2T04E
--    Rsyntax Gauge(0|400..660)
--  Units
--    milliseconds
    ACCESS read-write
    STATUS mandatory
    DESCRIPTION
        "Proving period timer emergency timer. "
    ::= { cItpSpScalars 8 }

cItpSpMtp2T04N OBJECT-TYPE
    SYNTAX CItpTcTimerMtp2T04N
--    Rsyntax Gauge(0|2007..9500)
--  Units
--    milliseconds
    ACCESS read-write
    STATUS mandatory
    DESCRIPTION
        "Proving period timer normal timer."
    ::= { cItpSpScalars 9 }

cItpSpMtp2T05 OBJECT-TYPE
    SYNTAX CItpTcTimerMtp2T05
--    Rsyntax Gauge(0|80..120)
--  Units
--    milliseconds
    ACCESS read-write
    STATUS mandatory
    DESCRIPTION
        "Sending SIB timer."
    ::= { cItpSpScalars 10 }

cItpSpMtp2T06 OBJECT-TYPE
    SYNTAX CItpTcTimerMtp2T06
--    Rsyntax Gauge(1000..6000)
--  Units
--    milliseconds
    ACCESS read-write
    STATUS mandatory
    DESCRIPTION
        "Remote congestion timer. "
    ::= { cItpSpScalars 11 }

cItpSpMtp2T07 OBJECT-TYPE
    SYNTAX CItpTcTimerMtp2T07
--    Rsyntax Gauge(0|100..6000)
--  Units
--    milliseconds
    ACCESS read-write
    STATUS mandatory
    DESCRIPTION
        "Excessive delay of acknowledgement timer."
    ::= { cItpSpScalars 12 }

cItpSpMtp3T01 OBJECT-TYPE
    SYNTAX CItpTcTimerMtp3T01
--    Rsyntax Gauge(500..1200)
--  Units
--    milliseconds
    ACCESS read-write
    STATUS mandatory
    DESCRIPTION
        "Delay to avoid message mis-sequencing on changeover."
    ::= { cItpSpScalars 13 }

cItpSpMtp3T02 OBJECT-TYPE
    SYNTAX CItpTcTimerMtp3T02
--    Rsyntax Gauge(700..2000)
--  Units
--    milliseconds
    ACCESS read-write
    STATUS mandatory
    DESCRIPTION
        "Waiting for changeover acknowledgement."
    ::= { cItpSpScalars 14 }

cItpSpMtp3T03 OBJECT-TYPE
    SYNTAX CItpTcTimerMtp3T03
--    Rsyntax Gauge(500..1200)
--  Units
--    milliseconds
    ACCESS read-write
    STATUS mandatory
    DESCRIPTION
        "Time controlled diversion-delay to avoid
        mis-sequencing on change back."
    ::= { cItpSpScalars 15 }

cItpSpMtp3T04 OBJECT-TYPE
    SYNTAX CItpTcTimerMtp3T04
--    Rsyntax Gauge(500..1200)
--  Units
--    milliseconds
    ACCESS read-write
    STATUS mandatory
    DESCRIPTION
        "Waiting for change back acknowledgement (first
        attempt)."
    ::= { cItpSpScalars 16 }

cItpSpMtp3T05 OBJECT-TYPE
    SYNTAX CItpTcTimerMtp3T05
--    Rsyntax Gauge(500..1200)
--  Units
--    milliseconds
    ACCESS read-write
    STATUS mandatory
    DESCRIPTION
        "Waiting for change back acknowledgement (second
         attempt)."
    ::= { cItpSpScalars 17 }

cItpSpMtp3T06 OBJECT-TYPE
    SYNTAX CItpTcTimerMtp3T06
--    Rsyntax Gauge(500..1200)
--  Units
--    milliseconds
    ACCESS read-write
    STATUS mandatory
    DESCRIPTION
        "Delay to avoid message mis-sequencing on controlled
         rerouting."
    ::= { cItpSpScalars 18 }

cItpSpMtp3T07 OBJECT-TYPE
    SYNTAX CItpTcTimerMtp3T07
--    Rsyntax Gauge(0|1000..2000)
--  Units
--    milliseconds
    ACCESS read-write
    STATUS mandatory
    DESCRIPTION
        "Waiting for Signalling data link connection
         acknowledgement."
    ::= { cItpSpScalars 19 }

cItpSpMtp3T08 OBJECT-TYPE
    SYNTAX CItpTcTimerMtp3T08
--    Rsyntax Gauge(800..1200)
--  Units
--    milliseconds
    ACCESS read-write
    STATUS mandatory
    DESCRIPTION
        "Transfer prohibited inhibition timer (transient
         solution)."
    ::= { cItpSpScalars 20 }

cItpSpMtp3T10 OBJECT-TYPE
    SYNTAX CItpTcTimerMtp3T10
--    Rsyntax Gauge(30000..60000)
--  Units
--    milliseconds
    ACCESS read-write
    STATUS mandatory
    DESCRIPTION
        "Waiting to repeat Signalling routeset test message."
    ::= { cItpSpScalars 21 }

cItpSpMtp3T11 OBJECT-TYPE
    SYNTAX CItpTcTimerMtp3T11
--    Rsyntax Gauge(30000..90000)
--  Units
--    milliseconds
    ACCESS read-write
    STATUS mandatory
    DESCRIPTION
        "Transfer restricted timer. (This is one way of
        implementing the function described in 13.4/Q.704 and
        mainly intended to simplify SPs.)."
    ::= { cItpSpScalars 22 }

cItpSpMtp3T12 OBJECT-TYPE
    SYNTAX CItpTcTimerMtp3T12
--    Rsyntax Gauge(800..1500)
--  Units
--    milliseconds
    ACCESS read-write
    STATUS mandatory
    DESCRIPTION
        "Waiting for uninhibit acknowledgement."
    ::= { cItpSpScalars 23 }

cItpSpMtp3T13 OBJECT-TYPE
    SYNTAX CItpTcTimerMtp3T13
--    Rsyntax Gauge(800..1500)
--  Units
--    milliseconds
    ACCESS read-write
    STATUS mandatory
    DESCRIPTION
        "Waiting for force uninhibit."
    ::= { cItpSpScalars 24 }

cItpSpMtp3T14 OBJECT-TYPE
    SYNTAX CItpTcTimerMtp3T14
--    Rsyntax Gauge(2000..3000)
--  Units
--    milliseconds
    ACCESS read-write
    STATUS mandatory
    DESCRIPTION
        "Waiting for inhibition acknowledgement."
    ::= { cItpSpScalars 25 }

cItpSpMtp3T15 OBJECT-TYPE
    SYNTAX CItpTcTimerMtp3T15
--    Rsyntax Gauge(2000..3000)
--  Units
--    milliseconds
    ACCESS read-write
    STATUS mandatory
    DESCRIPTION
        "Waiting to start Signalling routeset congestion
         test."
    ::= { cItpSpScalars 26 }

cItpSpMtp3T16 OBJECT-TYPE
    SYNTAX CItpTcTimerMtp3T16
--    Rsyntax Gauge(1400..2000)
--  Units
--    milliseconds
    ACCESS read-write
    STATUS mandatory
    DESCRIPTION
        "Waiting for routeset congestion status update."
    ::= { cItpSpScalars 27 }

cItpSpMtp3T17 OBJECT-TYPE
    SYNTAX CItpTcTimerMtp3T17
--    Rsyntax Gauge(800..1500)
--  Units
--    milliseconds
    ACCESS read-write
    STATUS mandatory
    DESCRIPTION
        "Delay to avoid oscillation of initial alignment
        failure and link restart."
    ::= { cItpSpScalars 28 }

cItpSpMtp3T18 OBJECT-TYPE
    SYNTAX CItpTcTimerMtp3T18
--    Rsyntax Gauge(1000..31000)
--  Units
--    milliseconds
    ACCESS read-write
    STATUS mandatory
    DESCRIPTION
        "This timers servers different function based on the 
         variant.
         
         ANSI: Repeat TFR once by response method
         ITU:  MTP restart link supervision"
    ::= { cItpSpScalars 29 }

cItpSpMtp3T19 OBJECT-TYPE
    SYNTAX CItpTcTimerMtp3T19
--    Rsyntax Gauge(67000..600000)
--  Units
--    milliseconds
    ACCESS read-write
    STATUS mandatory
    DESCRIPTION
        "This timers servers different function based on the 
         variant.
         
         ANSI: failed craft timer referral timer
         ITU:  supervision timer during MTP restart"
    ::= { cItpSpScalars 30 }

cItpSpMtp3T20 OBJECT-TYPE
    SYNTAX CItpTcTimerMtp3T20
--    Rsyntax Gauge(1000..120000)
--  Units
--    milliseconds
    ACCESS read-write
    STATUS mandatory
    DESCRIPTION
        "This timers servers different function based on the 
         variant.
         
         ANSI: waiting to repeat local inhibit test
         ITU:  MTP restart timer at the Signalling point"
    ::= { cItpSpScalars 31 }

cItpSpMtp3T21 OBJECT-TYPE
    SYNTAX CItpTcTimerMtp3T21
--    Rsyntax Gauge(63000..120000)
--  Units
--    milliseconds
    ACCESS read-write
    STATUS mandatory
    DESCRIPTION
        "This timers servers different function based on the 
         variant.
         
         ANSI: waiting to repeat remote inhibit test)       
         ITU:  MTP restart timer at adjacent Signalling point"
    ::= { cItpSpScalars 32 }

cItpSpMtp3T22 OBJECT-TYPE
    SYNTAX CItpTcTimerMtp3T22
--    Rsyntax Gauge(36000..360000)
--  Units
--    milliseconds
    ACCESS read-write
    STATUS mandatory
    DESCRIPTION
        "This timers servers different function based on the 
         variant.
         
         ANSI: restarting SP waiting for Signalling links avail
         ITU:  local inhibit test timer"
    ::= { cItpSpScalars 33 }

cItpSpMtp3T23 OBJECT-TYPE
    SYNTAX CItpTcTimerMtp3T23
--    Rsyntax Gauge(9000..360000)
--  Units
--    milliseconds
    ACCESS read-write
    STATUS mandatory
    DESCRIPTION
        "This timers servers different function based on the 
         variant.
         
         ANSI: restarting SP waiting to receive all TRA msgs
         ITU:  remote inhibit test timer"
    ::= { cItpSpScalars 34 }

cItpSpMtp3T24 OBJECT-TYPE
    SYNTAX CItpTcTimerMtp3T24
--    Rsyntax Gauge(500..60000)
--  Units
--    milliseconds
    ACCESS read-write
    STATUS mandatory
    DESCRIPTION
        "This timers servers different function based on the 
         variant.
         
         ANSI: restarting SP waiting to broadcast all TRA msgs
         ITU:  stabilizing timer after local processor outage"
    ::= { cItpSpScalars 35 }

cItpSpMtp3T25 OBJECT-TYPE
    SYNTAX CItpTcTimerMtp3T25
--    Rsyntax Gauge(0|30000..35000)
--  Units
--    milliseconds
    ACCESS read-write
    STATUS mandatory
    DESCRIPTION
        "Timer at Signalling point (SP) adjacent to restarting
        SP, waiting for traffic restart allowed message."
    ::= { cItpSpScalars 36 }

cItpSpMtp3T26 OBJECT-TYPE
    SYNTAX CItpTcTimerMtp3T26
--    Rsyntax Gauge(0|12000..15000)
--  Units
--    milliseconds
    ACCESS read-write
    STATUS mandatory
    DESCRIPTION
        "Timer at restarting SP waiting to repeat traffic
        restart waiting message."
    ::= { cItpSpScalars 37 }

cItpSpMtp3T27 OBJECT-TYPE
    SYNTAX CItpTcTimerMtp3T27
--    Rsyntax Gauge(0|2000..50000)
--  Units
--    milliseconds
    ACCESS read-write
    STATUS mandatory
    DESCRIPTION
        "Minimum duration of unavailability for full restart."
    ::= { cItpSpScalars 38 }

cItpSpMtp3T28 OBJECT-TYPE
    SYNTAX CItpTcTimerMtp3T28
--    Rsyntax Gauge(0|3000..35000)
--  Units
--    milliseconds
    ACCESS read-write
    STATUS mandatory
    DESCRIPTION
        "Timer at SP adjacent to restarting SP waiting for
        traffic restart waiting message."
    ::= { cItpSpScalars 39 }

cItpSpMtp3T29 OBJECT-TYPE
    SYNTAX CItpTcTimerMtp3T29
--    Rsyntax Gauge(0|60000..65000)
--  Units
--    milliseconds
    ACCESS read-write
    STATUS mandatory
    DESCRIPTION
        "Timer started when TRA sent in response to unexpected
        TRA or TRW."
    ::= { cItpSpScalars 40 }

cItpSpMtp3T30 OBJECT-TYPE
    SYNTAX CItpTcTimerMtp3T30
--    Rsyntax Gauge(0|30000..35000)
--  Units
--    milliseconds
    ACCESS read-write
    STATUS mandatory
    DESCRIPTION
        "Timer to limit sending of TFPs and TFRs in response
        to unexpected TRA or TRW."
    ::= { cItpSpScalars 41 }

cItpSpMtp3T31 OBJECT-TYPE
    SYNTAX CItpTcTimerMtp3T31
--    Rsyntax Gauge(0|10000..120000)
--  Units
--    milliseconds
    ACCESS read-write
    STATUS mandatory
    DESCRIPTION
        "False link congestion detection timer."
    ::= { cItpSpScalars 42 }

cItpSpMtp3T32 OBJECT-TYPE
    SYNTAX CItpTcTimerMtp3T32
--    Rsyntax Gauge(0|5000..120000)
--  Units
--    milliseconds
    ACCESS read-write
    STATUS mandatory
    DESCRIPTION
        "Link oscillation timer - Procedure A."
    ::= { cItpSpScalars 43 }

cItpSpMtp3T33 OBJECT-TYPE
    SYNTAX CItpTcTimerMtp3T33
--    Rsyntax Gauge(0|60000..600000)
--  Units
--    milliseconds
    ACCESS read-write
    STATUS mandatory
    DESCRIPTION
        "Probation timer for link oscillation - Procedure B."
    ::= { cItpSpScalars 44 }

cItpSpMtp3T34 OBJECT-TYPE
    SYNTAX CItpTcTimerMtp3T34
--    Rsyntax Gauge(0|5000..120000)
--  Units
--    milliseconds
    ACCESS read-write
    STATUS mandatory
    DESCRIPTION
        "Suspension timer for link oscillation - Procedure B."
    ::= { cItpSpScalars 45 }

cItpSpTimerLinkTest OBJECT-TYPE
    SYNTAX CItpTcTimerLinkTest
--    Rsyntax Gauge(0|4000..12000)
--  Units
--    milliseconds
    ACCESS read-write
    STATUS mandatory
    DESCRIPTION
        "Signalling Link test acknowledgement timer."
    ::= { cItpSpScalars 46 }

cItpSpTimerLinkMessage OBJECT-TYPE
    SYNTAX CItpTcTimerLinkMessage
--    Rsyntax Gauge(0|30000..90000)
--  Units
--    milliseconds
    ACCESS read-write
    STATUS mandatory
    DESCRIPTION
        "Interval timer for sending test messages."
    ::= { cItpSpScalars 47 }

cItpSpTimerLinkActRetry OBJECT-TYPE
    SYNTAX CItpTcTimerLinkActRetry
--    Rsyntax Gauge(0|60000..90000)
--  Units
--    milliseconds
    ACCESS read-write
    STATUS mandatory
    DESCRIPTION
        "Link activation retry timer."
    ::= { cItpSpScalars 48 }

cItpSpTFR OBJECT-TYPE
    SYNTAX TruthValue
--    Rsyntax INTEGER {
--        true(1),
--        false(2)
--        }
    ACCESS read-write
    STATUS mandatory
    DESCRIPTION
        "Allow transfer restricted messages.
        'true'  TFR are allowed.
        'false' TFR are disabled."
    DEFVAL { false }
    ::= { cItpSpScalars 49 }

cItpSpCongestionsLevels OBJECT-TYPE
    SYNTAX TruthValue
--    Rsyntax INTEGER {
--        true(1),
--        false(2)
--        }
    ACCESS read-write
    STATUS mandatory
    DESCRIPTION
        "Allow multiple congestion levels.
        'true'  multiple congestion levels are allowed.
        'false' multiple congestion levels are disabled."
    DEFVAL { false }
    ::= { cItpSpScalars 50 }

cItpSpFastRestart OBJECT-TYPE
    SYNTAX TruthValue
--    Rsyntax INTEGER {
--        true(1),
--        false(2)
--        }
    ACCESS read-write
    STATUS mandatory
    DESCRIPTION
        "The support for fast restarts as follows. 
        'true'  fast restart is enabled.
        'false' fast restart is disabled."
    DEFVAL { false }
    ::= { cItpSpScalars 51 }

cItpSpDistSccpUnseq OBJECT-TYPE
    SYNTAX TruthValue
--    Rsyntax INTEGER {
--        true(1),
--        false(2)
--        }
    ACCESS read-write
    STATUS mandatory
    DESCRIPTION
        "Evenly distribute Class 0 SCCP messages as follows. 
        'true'   Evenly distribute 0 SCCP messages is enabled.
        'false'  Evenly distribute 0 SCCP messages is disabled."
    DEFVAL { false }
    ::= { cItpSpScalars 52 }

cItpSpSummaryRoutingException OBJECT-TYPE
    SYNTAX TruthValue
--    Rsyntax INTEGER {
--        true(1),
--        false(2)
--        }
    ACCESS read-write
    STATUS mandatory
    DESCRIPTION
        "This object is used to control the usage of the summary
         route when both a summary route (or ANSI cluster route)
         and a full point-code route (within that summary) are
         configured.  The object is used to indicate whether
         the summary route is to be used when the full
         point-code destination is inaccessible as follows.
          'true'   Use summary routing.
          'false'  Do not use summary routing."
    DEFVAL { true }
    ::= { cItpSpScalars 53 }

cItpSpUtilSampleInterval OBJECT-TYPE
    SYNTAX CItpSpSampleInterval
--    Rsyntax Gauge(60..3600)
--  Units
--    seconds
    ACCESS read-write
    STATUS mandatory
    DESCRIPTION
        "This object specifies the time interval used to monitor
         the utilization of SS7 links.  This object in combination
         with cItpSpUtilThreshold, cItpSpLinkPlanCapacitySent and
         cItpSpLinkPlanCapacityRcvd will be used to calculate 
         utilization of SS7 links.  Changes to the polling interval
         will take effect after the completion of the current 
         sample interval."
    DEFVAL { 300 }
    ::= { cItpSpScalars 54 }

cItpSpUtilThreshold OBJECT-TYPE
    SYNTAX CItpSpPercentThreshold
--    Rsyntax Gauge(0..100)
--  Units
--    percent
    ACCESS read-write
    STATUS mandatory
    DESCRIPTION
        "This object specifies the threshold of usage for all
         SS7 links in SP.  This object is used to determine when
         to generate the cItpSpLinkRcvdUtilChange or 
         cItpSpLinkSentUtilChange notifications.
         
         A value of zero indicates that no default threshold
         is specified.  Therefore, only links with non-zero
         values for cItpSpLinkUtilThresholdRcvd or 
         cItpSpLinkUtilThresholdSent will generate notifications
         based on link utilization.
         
         Changes to the utilization threshold will take effect
         at the end of the current interval."
    DEFVAL { 40 }
    ::= { cItpSpScalars 55 }

cItpSpUtilAbateDelta OBJECT-TYPE
    SYNTAX CItpSpPercentThreshold
--    Rsyntax Gauge(0..100)
--  Units
--    percent
    ACCESS read-write
    STATUS mandatory
    DESCRIPTION
        "This object allows the falling threshold to be lower 
         than the rising theshold when calculating whether to 
         generate the cItpSpLinkUtilThresholdRcvd or 
         cItpSpLinkUtilThresholdSent notifications.  This is done
         to prevent generating notifications for slight changes
         in traffic."
    DEFVAL { 0 }
    ::= { cItpSpScalars 56 }

cItpSpPointCodeTable OBJECT-TYPE
    SYNTAX SEQUENCE OF CItpSpPointCodeTableEntry
    ACCESS not-accessible
    STATUS mandatory
    DESCRIPTION
        "A table that contain the varies types of point
        code defined for this Signalling point.'
        Entries are added to this table via
        cItpSpRowStatus  in accordance with the RowStatus
        convention."
    ::= { cItpSpPointCode 1 }

cItpSpPointCodeTableEntry OBJECT-TYPE
    SYNTAX CItpSpPointCodeTableEntry
    ACCESS not-accessible
    STATUS mandatory
    DESCRIPTION
        "A list of SP attributes."
    INDEX { cItpSpPointCodeNi, cItpSpPointCodeBin }
    ::= { cItpSpPointCodeTable 1 }

CItpSpPointCodeTableEntry ::= SEQUENCE {
    cItpSpPointCodeNi CItpTcNetworkIndicator,
    cItpSpPointCodeBin CItpTcPointCode,
    cItpSpPointCodeType CItpTcPointCodeType,
    cItpSpPointCodeDisplay CItpTcDisplayPC,
    cItpSpPointCodeRowStatus RowStatus
    }

cItpSpPointCodeNi OBJECT-TYPE
    SYNTAX CItpTcNetworkIndicator
--    Rsyntax INTEGER {
--        ?? enum value of zero may cause problems
--        international(0),
--        internationatSpare(1),
--        national(2),
--        nationalSpare(3)
--        }
    ACCESS not-accessible
    STATUS mandatory
    DESCRIPTION
        "The network Indicator for this pointcode."
    ::= { cItpSpPointCodeTableEntry 1 }

cItpSpPointCodeBin OBJECT-TYPE
    SYNTAX CItpTcPointCode
--    Rsyntax Gauge(0..16777216)
    ACCESS not-accessible
    STATUS mandatory
    DESCRIPTION
        "The point code for this SP."
    ::= { cItpSpPointCodeTableEntry 2 }

cItpSpPointCodeType OBJECT-TYPE
    SYNTAX CItpTcPointCodeType
--    Rsyntax INTEGER {
--        primary(1),
--        additional(2),
--        capability(3)
--        }
    ACCESS read-write
    STATUS mandatory
    DESCRIPTION
        "The function of this point code"
    ::= { cItpSpPointCodeTableEntry 3 }

cItpSpPointCodeDisplay OBJECT-TYPE
    SYNTAX CItpTcDisplayPC
--    Rsyntax OCTET STRING(SIZE(1..12))
    ACCESS read-only
    STATUS mandatory
    DESCRIPTION
        "The point code for this SP."
    ::= { cItpSpPointCodeTableEntry 4 }

cItpSpPointCodeRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpSpPointCodeTable  
        following the RowStatus textual convention."
    ::= { cItpSpPointCodeTableEntry 5 }

cItpSpLinksetTable OBJECT-TYPE
    SYNTAX SEQUENCE OF CItpSpLinksetTableEntry
    ACCESS not-accessible
    STATUS mandatory
    DESCRIPTION
        "A table of linksets for this SP. "
    ::= { cItpSpLinkset 1 }

cItpSpLinksetTableEntry OBJECT-TYPE
    SYNTAX CItpSpLinksetTableEntry
    ACCESS not-accessible
    STATUS mandatory
    DESCRIPTION
        "A list of SP linkset attributes for a particular SP
        entity."
    INDEX { cItpSpLinksetName }
    ::= { cItpSpLinksetTable 1 }

CItpSpLinksetTableEntry ::= SEQUENCE {
    cItpSpLinksetName CItpTcLinksetId,
    cItpSpLinksetSourcePointCode CItpTcPointCode,
    cItpSpLinksetSourceDisplayPC CItpTcDisplayPC,
    cItpSpLinksetAdjacentPointCode CItpTcPointCode,
    cItpSpLinksetAdjacentDisplayPC CItpTcDisplayPC,
    cItpSpLinksetState INTEGER,
    cItpSpLinksetInboundAcl CItpTcAclId,
    cItpSpLinksetOutboundAcl CItpTcAclId,
    cItpSpLinksetSnmmRTN CItpTcRouteTableName,
    cItpSpLinksetSntmRTN CItpTcRouteTableName,
    cItpSpLinksetSpare2RTN CItpTcRouteTableName,
    cItpSpLinksetSccpRTN CItpTcRouteTableName,
    cItpSpLinksetTupRTN CItpTcRouteTableName,
    cItpSpLinksetIsupRTN CItpTcRouteTableName,
    cItpSpLinksetDupcRTN CItpTcRouteTableName,
    cItpSpLinksetDupfRTN CItpTcRouteTableName,
    cItpSpLinksetMtupRTN CItpTcRouteTableName,
    cItpSpLinksetBisupRTN CItpTcRouteTableName,
    cItpSpLinksetSisupRTN CItpTcRouteTableName,
    cItpSpLinksetSpare11RTN CItpTcRouteTableName,
    cItpSpLinksetSpare12RTN CItpTcRouteTableName,
    cItpSpLinksetSpare13RTN CItpTcRouteTableName,
    cItpSpLinksetSpare14RTN CItpTcRouteTableName,
    cItpSpLinksetSpare15RTN CItpTcRouteTableName,
    cItpSpLinksetAccountingEnabled TruthValue,
    cItpSpLinksetNumLinks Gauge,
    cItpSpLinksetDurationInService TimeTicks,
    cItpSpLinksetDurationOutService TimeTicks,
    cItpSpLinksetMtp2T01 CItpTcTimerMtp2T01,
    cItpSpLinksetMtp2T02 CItpTcTimerMtp2T02,
    cItpSpLinksetMtp2T03 CItpTcTimerMtp2T03,
    cItpSpLinksetMtp2T04E CItpTcTimerMtp2T04E,
    cItpSpLinksetMtp2T04N CItpTcTimerMtp2T04N,
    cItpSpLinksetMtp2T05 CItpTcTimerMtp2T05,
    cItpSpLinksetMtp2T06 CItpTcTimerMtp2T06,
    cItpSpLinksetMtp2T07 CItpTcTimerMtp2T07,
    cItpSpLinksetMtp3T01 CItpTcTimerMtp3T01,
    cItpSpLinksetMtp3T02 CItpTcTimerMtp3T02,
    cItpSpLinksetMtp3T03 CItpTcTimerMtp3T03,
    cItpSpLinksetMtp3T04 CItpTcTimerMtp3T04,
    cItpSpLinksetMtp3T05 CItpTcTimerMtp3T05,
    cItpSpLinksetMtp3T06 CItpTcTimerMtp3T06,
    cItpSpLinksetMtp3T07 CItpTcTimerMtp3T07,
    cItpSpLinksetMtp3T08 CItpTcTimerMtp3T08,
    cItpSpLinksetMtp3T10 CItpTcTimerMtp3T10,
    cItpSpLinksetMtp3T11 CItpTcTimerMtp3T11,
    cItpSpLinksetMtp3T12 CItpTcTimerMtp3T12,
    cItpSpLinksetMtp3T13 CItpTcTimerMtp3T13,
    cItpSpLinksetMtp3T14 CItpTcTimerMtp3T14,
    cItpSpLinksetMtp3T15 CItpTcTimerMtp3T15,
    cItpSpLinksetMtp3T16 CItpTcTimerMtp3T16,
    cItpSpLinksetMtp3T17 CItpTcTimerMtp3T17,
    cItpSpLinksetMtp3T18 CItpTcTimerMtp3T18,
    cItpSpLinksetMtp3T19 CItpTcTimerMtp3T19,
    cItpSpLinksetMtp3T20 CItpTcTimerMtp3T20,
    cItpSpLinksetMtp3T21 CItpTcTimerMtp3T21,
    cItpSpLinksetMtp3T22 CItpTcTimerMtp3T22,
    cItpSpLinksetMtp3T23 CItpTcTimerMtp3T23,
    cItpSpLinksetMtp3T24 CItpTcTimerMtp3T24,
    cItpSpLinksetMtp3T25 CItpTcTimerMtp3T25,
    cItpSpLinksetMtp3T26 CItpTcTimerMtp3T26,
    cItpSpLinksetMtp3T27 CItpTcTimerMtp3T27,
    cItpSpLinksetMtp3T28 CItpTcTimerMtp3T28,
    cItpSpLinksetMtp3T29 CItpTcTimerMtp3T29,
    cItpSpLinksetMtp3T30 CItpTcTimerMtp3T30,
    cItpSpLinksetMtp3T31 CItpTcTimerMtp3T31,
    cItpSpLinksetMtp3T32 CItpTcTimerMtp3T32,
    cItpSpLinksetMtp3T33 CItpTcTimerMtp3T33,
    cItpSpLinksetMtp3T34 CItpTcTimerMtp3T34,
    cItpSpLinksetTimerLinkTest CItpTcTimerLinkTest,
    cItpSpLinksetTimerLinkMessage CItpTcTimerLinkMessage,
    cItpSpLinksetTimerLinkActRetry CItpTcTimerLinkActRetry,
    cItpSpLinksetPlanCapacity INTEGER,
    cItpSpLinksetActPriority Gauge,
    cItpSpLinksetType INTEGER,
    cItpSpLinksetRowStatus RowStatus,
    cItpSpLinksetNi CItpTcNetworkIndicator,
    cItpSpLinksetDisplayName SnmpAdminString,
    cItpSpLinksetDescription SnmpAdminString,
    cItpSpLinksetVariant CItpTcSs7Variant
    }

cItpSpLinksetName OBJECT-TYPE
    SYNTAX CItpTcLinksetId
--    Rsyntax OCTET STRING(SIZE(1..19))
    ACCESS not-accessible
    STATUS mandatory
    DESCRIPTION
        "The name of the linkset."
    ::= { cItpSpLinksetTableEntry 1 }

cItpSpLinksetSourcePointCode OBJECT-TYPE
    SYNTAX CItpTcPointCode
--    Rsyntax Gauge(0..16777216)
    ACCESS read-write
    STATUS mandatory
    DESCRIPTION
        "The point code to which this linkset is connected."
    ::= { cItpSpLinksetTableEntry 2 }

cItpSpLinksetSourceDisplayPC OBJECT-TYPE
    SYNTAX CItpTcDisplayPC
--    Rsyntax OCTET STRING(SIZE(1..12))
    ACCESS read-only
    STATUS mandatory
    DESCRIPTION
        "The point code to which this linkset is connected."
    ::= { cItpSpLinksetTableEntry 3 }

cItpSpLinksetAdjacentPointCode OBJECT-TYPE
    SYNTAX CItpTcPointCode
--    Rsyntax Gauge(0..16777216)
    ACCESS read-write
    STATUS mandatory
    DESCRIPTION
        "The point code to which this linkset is connected."
    ::= { cItpSpLinksetTableEntry 4 }

cItpSpLinksetAdjacentDisplayPC OBJECT-TYPE
    SYNTAX CItpTcDisplayPC
--    Rsyntax OCTET STRING(SIZE(1..12))
    ACCESS read-only
    STATUS mandatory
    DESCRIPTION
        "The point code to which this linkset is connected."
    ::= { cItpSpLinksetTableEntry 5 }

cItpSpLinksetState OBJECT-TYPE
    SYNTAX INTEGER {
        available(1),
        shutdown(2),
        unavailable(3)
        }
    ACCESS read-only
    STATUS mandatory
    DESCRIPTION
        "The list of possible linkset states.
         'available'  : Traffic may flow over this linkset
         'shutdown'   : This linkset has been forced to an
                        unavailable state by an administrative
                        action.
         'unavailable': The linkset is currently unable to support
                        traffic. Activation of this linkset will 
                        occur as required by protocol."
    ::= { cItpSpLinksetTableEntry 6 }

cItpSpLinksetInboundAcl OBJECT-TYPE
    SYNTAX CItpTcAclId
--    Rsyntax Gauge(0|2700..2999)
    ACCESS read-write
    STATUS mandatory
    DESCRIPTION
        "Packets are filtered against this access control list 
         before they are passed to the routing function.  A
         value of zero indicates that no access control list
         is present."
    ::= { cItpSpLinksetTableEntry 7 }

cItpSpLinksetOutboundAcl OBJECT-TYPE
    SYNTAX CItpTcAclId
--    Rsyntax Gauge(0|2700..2999)
    ACCESS read-write
    STATUS mandatory
    DESCRIPTION
        "Packets are filtered against this access control list 
         after they have passed through the routing function.  
         A value of zero indicates that no access control list
         is present."
    ::= { cItpSpLinksetTableEntry 8 }

cItpSpLinksetSnmmRTN OBJECT-TYPE
    SYNTAX CItpTcRouteTableName
--    Rsyntax OCTET STRING(SIZE(1..19))
    ACCESS read-write
    STATUS mandatory
    DESCRIPTION
        "The routing table for Signalling network management
        messages."
    REFERENCE
        "ITU Q.704 Signalling network functions and messages,
        section 14.2.1."
    ::= { cItpSpLinksetTableEntry 9 }

cItpSpLinksetSntmRTN OBJECT-TYPE
    SYNTAX CItpTcRouteTableName
--    Rsyntax OCTET STRING(SIZE(1..19))
    ACCESS read-write
    STATUS mandatory
    DESCRIPTION
        "The routing table for Signalling network test and
        maintenance messages."
    REFERENCE
        "ITU Q.704 Signalling network functions and messages,
        section 14.2.1."
    ::= { cItpSpLinksetTableEntry 10 }

cItpSpLinksetSpare2RTN OBJECT-TYPE
    SYNTAX CItpTcRouteTableName
--    Rsyntax OCTET STRING(SIZE(1..19))
    ACCESS read-write
    STATUS mandatory
    DESCRIPTION
        "This routing table has been defined as a spare
        routing table by the standards committee."
    REFERENCE
        "ITU Q.704 Signalling network functions and messages,
        section 14.2.1."
    ::= { cItpSpLinksetTableEntry 11 }

cItpSpLinksetSccpRTN OBJECT-TYPE
    SYNTAX CItpTcRouteTableName
--    Rsyntax OCTET STRING(SIZE(1..19))
    ACCESS read-write
    STATUS mandatory
    DESCRIPTION
        "The routing table for SS7 Signalling Connection
        Control Part(SCCP) messages."
    REFERENCE
        "ITU Q.704 Signalling network functions and messages,
        section 14.2.1."
    ::= { cItpSpLinksetTableEntry 12 }

cItpSpLinksetTupRTN OBJECT-TYPE
    SYNTAX CItpTcRouteTableName
--    Rsyntax OCTET STRING(SIZE(1..19))
    ACCESS read-write
    STATUS mandatory
    DESCRIPTION
        "The routing table for Telephone User Part(TUP) 
         messages."
    REFERENCE
        "ITU Q.704 Signalling network functions and messages,
        section 14.2.1."
    ::= { cItpSpLinksetTableEntry 13 }

cItpSpLinksetIsupRTN OBJECT-TYPE
    SYNTAX CItpTcRouteTableName
--    Rsyntax OCTET STRING(SIZE(1..19))
    ACCESS read-write
    STATUS mandatory
    DESCRIPTION
        "The routing table for ISDN User Part messages."
    REFERENCE
        "ITU Q.704 Signalling network functions and messages,
        section 14.2.1."
    ::= { cItpSpLinksetTableEntry 14 }

cItpSpLinksetDupcRTN OBJECT-TYPE
    SYNTAX CItpTcRouteTableName
--    Rsyntax OCTET STRING(SIZE(1..19))
    ACCESS read-write
    STATUS mandatory
    DESCRIPTION
        "The routing table for Data User Part (call and
        circuit-related messages)."
    REFERENCE
        "ITU Q.704 Signalling network functions and messages,
        section 14.2.1."
    ::= { cItpSpLinksetTableEntry 15 }

cItpSpLinksetDupfRTN OBJECT-TYPE
    SYNTAX CItpTcRouteTableName
--    Rsyntax OCTET STRING(SIZE(1..19))
    ACCESS read-write
    STATUS mandatory
    DESCRIPTION
        "The routing table for Data User Part (facility
        registration and cancellation messages)."
    REFERENCE
        "ITU Q.704 Signalling network functions and messages,
        section 14.2.1."
    ::= { cItpSpLinksetTableEntry 16 }

cItpSpLinksetMtupRTN OBJECT-TYPE
    SYNTAX CItpTcRouteTableName
--    Rsyntax OCTET STRING(SIZE(1..19))
    ACCESS read-write
    STATUS mandatory
    DESCRIPTION
        "The routing table for MTP Testing User Part
        messages."
    REFERENCE
        "ITU Q.704 Signalling network functions and messages,
        section 14.2.1."
    ::= { cItpSpLinksetTableEntry 17 }

cItpSpLinksetBisupRTN OBJECT-TYPE
    SYNTAX CItpTcRouteTableName
--    Rsyntax OCTET STRING(SIZE(1..19))
    ACCESS read-write
    STATUS mandatory
    DESCRIPTION
        "The routing table for Broadband ISDN User Part(BISUP)
        messages."
    REFERENCE
        "ITU Q.704 Signalling network functions and messages,
        section 14.2.1."
    ::= { cItpSpLinksetTableEntry 18 }

cItpSpLinksetSisupRTN OBJECT-TYPE
    SYNTAX CItpTcRouteTableName
--    Rsyntax OCTET STRING(SIZE(1..19))
    ACCESS read-write
    STATUS mandatory
    DESCRIPTION
        "The routing table for Satellite ISDN User Part(SISUP)
        messages."
    REFERENCE
        "ITU Q.704 Signalling network functions and messages,
        section 14.2.1."
    ::= { cItpSpLinksetTableEntry 19 }

cItpSpLinksetSpare11RTN OBJECT-TYPE
    SYNTAX CItpTcRouteTableName
--    Rsyntax OCTET STRING(SIZE(1..19))
    ACCESS read-write
    STATUS mandatory
    DESCRIPTION
        "This routing table has been defined as a spare
        routing table by the standards committee."
    REFERENCE
        "ITU Q.704 Signalling network functions and messages,
        section 14.2.1."
    ::= { cItpSpLinksetTableEntry 20 }

cItpSpLinksetSpare12RTN OBJECT-TYPE
    SYNTAX CItpTcRouteTableName
--    Rsyntax OCTET STRING(SIZE(1..19))
    ACCESS read-write
    STATUS mandatory
    DESCRIPTION
        "This routing table has been defined as a spare
        routing table by the standards committee."
    REFERENCE
        "ITU Q.704 Signalling network functions and messages,
        section 14.2.1."
    ::= { cItpSpLinksetTableEntry 21 }

cItpSpLinksetSpare13RTN OBJECT-TYPE
    SYNTAX CItpTcRouteTableName
--    Rsyntax OCTET STRING(SIZE(1..19))
    ACCESS read-write
    STATUS mandatory
    DESCRIPTION
        "This routing table has been defined as a spare
        routing table by the standards committee."
    REFERENCE
        "ITU Q.704 Signalling network functions and messages,
        section 14.2.1."
    ::= { cItpSpLinksetTableEntry 22 }

cItpSpLinksetSpare14RTN OBJECT-TYPE
    SYNTAX CItpTcRouteTableName
--    Rsyntax OCTET STRING(SIZE(1..19))
    ACCESS read-write
    STATUS mandatory
    DESCRIPTION
        "This routing table has been defined as a spare
        routing table by the standards committee."
    REFERENCE
        "ITU Q.704 Signalling network functions and messages,
        section 14.2.1."
    ::= { cItpSpLinksetTableEntry 23 }

cItpSpLinksetSpare15RTN OBJECT-TYPE
    SYNTAX CItpTcRouteTableName
--    Rsyntax OCTET STRING(SIZE(1..19))
    ACCESS read-write
    STATUS mandatory
    DESCRIPTION
        "This routing table has been defined as a spare
        routing table by the standards committee."
    REFERENCE
        "ITU Q.704 Signalling network functions and messages,
        section 14.2.1."
    ::= { cItpSpLinksetTableEntry 24 }

cItpSpLinksetAccountingEnabled OBJECT-TYPE
    SYNTAX TruthValue
--    Rsyntax INTEGER {
--        true(1),
--        false(2)
--        }
    ACCESS read-write
    STATUS mandatory
    DESCRIPTION
        "This indicates if accounting for this linkset is
        enabled.
        
        'true'  Indicates that the accounting function is
                enabled for this linkset and is being
                accumulated in cItpSpAccountingTable.
        
        'false' Indicates that the accounting function is 
                disabled."
    DEFVAL { false }
    ::= { cItpSpLinksetTableEntry 25 }

cItpSpLinksetNumLinks OBJECT-TYPE
    SYNTAX Gauge
    ACCESS read-only
    STATUS mandatory
    DESCRIPTION
        "The number of links in this linkset."
    ::= { cItpSpLinksetTableEntry 26 }

cItpSpLinksetDurationInService OBJECT-TYPE
    SYNTAX TimeTicks
    ACCESS read-only
    STATUS mandatory
    DESCRIPTION
        "Time linkset was providing service related to 
         Q752/Table 4.2."
    ::= { cItpSpLinksetTableEntry 27 }

cItpSpLinksetDurationOutService OBJECT-TYPE
    SYNTAX TimeTicks
    ACCESS read-only
    STATUS mandatory
    DESCRIPTION
        "Time linkset was Out-of-Service as required for 
         Q752/Table 4.2."
    ::= { cItpSpLinksetTableEntry 28 }

cItpSpLinksetMtp2T01 OBJECT-TYPE
    SYNTAX CItpTcTimerMtp2T01
--    Rsyntax Gauge(5000..150000)
--  Units
--    milliseconds
    ACCESS read-write
    STATUS mandatory
    DESCRIPTION
        "Alignment ready timer."
    ::= { cItpSpLinksetTableEntry 29 }

cItpSpLinksetMtp2T02 OBJECT-TYPE
    SYNTAX CItpTcTimerMtp2T02
--    Rsyntax Gauge(0|5000..150000)
--  Units
--    milliseconds
    ACCESS read-write
    STATUS mandatory
    DESCRIPTION
        "Not aligned timer."
    ::= { cItpSpLinksetTableEntry 30 }

cItpSpLinksetMtp2T03 OBJECT-TYPE
    SYNTAX CItpTcTimerMtp2T03
--    Rsyntax Gauge(0|1000..14000)
--  Units
--    milliseconds
    ACCESS read-write
    STATUS mandatory
    DESCRIPTION
        "Aligned timer."
    ::= { cItpSpLinksetTableEntry 31 }

cItpSpLinksetMtp2T04E OBJECT-TYPE
    SYNTAX CItpTcTimerMtp2T04E
--    Rsyntax Gauge(0|400..660)
--  Units
--    milliseconds
    ACCESS read-write
    STATUS mandatory
    DESCRIPTION
        "Proving period timer emergency timer. "
    ::= { cItpSpLinksetTableEntry 32 }

cItpSpLinksetMtp2T04N OBJECT-TYPE
    SYNTAX CItpTcTimerMtp2T04N
--    Rsyntax Gauge(0|2007..9500)
--  Units
--    milliseconds
    ACCESS read-write
    STATUS mandatory
    DESCRIPTION
        "Proving period timer normal timer."
    ::= { cItpSpLinksetTableEntry 33 }

cItpSpLinksetMtp2T05 OBJECT-TYPE
    SYNTAX CItpTcTimerMtp2T05
--    Rsyntax Gauge(0|80..120)
--  Units
--    milliseconds
    ACCESS read-write
    STATUS mandatory
    DESCRIPTION
        "Sending SIB timer."
    ::= { cItpSpLinksetTableEntry 34 }

cItpSpLinksetMtp2T06 OBJECT-TYPE
    SYNTAX CItpTcTimerMtp2T06
--    Rsyntax Gauge(1000..6000)
--  Units
--    milliseconds
    ACCESS read-write
    STATUS mandatory
    DESCRIPTION
        "Remote congestion timer. "
    ::= { cItpSpLinksetTableEntry 35 }

cItpSpLinksetMtp2T07 OBJECT-TYPE
    SYNTAX CItpTcTimerMtp2T07
--    Rsyntax Gauge(0|100..6000)
--  Units
--    milliseconds
    ACCESS read-write
    STATUS mandatory
    DESCRIPTION
        "Excessive delay of acknowledgement timer."
    ::= { cItpSpLinksetTableEntry 36 }

cItpSpLinksetMtp3T01 OBJECT-TYPE
    SYNTAX CItpTcTimerMtp3T01
--    Rsyntax Gauge(500..1200)
--  Units
--    milliseconds
    ACCESS read-write
    STATUS mandatory
    DESCRIPTION
        "Delay to avoid message mis-sequencing on changeover."
    ::= { cItpSpLinksetTableEntry 37 }

cItpSpLinksetMtp3T02 OBJECT-TYPE
    SYNTAX CItpTcTimerMtp3T02
--    Rsyntax Gauge(700..2000)
--  Units
--    milliseconds
    ACCESS read-write
    STATUS mandatory
    DESCRIPTION
        "Waiting for changeover acknowledgement."
    ::= { cItpSpLinksetTableEntry 38 }

cItpSpLinksetMtp3T03 OBJECT-TYPE
    SYNTAX CItpTcTimerMtp3T03
--    Rsyntax Gauge(500..1200)
--  Units
--    milliseconds
    ACCESS read-write
    STATUS mandatory
    DESCRIPTION
        "Time controlled diversion-delay to avoid
        mis-sequencing on change back."
    ::= { cItpSpLinksetTableEntry 39 }

cItpSpLinksetMtp3T04 OBJECT-TYPE
    SYNTAX CItpTcTimerMtp3T04
--    Rsyntax Gauge(500..1200)
--  Units
--    milliseconds
    ACCESS read-write
    STATUS mandatory
    DESCRIPTION
        "Waiting for change back acknowledgement (first
        attempt)."
    ::= { cItpSpLinksetTableEntry 40 }

cItpSpLinksetMtp3T05 OBJECT-TYPE
    SYNTAX CItpTcTimerMtp3T05
--    Rsyntax Gauge(500..1200)
--  Units
--    milliseconds
    ACCESS read-write
    STATUS mandatory
    DESCRIPTION
        "Waiting for change back acknowledgement (second
         attempt)."
    ::= { cItpSpLinksetTableEntry 41 }

cItpSpLinksetMtp3T06 OBJECT-TYPE
    SYNTAX CItpTcTimerMtp3T06
--    Rsyntax Gauge(500..1200)
--  Units
--    milliseconds
    ACCESS read-write
    STATUS mandatory
    DESCRIPTION
        "Delay to avoid message mis-sequencing on controlled
         rerouting."
    ::= { cItpSpLinksetTableEntry 42 }

cItpSpLinksetMtp3T07 OBJECT-TYPE
    SYNTAX CItpTcTimerMtp3T07
--    Rsyntax Gauge(0|1000..2000)
--  Units
--    milliseconds
    ACCESS read-write
    STATUS mandatory
    DESCRIPTION
        "Waiting for Signalling data link connection
         acknowledgement."
    ::= { cItpSpLinksetTableEntry 43 }

cItpSpLinksetMtp3T08 OBJECT-TYPE
    SYNTAX CItpTcTimerMtp3T08
--    Rsyntax Gauge(800..1200)
--  Units
--    milliseconds
    ACCESS read-write
    STATUS mandatory
    DESCRIPTION
        "Transfer prohibited inhibition timer (transient
         solution)."
    ::= { cItpSpLinksetTableEntry 44 }

cItpSpLinksetMtp3T10 OBJECT-TYPE
    SYNTAX CItpTcTimerMtp3T10
--    Rsyntax Gauge(30000..60000)
--  Units
--    milliseconds
    ACCESS read-write
    STATUS mandatory
    DESCRIPTION
        "Waiting to repeat Signalling routeset test message."
    ::= { cItpSpLinksetTableEntry 45 }

cItpSpLinksetMtp3T11 OBJECT-TYPE
    SYNTAX CItpTcTimerMtp3T11
--    Rsyntax Gauge(30000..90000)
--  Units
--    milliseconds
    ACCESS read-write
    STATUS mandatory
    DESCRIPTION
        "Transfer restricted timer. (This is one way of
        implementing the function described in 13.4/Q.704 and
        mainly intended to simplify SPs.)."
    ::= { cItpSpLinksetTableEntry 46 }

cItpSpLinksetMtp3T12 OBJECT-TYPE
    SYNTAX CItpTcTimerMtp3T12
--    Rsyntax Gauge(800..1500)
--  Units
--    milliseconds
    ACCESS read-write
    STATUS mandatory
    DESCRIPTION
        "Waiting for uninhibit acknowledgement."
    ::= { cItpSpLinksetTableEntry 47 }

cItpSpLinksetMtp3T13 OBJECT-TYPE
    SYNTAX CItpTcTimerMtp3T13
--    Rsyntax Gauge(800..1500)
--  Units
--    milliseconds
    ACCESS read-write
    STATUS mandatory
    DESCRIPTION
        "Waiting for force uninhibit."
    ::= { cItpSpLinksetTableEntry 48 }

cItpSpLinksetMtp3T14 OBJECT-TYPE
    SYNTAX CItpTcTimerMtp3T14
--    Rsyntax Gauge(2000..3000)
--  Units
--    milliseconds
    ACCESS read-write
    STATUS mandatory
    DESCRIPTION
        "Waiting for inhibition acknowledgement."
    ::= { cItpSpLinksetTableEntry 49 }

cItpSpLinksetMtp3T15 OBJECT-TYPE
    SYNTAX CItpTcTimerMtp3T15
--    Rsyntax Gauge(2000..3000)
--  Units
--    milliseconds
    ACCESS read-write
    STATUS mandatory
    DESCRIPTION
        "Waiting to start Signalling routeset congestion
         test."
    ::= { cItpSpLinksetTableEntry 50 }

cItpSpLinksetMtp3T16 OBJECT-TYPE
    SYNTAX CItpTcTimerMtp3T16
--    Rsyntax Gauge(1400..2000)
--  Units
--    milliseconds
    ACCESS read-write
    STATUS mandatory
    DESCRIPTION
        "Waiting for routeset congestion status update."
    ::= { cItpSpLinksetTableEntry 51 }

cItpSpLinksetMtp3T17 OBJECT-TYPE
    SYNTAX CItpTcTimerMtp3T17
--    Rsyntax Gauge(800..1500)
--  Units
--    milliseconds
    ACCESS read-write
    STATUS mandatory
    DESCRIPTION
        "Delay to avoid oscillation of initial alignment
        failure and link restart."
    ::= { cItpSpLinksetTableEntry 52 }

cItpSpLinksetMtp3T18 OBJECT-TYPE
    SYNTAX CItpTcTimerMtp3T18
--    Rsyntax Gauge(1000..31000)
--  Units
--    milliseconds
    ACCESS read-write
    STATUS mandatory
    DESCRIPTION
        "This timers servers different function based on the 
         variant.
         
         ANSI: Repeat TFR once by response method
         ITU:  MTP restart link supervision"
    ::= { cItpSpLinksetTableEntry 53 }

cItpSpLinksetMtp3T19 OBJECT-TYPE
    SYNTAX CItpTcTimerMtp3T19
--    Rsyntax Gauge(67000..600000)
--  Units
--    milliseconds
    ACCESS read-write
    STATUS mandatory
    DESCRIPTION
        "This timers servers different function based on the 
         variant.
         
         ANSI: failed craft timer referral timer
         ITU:  supervision timer during MTP restart"
    ::= { cItpSpLinksetTableEntry 54 }

cItpSpLinksetMtp3T20 OBJECT-TYPE
    SYNTAX CItpTcTimerMtp3T20
--    Rsyntax Gauge(1000..120000)
--  Units
--    milliseconds
    ACCESS read-write
    STATUS mandatory
    DESCRIPTION
        "This timers servers different function based on the 
         variant.
         
         ANSI: waiting to repeat local inhibit test
         ITU:  MTP restart timer at the Signalling point"
    ::= { cItpSpLinksetTableEntry 55 }

cItpSpLinksetMtp3T21 OBJECT-TYPE
    SYNTAX CItpTcTimerMtp3T21
--    Rsyntax Gauge(63000..120000)
--  Units
--    milliseconds
    ACCESS read-write
    STATUS mandatory
    DESCRIPTION
        "This timers servers different function based on the 
         variant.
         
         ANSI: waiting to repeat remote inhibit test)       
         ITU:  MTP restart timer at adjacent Signalling point"
    ::= { cItpSpLinksetTableEntry 56 }

cItpSpLinksetMtp3T22 OBJECT-TYPE
    SYNTAX CItpTcTimerMtp3T22
--    Rsyntax Gauge(36000..360000)
--  Units
--    milliseconds
    ACCESS read-write
    STATUS mandatory
    DESCRIPTION
        "This timers servers different function based on the 
         variant.
         
         ANSI: restarting SP waiting for Signalling links avail
         ITU:  local inhibit test timer"
    ::= { cItpSpLinksetTableEntry 57 }

cItpSpLinksetMtp3T23 OBJECT-TYPE
    SYNTAX CItpTcTimerMtp3T23
--    Rsyntax Gauge(9000..360000)
--  Units
--    milliseconds
    ACCESS read-write
    STATUS mandatory
    DESCRIPTION
        "This timers servers different function based on the 
         variant.
         
         ANSI: restarting SP waiting to receive all TRA msgs
         ITU:  remote inhibit test timer"
    ::= { cItpSpLinksetTableEntry 58 }

cItpSpLinksetMtp3T24 OBJECT-TYPE
    SYNTAX CItpTcTimerMtp3T24
--    Rsyntax Gauge(500..60000)
--  Units
--    milliseconds
    ACCESS read-write
    STATUS mandatory
    DESCRIPTION
        "This timers servers different function based on the 
         variant.
         
         ANSI: restarting SP waiting to broadcast all TRA msgs
         ITU:  stabilizing timer after local processor outage"
    ::= { cItpSpLinksetTableEntry 59 }

cItpSpLinksetMtp3T25 OBJECT-TYPE
    SYNTAX CItpTcTimerMtp3T25
--    Rsyntax Gauge(0|30000..35000)
--  Units
--    milliseconds
    ACCESS read-write
    STATUS mandatory
    DESCRIPTION
        "Timer at Signalling Point (SP) adjacent to restarting
        SP, waiting for traffic restart allowed message."
    ::= { cItpSpLinksetTableEntry 60 }

cItpSpLinksetMtp3T26 OBJECT-TYPE
    SYNTAX CItpTcTimerMtp3T26
--    Rsyntax Gauge(0|12000..15000)
--  Units
--    milliseconds
    ACCESS read-write
    STATUS mandatory
    DESCRIPTION
        "Timer at restarting SP waiting to repeat traffic
        restart waiting message."
    ::= { cItpSpLinksetTableEntry 61 }

cItpSpLinksetMtp3T27 OBJECT-TYPE
    SYNTAX CItpTcTimerMtp3T27
--    Rsyntax Gauge(0|2000..50000)
--  Units
--    milliseconds
    ACCESS read-write
    STATUS mandatory
    DESCRIPTION
        "Minimum duration of unavailability for full restart."
    ::= { cItpSpLinksetTableEntry 62 }

cItpSpLinksetMtp3T28 OBJECT-TYPE
    SYNTAX CItpTcTimerMtp3T28
--    Rsyntax Gauge(0|3000..35000)
--  Units
--    milliseconds
    ACCESS read-write
    STATUS mandatory
    DESCRIPTION
        "Timer at SP adjacent to restarting SP waiting for
        traffic restart waiting message."
    ::= { cItpSpLinksetTableEntry 63 }

cItpSpLinksetMtp3T29 OBJECT-TYPE
    SYNTAX CItpTcTimerMtp3T29
--    Rsyntax Gauge(0|60000..65000)
--  Units
--    milliseconds
    ACCESS read-write
    STATUS mandatory
    DESCRIPTION
        "Timer started when TRA sent in response to unexpected
        TRA or TRW."
    ::= { cItpSpLinksetTableEntry 64 }

cItpSpLinksetMtp3T30 OBJECT-TYPE
    SYNTAX CItpTcTimerMtp3T30
--    Rsyntax Gauge(0|30000..35000)
--  Units
--    milliseconds
    ACCESS read-write
    STATUS mandatory
    DESCRIPTION
        "Timer to limit sending of TFPs and TFRs in response
        to unexpected TRA or TRW."
    ::= { cItpSpLinksetTableEntry 65 }

cItpSpLinksetMtp3T31 OBJECT-TYPE
    SYNTAX CItpTcTimerMtp3T31
--    Rsyntax Gauge(0|10000..120000)
--  Units
--    milliseconds
    ACCESS read-write
    STATUS mandatory
    DESCRIPTION
        "False link congestion detection timer."
    ::= { cItpSpLinksetTableEntry 66 }

cItpSpLinksetMtp3T32 OBJECT-TYPE
    SYNTAX CItpTcTimerMtp3T32
--    Rsyntax Gauge(0|5000..120000)
--  Units
--    milliseconds
    ACCESS read-write
    STATUS mandatory
    DESCRIPTION
        "Link oscillation timer - Procedure A."
    ::= { cItpSpLinksetTableEntry 67 }

cItpSpLinksetMtp3T33 OBJECT-TYPE
    SYNTAX CItpTcTimerMtp3T33
--    Rsyntax Gauge(0|60000..600000)
--  Units
--    milliseconds
    ACCESS read-write
    STATUS mandatory
    DESCRIPTION
        "Probation timer for link oscillation - Procedure B."
    ::= { cItpSpLinksetTableEntry 68 }

cItpSpLinksetMtp3T34 OBJECT-TYPE
    SYNTAX CItpTcTimerMtp3T34
--    Rsyntax Gauge(0|5000..120000)
--  Units
--    milliseconds
    ACCESS read-write
    STATUS mandatory
    DESCRIPTION
        "Suspension timer for link oscillation - Procedure B."
    ::= { cItpSpLinksetTableEntry 69 }

cItpSpLinksetTimerLinkTest OBJECT-TYPE
    SYNTAX CItpTcTimerLinkTest
--    Rsyntax Gauge(0|4000..12000)
--  Units
--    milliseconds
    ACCESS read-write
    STATUS mandatory
    DESCRIPTION
        "Signalling Link test acknowledgement timer."
    ::= { cItpSpLinksetTableEntry 70 }

cItpSpLinksetTimerLinkMessage OBJECT-TYPE
    SYNTAX CItpTcTimerLinkMessage
--    Rsyntax Gauge(0|30000..90000)
--  Units
--    milliseconds
    ACCESS read-write
    STATUS mandatory
    DESCRIPTION
        "Interval timer for sending test messages."
    ::= { cItpSpLinksetTableEntry 71 }

cItpSpLinksetTimerLinkActRetry OBJECT-TYPE
    SYNTAX CItpTcTimerLinkActRetry
--    Rsyntax Gauge(0|60000..90000)
--  Units
--    milliseconds
    ACCESS read-write
    STATUS mandatory
    DESCRIPTION
        "Link activation retry timer."
    ::= { cItpSpLinksetTableEntry 72 }

cItpSpLinksetPlanCapacity OBJECT-TYPE
    SYNTAX INTEGER(0|56000..2147483647)
--  Units
--    bps
    ACCESS read-write
    STATUS deprecated
    DESCRIPTION
        "An estimate of the number of bits per second that is
         expected to be transmitted over a linkset.  This 
         attribute will be used by network management stations
         to generate traps and maintain statistics on linksets
         based on Stream Control Transmission Protocol. 
         The information for this attribute is specified via 
         CLI by the system administrator. A value of zero 
         for this object indicates that a planning capacity
         has not been specified. 
         
         This objects has been deprecated and replaced by 
         cItpSpLinkPlanCapacityRcvd and 
         cItpSpLinkPlanCapacitySent objects.
         "
    ::= { cItpSpLinksetTableEntry 73 }

cItpSpLinksetActPriority OBJECT-TYPE
    SYNTAX Gauge(0..255)
    ACCESS read-write
    STATUS mandatory
    DESCRIPTION
        "Defines the activation priority for linksets. Each 
         linkset can be defined a priority. The linkset with
         the lowest values will be activated first.  If two 
         linksets share the same values they will be 
         activated in the order they were defined."
    ::= { cItpSpLinksetTableEntry 74 }

cItpSpLinksetType OBJECT-TYPE
    SYNTAX INTEGER {
        access(1),
        bridge(2),
        cross(3),
        diagonal(4),
        fullyAssoc(5)
        }
    ACCESS read-write
    STATUS mandatory
    DESCRIPTION
        "The list of possible Signalling link types.  All links
         in the same linkset will be of the same type.
        'A-link'     : Access link
        'B-link'     : Bridge link
        'C-link'     : Cross link
        'D-link'     : Diagonal link
        'E-link'     : Fully associated link"
    ::= { cItpSpLinksetTableEntry 75 }

cItpSpLinksetRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpSpLinksetTable  
         following the RowStatus textual convention."
    ::= { cItpSpLinksetTableEntry 76 }

cItpSpLinksetNi OBJECT-TYPE
    SYNTAX CItpTcNetworkIndicator
--    Rsyntax INTEGER {
--        ?? enum value of zero may cause problems
--        international(0),
--        internationatSpare(1),
--        national(2),
--        nationalSpare(3)
--        }
    ACCESS read-write
    STATUS mandatory
    DESCRIPTION
        "The Network Indicator in which the Linkset resides."
    ::= { cItpSpLinksetTableEntry 77 }

cItpSpLinksetDisplayName OBJECT-TYPE
    SYNTAX SnmpAdminString(SIZE(0..30))
--    Rsyntax OCTET STRING(SIZE(0..30))
    ACCESS read-write
    STATUS mandatory
    DESCRIPTION
        "A short identifier for each linkset.
         This value can be set by system administrator
         or defaults to the linkset name."
    ::= { cItpSpLinksetTableEntry 78 }

cItpSpLinksetDescription OBJECT-TYPE
    SYNTAX SnmpAdminString(SIZE(0..254))
--    Rsyntax OCTET STRING(SIZE(0..254))
    ACCESS read-write
    STATUS mandatory
    DESCRIPTION
        "A textual description for the Signalling point."
    ::= { cItpSpLinksetTableEntry 79 }

cItpSpLinksetVariant OBJECT-TYPE
    SYNTAX CItpTcSs7Variant
--    Rsyntax INTEGER {
--        ansi(1),
--        itu(2),
--        china(3)
--        }
    ACCESS read-write
    STATUS mandatory
    DESCRIPTION
        "The SS7 variant used to format data transmitted 
         on this linkset."
    ::= { cItpSpLinksetTableEntry 80 }

cItpSpLinkTable OBJECT-TYPE
    SYNTAX SEQUENCE OF CItpSpLinkTableEntry
    ACCESS not-accessible
    STATUS mandatory
    DESCRIPTION
        "A table of SP links for this SP."
    ::= { cItpSpLink 1 }

cItpSpLinkTableEntry OBJECT-TYPE
    SYNTAX CItpSpLinkTableEntry
    ACCESS not-accessible
    STATUS mandatory
    DESCRIPTION
        "A list of SP link attributes."
    INDEX { cItpSpLinksetName, cItpSpLinkSlc }
    ::= { cItpSpLinkTable 1 }

CItpSpLinkTableEntry ::= SEQUENCE {
    cItpSpLinkSlc CItpTcLinkSLC,
    cItpSpLinkDescription SnmpAdminString,
    cItpSpLinkState INTEGER,
    cItpSpLinkType CItpTcLinkType,
    cItpSpLinkifIndex InterfaceIndexOrZero,
    cItpSpLinkSctpAssociation INTEGER,
    cItpSpLinkMtp3PacketsRcvd Counter,
    cItpSpLinkMtp3PacketsSent Counter,
    cItpSpLinkMtp3BytesRcvd Counter,
    cItpSpLinkMtp3BytesSent Counter,
    cItpSpLinkMtp2T01 CItpTcTimerMtp2T01,
    cItpSpLinkMtp2T02 CItpTcTimerMtp2T02,
    cItpSpLinkMtp2T03 CItpTcTimerMtp2T03,
    cItpSpLinkMtp2T04E CItpTcTimerMtp2T04E,
    cItpSpLinkMtp2T04N CItpTcTimerMtp2T04N,
    cItpSpLinkMtp2T05 CItpTcTimerMtp2T05,
    cItpSpLinkMtp2T06 CItpTcTimerMtp2T06,
    cItpSpLinkMtp2T07 CItpTcTimerMtp2T07,
    cItpSpLinkMtp3T01 CItpTcTimerMtp3T01,
    cItpSpLinkMtp3T02 CItpTcTimerMtp3T02,
    cItpSpLinkMtp3T03 CItpTcTimerMtp3T03,
    cItpSpLinkMtp3T04 CItpTcTimerMtp3T04,
    cItpSpLinkMtp3T05 CItpTcTimerMtp3T05,
    cItpSpLinkMtp3T06 CItpTcTimerMtp3T06,
    cItpSpLinkMtp3T07 CItpTcTimerMtp3T07,
    cItpSpLinkMtp3T08 CItpTcTimerMtp3T08,
    cItpSpLinkMtp3T10 CItpTcTimerMtp3T10,
    cItpSpLinkMtp3T11 CItpTcTimerMtp3T11,
    cItpSpLinkMtp3T12 CItpTcTimerMtp3T12,
    cItpSpLinkMtp3T13 CItpTcTimerMtp3T13,
    cItpSpLinkMtp3T14 CItpTcTimerMtp3T14,
    cItpSpLinkMtp3T15 CItpTcTimerMtp3T15,
    cItpSpLinkMtp3T16 CItpTcTimerMtp3T16,
    cItpSpLinkMtp3T17 CItpTcTimerMtp3T17,
    cItpSpLinkMtp3T18 CItpTcTimerMtp3T18,
    cItpSpLinkMtp3T19 CItpTcTimerMtp3T19,
    cItpSpLinkMtp3T20 CItpTcTimerMtp3T20,
    cItpSpLinkMtp3T21 CItpTcTimerMtp3T21,
    cItpSpLinkMtp3T22 CItpTcTimerMtp3T22,
    cItpSpLinkMtp3T23 CItpTcTimerMtp3T23,
    cItpSpLinkMtp3T24 CItpTcTimerMtp3T24,
    cItpSpLinkMtp3T25 CItpTcTimerMtp3T25,
    cItpSpLinkMtp3T26 CItpTcTimerMtp3T26,
    cItpSpLinkMtp3T27 CItpTcTimerMtp3T27,
    cItpSpLinkMtp3T28 CItpTcTimerMtp3T28,
    cItpSpLinkMtp3T29 CItpTcTimerMtp3T29,
    cItpSpLinkMtp3T30 CItpTcTimerMtp3T30,
    cItpSpLinkMtp3T31 CItpTcTimerMtp3T31,
    cItpSpLinkMtp3T32 CItpTcTimerMtp3T32,
    cItpSpLinkMtp3T33 CItpTcTimerMtp3T33,
    cItpSpLinkMtp3T34 CItpTcTimerMtp3T34,
    cItpSpLinkTimerLinkTest CItpTcTimerLinkTest,
    cItpSpLinkTimerLinkMessage CItpTcTimerLinkMessage,
    cItpSpLinkTimerLinkActRetry CItpTcTimerLinkActRetry,
    cItpSpLinkXmitQueueDepth Gauge,
    cItpSpLinkXmitQueueDepthHigh Gauge,
    cItpSpLinkXmitQueueDepthHighRT TimeStamp,
    cItpSpLinkCongestionState Gauge,
    cItpSpLinkCongestionAbate1 Gauge,
    cItpSpLinkCongestionAbate2 Gauge,
    cItpSpLinkCongestionAbate3 Gauge,
    cItpSpLinkCongestionOnset1 Gauge,
    cItpSpLinkCongestionOnset2 Gauge,
    cItpSpLinkCongestionOnset3 Gauge,
    cItpSpLinkSigLinkTest TruthValue,
    cItpSpLinkQ752T1E1 TimeTicks,
    cItpSpLinkQ752T1E2 Counter,
    cItpSpLinkQ752T1E3 Counter,
    cItpSpLinkQ752T1E4 Counter,
    cItpSpLinkQ752T1E5 Counter,
    cItpSpLinkQ752T1E6 Counter,
    cItpSpLinkQ752T1E7 Counter,
    cItpSpLinkQ752T1E8 Counter,
    cItpSpLinkQ752T1E9 Counter,
    cItpSpLinkQ752T1E10 Counter,
    cItpSpLinkQ752T1E11 Counter,
    cItpSpLinkQ752T2E1 TimeTicks,
    cItpSpLinkQ752T2E5 TimeTicks,
    cItpSpLinkQ752T2E6 TimeTicks,
    cItpSpLinkQ752T2E7 TimeTicks,
    cItpSpLinkQ752T2E9 TimeTicks,
    cItpSpLinkQ752T2E10 Counter,
    cItpSpLinkQ752T2E15 TimeTicks,
    cItpSpLinkQ752T2E16 Counter,
    cItpSpLinkQ752T2E18 Counter,
    cItpSpLinkMtp3PacketsRetrans Counter,
    cItpSpLinkMtp3BytesRetrans Counter,
    cItpSpLinkQ752T3E6 Counter,
    cItpSpLinkQ752T3E7 TimeTicks,
    cItpSpLinkQ752T3E10L1 Counter,
    cItpSpLinkQ752T3E10L2 Counter,
    cItpSpLinkQ752T3E10L3 Counter,
    cItpSpLinkQ752T3E11L1 Counter,
    cItpSpLinkQ752T3E11L2 Counter,
    cItpSpLinkQ752T3E11L3 Counter,
    cItpSpLinkIPType1 InetAddressType,
    cItpSpLinkIPType2 InetAddressType,
    cItpSpLinkIPType3 InetAddressType,
    cItpSpLinkIPType4 InetAddressType,
    cItpSpLinkIPAddr1 InetAddress,
    cItpSpLinkIPAddr2 InetAddress,
    cItpSpLinkIPAddr3 InetAddress,
    cItpSpLinkIPAddr4 InetAddress,
    cItpSpLinkLocalPort Gauge,
    cItpSpLinkRemotePort Gauge,
    cItpSpLinkQosClass CItpTcQos,
    cItpSpLinkRowStatus RowStatus,
    cItpSpLinkStateReason OCTET STRING,
    cItpSpLinkDisplayName SnmpAdminString,
    cItpSpLinkDroppedPkts Counter,
    cItpSpLinkTransmittedLssu Counter,
    cItpSpLinkReceivedLssu Counter,
    cItpSpLinkProtocolDetails OCTET STRING,
    cItpSpLinkLsacState INTEGER,
    cItpSpLinkTsrcState INTEGER,
    cItpSpLinkTcocState INTEGER,
    cItpSpLinkTcocLocalBSNT CItpSpSequenceNumber,
    cItpSpLinkTcocRemoteBSNT CItpSpSequenceNumber,
    cItpSpLinkTcbcState INTEGER,
    cItpSpLinkReceivedSIB Counter,
    cItpSpLinkTransmittedSIB Counter,
    cItpSpLinkMtp2ExpiredT01 Counter,
    cItpSpLinkMtp2ExpiredT02 Counter,
    cItpSpLinkMtp2ExpiredT03 Counter,
    cItpSpLinkMtp2ExpiredT04 Counter,
    cItpSpLinkMtp2ExpiredT05 Counter,
    cItpSpLinkMtp2ExpiredT06 Counter,
    cItpSpLinkMtp2ExpiredT07 Counter,
    cItpSpLinkOMAERMCount Counter,
    cItpSpLinkOMAERMFailCount Counter,
    cItpSpLinkOMSURMCount Counter,
    cItpSpLinkOMSURMFailCount Counter,
    cItpSpLinkPlanCapacityRcvd CItpSpLinkCapacity,
    cItpSpLinkUtilThresholdRcvd CItpSpPercentThreshold,
    cItpSpLinkUtilizationRcvd CItpSpLinkUtilization,
    cItpSpLinkUtilStateRcvd CItpSpLinkUtilizationState,
    cItpSpLinkL2BytesRcvd Counter,
    cItpSpLinkPlanCapacitySent CItpSpLinkCapacity,
    cItpSpLinkUtilThresholdSent CItpSpPercentThreshold,
    cItpSpLinkUtilizationSent CItpSpLinkUtilization,
    cItpSpLinkUtilStateSent CItpSpLinkUtilizationState,
    cItpSpLinkL2BytesSent Counter
    }

cItpSpLinkSlc OBJECT-TYPE
    SYNTAX CItpTcLinkSLC
--    Rsyntax Gauge(0..15)
    ACCESS not-accessible
    STATUS mandatory
    DESCRIPTION
        "The Signalling Link Code for this link."
    REFERENCE
        "ITU Q.704 Signalling network functions and messages.
        ANSI T1.111 Telecommunications - Signalling system
        No. 7 (SS7)-Message Transfer Part (MTP)."
    ::= { cItpSpLinkTableEntry 1 }

cItpSpLinkDescription OBJECT-TYPE
    SYNTAX SnmpAdminString(SIZE(0..254))
--    Rsyntax OCTET STRING(SIZE(0..254))
    ACCESS read-write
    STATUS mandatory
    DESCRIPTION
        "A textual description for this link."
    ::= { cItpSpLinkTableEntry 2 }

cItpSpLinkState OBJECT-TYPE
    SYNTAX INTEGER {
        available(1),
        failed(2),
        shutdown(3),
        unavailable(4)
        }
    ACCESS read-only
    STATUS mandatory
    DESCRIPTION
        "The list of possible links states.
         'available'  : Traffic may flow over this linkset
         'failed'     : Traffic management has detected a failure
                        that prevents activating this linkset. 
         'shutdown'   : This linkset has been forced to an
                        unavailable state by an administrative
                        action.
         'unavailable': The linkset is currently unable to support
                        traffic. Activation of this linkset will 
                        occur as required by protocol."
    ::= { cItpSpLinkTableEntry 3 }

cItpSpLinkType OBJECT-TYPE
    SYNTAX CItpTcLinkType
--    Rsyntax INTEGER {
--        other(1),
--        serial(2),
--        sctpIp(3),
--        hsl(4)
--        }
    ACCESS read-write
    STATUS mandatory
    DESCRIPTION
        "The link type."
    REFERENCE
        "For SCTP see RFC 2960."
    ::= { cItpSpLinkTableEntry 4 }

cItpSpLinkifIndex OBJECT-TYPE
    SYNTAX InterfaceIndexOrZero
--    Rsyntax INTEGER(0..2147483647)
    ACCESS read-write
    STATUS mandatory
    DESCRIPTION
        "If the link type specified by cItpSpLinkType is serial 
         or hsl, this is the ifIndex specified in IF-MIB, 
         otherwise no significance is to be placed on this value."
    REFERENCE
        "RFC1213.txt"
    ::= { cItpSpLinkTableEntry 5 }

cItpSpLinkSctpAssociation OBJECT-TYPE
    SYNTAX INTEGER(0..65535)
    ACCESS read-only
    STATUS mandatory
    DESCRIPTION
        "If the link type specified by cItpSpLinkType is 'sctpIp',
         this is the association identifier defined in the  
         Stream Control Transmission Protocol(SCTP) MIB.
         Where value greater than zero indicates
         a valid association and zero one indicates an 
         invalid association. This value will always be set to 
         zero one when cItpSpLinkType is not equal to the 
         'sctpIp' value."
    ::= { cItpSpLinkTableEntry 6 }

cItpSpLinkMtp3PacketsRcvd OBJECT-TYPE
    SYNTAX Counter
--  Units
--    packets
    ACCESS read-only
    STATUS mandatory
    DESCRIPTION
        "The number of MTP3 packets received by this link.
        This measurement is specified in Q752/3.5"
    ::= { cItpSpLinkTableEntry 7 }

cItpSpLinkMtp3PacketsSent OBJECT-TYPE
    SYNTAX Counter
--  Units
--    packets
    ACCESS read-only
    STATUS mandatory
    DESCRIPTION
        "The number of MTP3 packets sent by this link.
        This measurement is specified in Q752/3.3"
    ::= { cItpSpLinkTableEntry 8 }

cItpSpLinkMtp3BytesRcvd OBJECT-TYPE
    SYNTAX Counter
--  Units
--    bytes
    ACCESS read-only
    STATUS mandatory
    DESCRIPTION
        "The number of MTP3 bytes received by this link.
         This measurement is specified in Q752/3.4"
    ::= { cItpSpLinkTableEntry 9 }

cItpSpLinkMtp3BytesSent OBJECT-TYPE
    SYNTAX Counter
--  Units
--    bytes
    ACCESS read-only
    STATUS mandatory
    DESCRIPTION
        "The number of MTP3 bytes sent by this link.
         This measurement is specified in Q752/3.1"
    ::= { cItpSpLinkTableEntry 10 }

cItpSpLinkMtp2T01 OBJECT-TYPE
    SYNTAX CItpTcTimerMtp2T01
--    Rsyntax Gauge(5000..150000)
--  Units
--    milliseconds
    ACCESS read-write
    STATUS mandatory
    DESCRIPTION
        "Alignment ready timer."
    ::= { cItpSpLinkTableEntry 11 }

cItpSpLinkMtp2T02 OBJECT-TYPE
    SYNTAX CItpTcTimerMtp2T02
--    Rsyntax Gauge(0|5000..150000)
--  Units
--    milliseconds
    ACCESS read-write
    STATUS mandatory
    DESCRIPTION
        "Not aligned timer."
    ::= { cItpSpLinkTableEntry 12 }

cItpSpLinkMtp2T03 OBJECT-TYPE
    SYNTAX CItpTcTimerMtp2T03
--    Rsyntax Gauge(0|1000..14000)
--  Units
--    milliseconds
    ACCESS read-write
    STATUS mandatory
    DESCRIPTION
        "Aligned timer."
    ::= { cItpSpLinkTableEntry 13 }

cItpSpLinkMtp2T04E OBJECT-TYPE
    SYNTAX CItpTcTimerMtp2T04E
--    Rsyntax Gauge(0|400..660)
--  Units
--    milliseconds
    ACCESS read-write
    STATUS mandatory
    DESCRIPTION
        "Proving period timer emergency timer. "
    ::= { cItpSpLinkTableEntry 14 }

cItpSpLinkMtp2T04N OBJECT-TYPE
    SYNTAX CItpTcTimerMtp2T04N
--    Rsyntax Gauge(0|2007..9500)
--  Units
--    milliseconds
    ACCESS read-write
    STATUS mandatory
    DESCRIPTION
        "Proving period timer normal timer."
    ::= { cItpSpLinkTableEntry 15 }

cItpSpLinkMtp2T05 OBJECT-TYPE
    SYNTAX CItpTcTimerMtp2T05
--    Rsyntax Gauge(0|80..120)
--  Units
--    milliseconds
    ACCESS read-write
    STATUS mandatory
    DESCRIPTION
        "Sending SIB timer."
    ::= { cItpSpLinkTableEntry 16 }

cItpSpLinkMtp2T06 OBJECT-TYPE
    SYNTAX CItpTcTimerMtp2T06
--    Rsyntax Gauge(1000..6000)
--  Units
--    milliseconds
    ACCESS read-write
    STATUS mandatory
    DESCRIPTION
        "Remote congestion timer. "
    ::= { cItpSpLinkTableEntry 17 }

cItpSpLinkMtp2T07 OBJECT-TYPE
    SYNTAX CItpTcTimerMtp2T07
--    Rsyntax Gauge(0|100..6000)
--  Units
--    milliseconds
    ACCESS read-write
    STATUS mandatory
    DESCRIPTION
        "Excessive delay of acknowledgement timer."
    ::= { cItpSpLinkTableEntry 18 }

cItpSpLinkMtp3T01 OBJECT-TYPE
    SYNTAX CItpTcTimerMtp3T01
--    Rsyntax Gauge(500..1200)
--  Units
--    milliseconds
    ACCESS read-write
    STATUS mandatory
    DESCRIPTION
        "Delay to avoid message mis-sequencing on changeover."
    ::= { cItpSpLinkTableEntry 19 }

cItpSpLinkMtp3T02 OBJECT-TYPE
    SYNTAX CItpTcTimerMtp3T02
--    Rsyntax Gauge(700..2000)
--  Units
--    milliseconds
    ACCESS read-write
    STATUS mandatory
    DESCRIPTION
        "Waiting for changeover acknowledgement."
    ::= { cItpSpLinkTableEntry 20 }

cItpSpLinkMtp3T03 OBJECT-TYPE
    SYNTAX CItpTcTimerMtp3T03
--    Rsyntax Gauge(500..1200)
--  Units
--    milliseconds
    ACCESS read-write
    STATUS mandatory
    DESCRIPTION
        "Time controlled diversion-delay to avoid
        mis-sequencing on change back."
    ::= { cItpSpLinkTableEntry 21 }

cItpSpLinkMtp3T04 OBJECT-TYPE
    SYNTAX CItpTcTimerMtp3T04
--    Rsyntax Gauge(500..1200)
--  Units
--    milliseconds
    ACCESS read-write
    STATUS mandatory
    DESCRIPTION
        "Waiting for change back acknowledgement (first
        attempt)."
    ::= { cItpSpLinkTableEntry 22 }

cItpSpLinkMtp3T05 OBJECT-TYPE
    SYNTAX CItpTcTimerMtp3T05
--    Rsyntax Gauge(500..1200)
--  Units
--    milliseconds
    ACCESS read-write
    STATUS mandatory
    DESCRIPTION
        "Waiting for change back acknowledgement (second
         attempt)."
    ::= { cItpSpLinkTableEntry 23 }

cItpSpLinkMtp3T06 OBJECT-TYPE
    SYNTAX CItpTcTimerMtp3T06
--    Rsyntax Gauge(500..1200)
--  Units
--    milliseconds
    ACCESS read-write
    STATUS mandatory
    DESCRIPTION
        "Delay to avoid message mis-sequencing on controlled
         rerouting."
    ::= { cItpSpLinkTableEntry 24 }

cItpSpLinkMtp3T07 OBJECT-TYPE
    SYNTAX CItpTcTimerMtp3T07
--    Rsyntax Gauge(0|1000..2000)
--  Units
--    milliseconds
    ACCESS read-write
    STATUS mandatory
    DESCRIPTION
        "Waiting for Signalling data link connection
         acknowledgement."
    ::= { cItpSpLinkTableEntry 25 }

cItpSpLinkMtp3T08 OBJECT-TYPE
    SYNTAX CItpTcTimerMtp3T08
--    Rsyntax Gauge(800..1200)
--  Units
--    milliseconds
    ACCESS read-write
    STATUS mandatory
    DESCRIPTION
        "Transfer prohibited inhibition timer (transient
         solution)."
    ::= { cItpSpLinkTableEntry 26 }

cItpSpLinkMtp3T10 OBJECT-TYPE
    SYNTAX CItpTcTimerMtp3T10
--    Rsyntax Gauge(30000..60000)
--  Units
--    milliseconds
    ACCESS read-write
    STATUS mandatory
    DESCRIPTION
        "Waiting to repeat Signalling routeset test message."
    ::= { cItpSpLinkTableEntry 27 }

cItpSpLinkMtp3T11 OBJECT-TYPE
    SYNTAX CItpTcTimerMtp3T11
--    Rsyntax Gauge(30000..90000)
--  Units
--    milliseconds
    ACCESS read-write
    STATUS mandatory
    DESCRIPTION
        "Transfer restricted timer. (This is one way of
        implementing the function described in 13.4/Q.704 and
        mainly intended to simplify SPs.)."
    ::= { cItpSpLinkTableEntry 28 }

cItpSpLinkMtp3T12 OBJECT-TYPE
    SYNTAX CItpTcTimerMtp3T12
--    Rsyntax Gauge(800..1500)
--  Units
--    milliseconds
    ACCESS read-write
    STATUS mandatory
    DESCRIPTION
        "Waiting for uninhibit acknowledgement."
    ::= { cItpSpLinkTableEntry 29 }

cItpSpLinkMtp3T13 OBJECT-TYPE
    SYNTAX CItpTcTimerMtp3T13
--    Rsyntax Gauge(800..1500)
--  Units
--    milliseconds
    ACCESS read-write
    STATUS mandatory
    DESCRIPTION
        "Waiting for force uninhibit."
    ::= { cItpSpLinkTableEntry 30 }

cItpSpLinkMtp3T14 OBJECT-TYPE
    SYNTAX CItpTcTimerMtp3T14
--    Rsyntax Gauge(2000..3000)
--  Units
--    milliseconds
    ACCESS read-write
    STATUS mandatory
    DESCRIPTION
        "Waiting for inhibition acknowledgement."
    ::= { cItpSpLinkTableEntry 31 }

cItpSpLinkMtp3T15 OBJECT-TYPE
    SYNTAX CItpTcTimerMtp3T15
--    Rsyntax Gauge(2000..3000)
--  Units
--    milliseconds
    ACCESS read-write
    STATUS mandatory
    DESCRIPTION
        "Waiting to start Signalling routeset congestion
         test."
    ::= { cItpSpLinkTableEntry 32 }

cItpSpLinkMtp3T16 OBJECT-TYPE
    SYNTAX CItpTcTimerMtp3T16
--    Rsyntax Gauge(1400..2000)
--  Units
--    milliseconds
    ACCESS read-write
    STATUS mandatory
    DESCRIPTION
        "Waiting for routeset congestion status update."
    ::= { cItpSpLinkTableEntry 33 }

cItpSpLinkMtp3T17 OBJECT-TYPE
    SYNTAX CItpTcTimerMtp3T17
--    Rsyntax Gauge(800..1500)
--  Units
--    milliseconds
    ACCESS read-write
    STATUS mandatory
    DESCRIPTION
        "Delay to avoid oscillation of initial alignment
        failure and link restart."
    ::= { cItpSpLinkTableEntry 34 }

cItpSpLinkMtp3T18 OBJECT-TYPE
    SYNTAX CItpTcTimerMtp3T18
--    Rsyntax Gauge(1000..31000)
--  Units
--    milliseconds
    ACCESS read-write
    STATUS mandatory
    DESCRIPTION
        "This timers servers different function based on the 
         variant.
         
         ANSI: Repeat TFR once by response method
         ITU:  MTP restart link supervision"
    ::= { cItpSpLinkTableEntry 35 }

cItpSpLinkMtp3T19 OBJECT-TYPE
    SYNTAX CItpTcTimerMtp3T19
--    Rsyntax Gauge(67000..600000)
--  Units
--    milliseconds
    ACCESS read-write
    STATUS mandatory
    DESCRIPTION
        "This timers servers different function based on the 
         variant.
         
         ANSI: failed craft timer referral timer
         ITU:  supervision timer during MTP restart"
    ::= { cItpSpLinkTableEntry 36 }

cItpSpLinkMtp3T20 OBJECT-TYPE
    SYNTAX CItpTcTimerMtp3T20
--    Rsyntax Gauge(1000..120000)
--  Units
--    milliseconds
    ACCESS read-write
    STATUS mandatory
    DESCRIPTION
        "This timers servers different function based on the 
         variant.
         
         ANSI: waiting to repeat local inhibit test
         ITU:  MTP restart timer at the Signalling point"
    ::= { cItpSpLinkTableEntry 37 }

cItpSpLinkMtp3T21 OBJECT-TYPE
    SYNTAX CItpTcTimerMtp3T21
--    Rsyntax Gauge(63000..120000)
--  Units
--    milliseconds
    ACCESS read-write
    STATUS mandatory
    DESCRIPTION
        "This timers servers different function based on the 
         variant.
         
         ANSI: waiting to repeat remote inhibit test)       
         ITU:  MTP restart timer at adjacent Signalling point"
    ::= { cItpSpLinkTableEntry 38 }

cItpSpLinkMtp3T22 OBJECT-TYPE
    SYNTAX CItpTcTimerMtp3T22
--    Rsyntax Gauge(36000..360000)
--  Units
--    milliseconds
    ACCESS read-write
    STATUS mandatory
    DESCRIPTION
        "This timers servers different function based on the 
         variant.
         
         ANSI: restarting SP waiting for Signalling links avail
         ITU:  local inhibit test timer"
    ::= { cItpSpLinkTableEntry 39 }

cItpSpLinkMtp3T23 OBJECT-TYPE
    SYNTAX CItpTcTimerMtp3T23
--    Rsyntax Gauge(9000..360000)
--  Units
--    milliseconds
    ACCESS read-write
    STATUS mandatory
    DESCRIPTION
        "This timers servers different function based on the 
         variant.
         
         ANSI: restarting SP waiting to receive all TRA msgs
         ITU:  remote inhibit test timer"
    ::= { cItpSpLinkTableEntry 40 }

cItpSpLinkMtp3T24 OBJECT-TYPE
    SYNTAX CItpTcTimerMtp3T24
--    Rsyntax Gauge(500..60000)
--  Units
--    milliseconds
    ACCESS read-write
    STATUS mandatory
    DESCRIPTION
        "This timers servers different function based on the 
         variant.
         
         ANSI: restarting SP waiting to broadcast all TRA msgs
         ITU:  stabilizing timer after local processor outage"
    ::= { cItpSpLinkTableEntry 41 }

cItpSpLinkMtp3T25 OBJECT-TYPE
    SYNTAX CItpTcTimerMtp3T25
--    Rsyntax Gauge(0|30000..35000)
--  Units
--    milliseconds
    ACCESS read-write
    STATUS mandatory
    DESCRIPTION
        "Timer at Signalling Point (SP) adjacent to restarting
        SP, waiting for traffic restart allowed message."
    ::= { cItpSpLinkTableEntry 42 }

cItpSpLinkMtp3T26 OBJECT-TYPE
    SYNTAX CItpTcTimerMtp3T26
--    Rsyntax Gauge(0|12000..15000)
--  Units
--    milliseconds
    ACCESS read-write
    STATUS mandatory
    DESCRIPTION
        "Timer at restarting SP waiting to repeat traffic
        restart waiting message."
    ::= { cItpSpLinkTableEntry 43 }

cItpSpLinkMtp3T27 OBJECT-TYPE
    SYNTAX CItpTcTimerMtp3T27
--    Rsyntax Gauge(0|2000..50000)
--  Units
--    milliseconds
    ACCESS read-write
    STATUS mandatory
    DESCRIPTION
        "Minimum duration of unavailability for full restart."
    ::= { cItpSpLinkTableEntry 44 }

cItpSpLinkMtp3T28 OBJECT-TYPE
    SYNTAX CItpTcTimerMtp3T28
--    Rsyntax Gauge(0|3000..35000)
--  Units
--    milliseconds
    ACCESS read-write
    STATUS mandatory
    DESCRIPTION
        "Timer at SP adjacent to restarting SP waiting for
        traffic restart waiting message."
    ::= { cItpSpLinkTableEntry 45 }

cItpSpLinkMtp3T29 OBJECT-TYPE
    SYNTAX CItpTcTimerMtp3T29
--    Rsyntax Gauge(0|60000..65000)
--  Units
--    milliseconds
    ACCESS read-write
    STATUS mandatory
    DESCRIPTION
        "Timer started when TRA sent in response to unexpected
        TRA or TRW."
    ::= { cItpSpLinkTableEntry 46 }

cItpSpLinkMtp3T30 OBJECT-TYPE
    SYNTAX CItpTcTimerMtp3T30
--    Rsyntax Gauge(0|30000..35000)
--  Units
--    milliseconds
    ACCESS read-write
    STATUS mandatory
    DESCRIPTION
        "Timer to limit sending of TFPs and TFRs in response
        to unexpected TRA or TRW."
    ::= { cItpSpLinkTableEntry 47 }

cItpSpLinkMtp3T31 OBJECT-TYPE
    SYNTAX CItpTcTimerMtp3T31
--    Rsyntax Gauge(0|10000..120000)
--  Units
--    milliseconds
    ACCESS read-write
    STATUS mandatory
    DESCRIPTION
        "False link congestion detection timer."
    ::= { cItpSpLinkTableEntry 48 }

cItpSpLinkMtp3T32 OBJECT-TYPE
    SYNTAX CItpTcTimerMtp3T32
--    Rsyntax Gauge(0|5000..120000)
--  Units
--    milliseconds
    ACCESS read-write
    STATUS mandatory
    DESCRIPTION
        "Link oscillation timer - Procedure A."
    ::= { cItpSpLinkTableEntry 49 }

cItpSpLinkMtp3T33 OBJECT-TYPE
    SYNTAX CItpTcTimerMtp3T33
--    Rsyntax Gauge(0|60000..600000)
--  Units
--    milliseconds
    ACCESS read-write
    STATUS mandatory
    DESCRIPTION
        "Probation timer for link oscillation - Procedure B."
    ::= { cItpSpLinkTableEntry 50 }

cItpSpLinkMtp3T34 OBJECT-TYPE
    SYNTAX CItpTcTimerMtp3T34
--    Rsyntax Gauge(0|5000..120000)
--  Units
--    milliseconds
    ACCESS read-write
    STATUS mandatory
    DESCRIPTION
        "Suspension timer for link oscillation - Procedure B."
    ::= { cItpSpLinkTableEntry 51 }

cItpSpLinkTimerLinkTest OBJECT-TYPE
    SYNTAX CItpTcTimerLinkTest
--    Rsyntax Gauge(0|4000..12000)
--  Units
--    milliseconds
    ACCESS read-write
    STATUS mandatory
    DESCRIPTION
        "Signalling Link test acknowledgement timer."
    ::= { cItpSpLinkTableEntry 52 }

cItpSpLinkTimerLinkMessage OBJECT-TYPE
    SYNTAX CItpTcTimerLinkMessage
--    Rsyntax Gauge(0|30000..90000)
--  Units
--    milliseconds
    ACCESS read-write
    STATUS mandatory
    DESCRIPTION
        "Interval timer for sending test messages."
    ::= { cItpSpLinkTableEntry 53 }

cItpSpLinkTimerLinkActRetry OBJECT-TYPE
    SYNTAX CItpTcTimerLinkActRetry
--    Rsyntax Gauge(0|60000..90000)
--  Units
--    milliseconds
    ACCESS read-write
    STATUS mandatory
    DESCRIPTION
        "Link activation retry timer."
    ::= { cItpSpLinkTableEntry 54 }

cItpSpLinkXmitQueueDepth OBJECT-TYPE
    SYNTAX Gauge
    ACCESS read-only
    STATUS mandatory
    DESCRIPTION
        "Number of packets waiting to be sent over this link."
    ::= { cItpSpLinkTableEntry 55 }

cItpSpLinkXmitQueueDepthHigh OBJECT-TYPE
    SYNTAX Gauge
    ACCESS read-write
    STATUS mandatory
    DESCRIPTION
        "This is the maximum number of packets waiting
         to be sent over this link since the last time this
         value was reset as indicated by 
         cItpSpLinkXmitQueueDepthHighReset. 
         Resetting this object is achieved by setting this
         object to 0. Attempting to set this object to any
         other value will result in a wrongValue error."
    ::= { cItpSpLinkTableEntry 56 }

cItpSpLinkXmitQueueDepthHighRT OBJECT-TYPE
    SYNTAX TimeStamp
--    Rsyntax TimeTicks
    ACCESS read-only
    STATUS mandatory
    DESCRIPTION
        "This indicates when cItpSpLinkXmitQueueDepthHigh
        was set to 0."
    ::= { cItpSpLinkTableEntry 57 }

cItpSpLinkCongestionState OBJECT-TYPE
    SYNTAX Gauge(0..3)
    ACCESS read-only
    STATUS mandatory
    DESCRIPTION
        "The Signalling link congestion status of this link. 0
        is the least congestion level, 3 is the highest
        congestion level."
    REFERENCE
        "ITU Q.704 Signalling network functions and messages.
        ANSI T1.111 Telecommunications - Signalling system
        No. 7 (SS7)-Signalling network functions and messages
        2.3.5.2."
    ::= { cItpSpLinkTableEntry 58 }

cItpSpLinkCongestionAbate1 OBJECT-TYPE
    SYNTAX Gauge(0..65535)
    ACCESS read-write
    STATUS mandatory
    DESCRIPTION
        "Threshold used to abate congestion level 1."
    ::= { cItpSpLinkTableEntry 59 }

cItpSpLinkCongestionAbate2 OBJECT-TYPE
    SYNTAX Gauge(0..65535)
    ACCESS read-write
    STATUS mandatory
    DESCRIPTION
        "Threshold used to abate congestion level 2."
    ::= { cItpSpLinkTableEntry 60 }

cItpSpLinkCongestionAbate3 OBJECT-TYPE
    SYNTAX Gauge(0..65535)
    ACCESS read-write
    STATUS mandatory
    DESCRIPTION
        "Threshold used to abate congestion level 3."
    ::= { cItpSpLinkTableEntry 61 }

cItpSpLinkCongestionOnset1 OBJECT-TYPE
    SYNTAX Gauge(0..65535)
    ACCESS read-write
    STATUS mandatory
    DESCRIPTION
        "Threshold used to mark onset of congestion level 1."
    ::= { cItpSpLinkTableEntry 62 }

cItpSpLinkCongestionOnset2 OBJECT-TYPE
    SYNTAX Gauge(0..65535)
    ACCESS read-write
    STATUS mandatory
    DESCRIPTION
        "Threshold used to mark onset of congestion level 2."
    ::= { cItpSpLinkTableEntry 63 }

cItpSpLinkCongestionOnset3 OBJECT-TYPE
    SYNTAX Gauge(0..65535)
    ACCESS read-write
    STATUS mandatory
    DESCRIPTION
        "Threshold used to mark onset of congestion level 3."
    ::= { cItpSpLinkTableEntry 64 }

cItpSpLinkSigLinkTest OBJECT-TYPE
    SYNTAX TruthValue
--    Rsyntax INTEGER {
--        true(1),
--        false(2)
--        }
    ACCESS read-write
    STATUS mandatory
    DESCRIPTION
        "Indicated if Signalling link test is enabled on this
        link.
        
        true  : Signalling link test is enabled.
        false : Signalling link test not enabled."
    DEFVAL { true }
    ::= { cItpSpLinkTableEntry 65 }

cItpSpLinkQ752T1E1 OBJECT-TYPE
    SYNTAX TimeTicks
    ACCESS read-only
    STATUS mandatory
    DESCRIPTION
        "Duration of link in the In-Service state Q752/1.1."
    ::= { cItpSpLinkTableEntry 66 }

cItpSpLinkQ752T1E2 OBJECT-TYPE
    SYNTAX Counter
    ACCESS read-only
    STATUS mandatory
    DESCRIPTION
        "Count of Signalling Link failures - All reasons Q752/1.2."
    ::= { cItpSpLinkTableEntry 67 }

cItpSpLinkQ752T1E3 OBJECT-TYPE
    SYNTAX Counter
--  Units
--    occurrences
    ACCESS read-only
    STATUS mandatory
    DESCRIPTION
        "Count of Signalling Link failures - Abnormal FIBR/BSNR 
         Q752/1.4."
    ::= { cItpSpLinkTableEntry 68 }

cItpSpLinkQ752T1E4 OBJECT-TYPE
    SYNTAX Counter
--  Units
--    occurrences
    ACCESS read-only
    STATUS mandatory
    DESCRIPTION
        "Count of Signalling Link failures - Excessive delay of 
         acknowledgement Q752/1.4."
    ::= { cItpSpLinkTableEntry 69 }

cItpSpLinkQ752T1E5 OBJECT-TYPE
    SYNTAX Counter
--  Units
--    occurrences
    ACCESS read-only
    STATUS mandatory
    DESCRIPTION
        "Count of Signalling Link failures - Excessive error rate 
         Q752/1.5."
    ::= { cItpSpLinkTableEntry 70 }

cItpSpLinkQ752T1E6 OBJECT-TYPE
    SYNTAX Counter
--  Units
--    occurrences
    ACCESS read-only
    STATUS mandatory
    DESCRIPTION
        "Count of Signalling Link failures - Excessive duration 
         of congestion Q752/1.6."
    ::= { cItpSpLinkTableEntry 71 }

cItpSpLinkQ752T1E7 OBJECT-TYPE
    SYNTAX Counter
--  Units
--    occurrences
    ACCESS read-only
    STATUS mandatory
    DESCRIPTION
        "Count of alignment or proving errors Q752/1.7."
    ::= { cItpSpLinkTableEntry 72 }

cItpSpLinkQ752T1E8 OBJECT-TYPE
    SYNTAX Counter
--  Units
--    occurrences
    ACCESS read-only
    STATUS mandatory
    DESCRIPTION
        "Count of signal units received in error Q752/1.8."
    ::= { cItpSpLinkTableEntry 73 }

cItpSpLinkQ752T1E9 OBJECT-TYPE
    SYNTAX Counter
--  Units
--    negative acknowledgements
    ACCESS read-only
    STATUS mandatory
    DESCRIPTION
        "Count of negative acknowledgements received Q752/1.9."
    ::= { cItpSpLinkTableEntry 74 }

cItpSpLinkQ752T1E10 OBJECT-TYPE
    SYNTAX Counter
--  Units
--    occurrences
    ACCESS read-only
    STATUS mandatory
    DESCRIPTION
        "Count of 'local automatic changeover' events
            Q752/1.10."
    ::= { cItpSpLinkTableEntry 75 }

cItpSpLinkQ752T1E11 OBJECT-TYPE
    SYNTAX Counter
--  Units
--    occurrences
    ACCESS read-only
    STATUS mandatory
    DESCRIPTION
        "Count of 'local automatic changeback' events Q752/1.11."
    ::= { cItpSpLinkTableEntry 76 }

cItpSpLinkQ752T2E1 OBJECT-TYPE
    SYNTAX TimeTicks
    ACCESS read-only
    STATUS mandatory
    DESCRIPTION
        "Duration of Signalling Link unavailable(for any reason)
         Q752/2.1."
    ::= { cItpSpLinkTableEntry 77 }

cItpSpLinkQ752T2E5 OBJECT-TYPE
    SYNTAX TimeTicks
    ACCESS read-only
    STATUS mandatory
    DESCRIPTION
        "Duration of Signalling Link unavailable due to local 
         management actions Q752/2.5."
    ::= { cItpSpLinkTableEntry 78 }

cItpSpLinkQ752T2E6 OBJECT-TYPE
    SYNTAX TimeTicks
    ACCESS read-only
    STATUS mandatory
    DESCRIPTION
        "Duration of Signalling Link unavailable due to remote 
         management actions Q752/2.6."
    ::= { cItpSpLinkTableEntry 79 }

cItpSpLinkQ752T2E7 OBJECT-TYPE
    SYNTAX TimeTicks
    ACCESS read-only
    STATUS mandatory
    DESCRIPTION
        "Duration of Signalling Link unavailable due to link 
         failure Q752/2.7."
    ::= { cItpSpLinkTableEntry 80 }

cItpSpLinkQ752T2E9 OBJECT-TYPE
    SYNTAX TimeTicks
    ACCESS read-only
    STATUS mandatory
    DESCRIPTION
        "Duration of Signalling Link unavailable due to remote 
         processor outage Q752/2.9."
    ::= { cItpSpLinkTableEntry 81 }

cItpSpLinkQ752T2E10 OBJECT-TYPE
    SYNTAX Counter
--  Units
--    occurrences
    ACCESS read-only
    STATUS mandatory
    DESCRIPTION
        "Count of 'remote processor outage' events Q752/2.10 and
         Q752/2.11.  The standard only requires that events are
         issued.  The entries have been combined into a single 
         entry to track all occurrences of these event types."
    ::= { cItpSpLinkTableEntry 82 }

cItpSpLinkQ752T2E15 OBJECT-TYPE
    SYNTAX TimeTicks
    ACCESS read-only
    STATUS mandatory
    DESCRIPTION
        "Duration of local busy Q752/2.15."
    ::= { cItpSpLinkTableEntry 83 }

cItpSpLinkQ752T2E16 OBJECT-TYPE
    SYNTAX Counter
--  Units
--    occurrences
    ACCESS read-only
    STATUS mandatory
    DESCRIPTION
        "Count of local inhibition Q752/2.16 and Q752/2.17.
         The standard only requires that events are issued.
         The entries have been combined into a single 
         entry to track all occurrences of these event types."
    ::= { cItpSpLinkTableEntry 84 }

cItpSpLinkQ752T2E18 OBJECT-TYPE
    SYNTAX Counter
--  Units
--    occurrences
    ACCESS read-only
    STATUS mandatory
    DESCRIPTION
        "Count of remote inhibition Q752/2.18 and Q752/2.19.
         The standard only requires that events are issued.
         The entries have been combined into a single 
         entry to track all occurrences of these event types."
    ::= { cItpSpLinkTableEntry 85 }

cItpSpLinkMtp3PacketsRetrans OBJECT-TYPE
    SYNTAX Counter
--  Units
--    packets
    ACCESS read-only
    STATUS mandatory
    DESCRIPTION
        "The number of MTP3 packets retransmitted on this link.
         This measurement is specified in Q752/3.2"
    ::= { cItpSpLinkTableEntry 86 }

cItpSpLinkMtp3BytesRetrans OBJECT-TYPE
    SYNTAX Counter
--  Units
--    bytes
    ACCESS read-only
    STATUS mandatory
    DESCRIPTION
        "The number of MTP3 bytes retransmitted on this link.
         This measurement is specified in Q752/3.2"
    ::= { cItpSpLinkTableEntry 87 }

cItpSpLinkQ752T3E6 OBJECT-TYPE
    SYNTAX Counter
--  Units
--    events
    ACCESS read-only
    STATUS mandatory
    DESCRIPTION
        "The number times this Signalling link was marked
         congested. This measurement is specified in Q752/3.6"
    ::= { cItpSpLinkTableEntry 88 }

cItpSpLinkQ752T3E7 OBJECT-TYPE
    SYNTAX TimeTicks
    ACCESS read-only
    STATUS mandatory
    DESCRIPTION
        "Cumulative duration of Signalling link congestion 
          Q752/3.7."
    ::= { cItpSpLinkTableEntry 89 }

cItpSpLinkQ752T3E10L1 OBJECT-TYPE
    SYNTAX Counter
--  Units
--    Packets
    ACCESS read-only
    STATUS mandatory
    DESCRIPTION
        "The number of packets(MSUs) discarded due to Signalling 
         link level 1 congestion Q752/3.10"
    ::= { cItpSpLinkTableEntry 90 }

cItpSpLinkQ752T3E10L2 OBJECT-TYPE
    SYNTAX Counter
--  Units
--    Packets
    ACCESS read-only
    STATUS mandatory
    DESCRIPTION
        "The number of packets(MSUs) discard due to Signalling 
         link level 2 congestion Q752/3.10"
    ::= { cItpSpLinkTableEntry 91 }

cItpSpLinkQ752T3E10L3 OBJECT-TYPE
    SYNTAX Counter
--  Units
--    Packets
    ACCESS read-only
    STATUS mandatory
    DESCRIPTION
        "The number of packets(MSUs) discard due to Signalling 
         link level 3 congestion Q752/3.10"
    ::= { cItpSpLinkTableEntry 92 }

cItpSpLinkQ752T3E11L1 OBJECT-TYPE
    SYNTAX Counter
--  Units
--    bytes
    ACCESS read-only
    STATUS mandatory
    DESCRIPTION
        "The number times this Signalling link entered congestion
         level 1 and packets were discarded. This measurement is 
         specified in Q752/3.11"
    ::= { cItpSpLinkTableEntry 93 }

cItpSpLinkQ752T3E11L2 OBJECT-TYPE
    SYNTAX Counter
--  Units
--    bytes
    ACCESS read-only
    STATUS mandatory
    DESCRIPTION
        "The number times this Signalling link entered congestion
         level 2 and packets were discarded. This measurement is 
         specified in Q752/3.11"
    ::= { cItpSpLinkTableEntry 94 }

cItpSpLinkQ752T3E11L3 OBJECT-TYPE
    SYNTAX Counter
--  Units
--    bytes
    ACCESS read-only
    STATUS mandatory
    DESCRIPTION
        "The number times this Signalling link entered congestion
         level 3 and packets were discarded. This measurement is 
         specified in Q752/3.11"
    ::= { cItpSpLinkTableEntry 95 }

cItpSpLinkIPType1 OBJECT-TYPE
    SYNTAX InetAddressType
--    Rsyntax INTEGER {
--        ?? enum value of zero may cause problems
--        unknown(0),
--        ipv4(1),
--        ipv6(2),
--        dns(16)
--        }
    ACCESS read-write
    STATUS mandatory
    DESCRIPTION
        "When cItpSpLinkType is set to sctpIp then this object 
         contains the type of the first of four possible local 
         IP addresses used to create the association supporting
         this link. When cItpSpLinkType is not set to sctpIp 
         then no significance is to be placed on this value."
    ::= { cItpSpLinkTableEntry 96 }

cItpSpLinkIPType2 OBJECT-TYPE
    SYNTAX InetAddressType
--    Rsyntax INTEGER {
--        ?? enum value of zero may cause problems
--        unknown(0),
--        ipv4(1),
--        ipv6(2),
--        dns(16)
--        }
    ACCESS read-write
    STATUS mandatory
    DESCRIPTION
        "When cItpSpLinkType is set to sctpIp then this object 
         contains the type of the second of four possible local 
         IP addresses used to create the association supporting
         this link. When cItpSpLinkType is not set to sctpIp 
         then no significance is to be placed on this value."
    ::= { cItpSpLinkTableEntry 97 }

cItpSpLinkIPType3 OBJECT-TYPE
    SYNTAX InetAddressType
--    Rsyntax INTEGER {
--        ?? enum value of zero may cause problems
--        unknown(0),
--        ipv4(1),
--        ipv6(2),
--        dns(16)
--        }
    ACCESS read-write
    STATUS mandatory
    DESCRIPTION
        "When cItpSpLinkType is set to sctpIp then this object 
         contains the type of the third of four possible local 
         IP addresses used to create the association supporting
         this link. When cItpSpLinkType is not set to sctpIp 
         then no significance is to be placed on this value."
    ::= { cItpSpLinkTableEntry 98 }

cItpSpLinkIPType4 OBJECT-TYPE
    SYNTAX InetAddressType
--    Rsyntax INTEGER {
--        ?? enum value of zero may cause problems
--        unknown(0),
--        ipv4(1),
--        ipv6(2),
--        dns(16)
--        }
    ACCESS read-write
    STATUS mandatory
    DESCRIPTION
        "When cItpSpLinkType is set to sctpIp then this object 
         contains the type of the fourth of four possible local 
         IP addresses used to create the association supporting
         this link. When cItpSpLinkType is not set to sctpIp 
         then no significance is to be placed on this value."
    ::= { cItpSpLinkTableEntry 99 }

cItpSpLinkIPAddr1 OBJECT-TYPE
    SYNTAX InetAddress
--    Rsyntax OCTET STRING(SIZE(0..255))
    ACCESS read-write
    STATUS mandatory
    DESCRIPTION
        "When cItpSpLinkType is set to sctpIp then this object 
         contains the first of four possible local IP addresses 
         used to create the association supporting this link.
         When cItpSpLinkType is not set to sctpIp then no
         significance is to be placed on this value."
    ::= { cItpSpLinkTableEntry 100 }

cItpSpLinkIPAddr2 OBJECT-TYPE
    SYNTAX InetAddress
--    Rsyntax OCTET STRING(SIZE(0..255))
    ACCESS read-write
    STATUS mandatory
    DESCRIPTION
        "When cItpSpLinkType is set to sctpIp then this object 
         contains the second of four possible local IP addresses 
         used to create the association supporting this link.
         When cItpSpLinkType is not set to sctpIp then no
         significance is to be placed on this value."
    ::= { cItpSpLinkTableEntry 101 }

cItpSpLinkIPAddr3 OBJECT-TYPE
    SYNTAX InetAddress
--    Rsyntax OCTET STRING(SIZE(0..255))
    ACCESS read-write
    STATUS mandatory
    DESCRIPTION
        "When cItpSpLinkType is set to sctpIp then this object 
         contains the third of four possible local IP addresses 
         used to create the association supporting this link.
         When cItpSpLinkType is not set to sctpIp then no
         significance is to be placed on this value."
    ::= { cItpSpLinkTableEntry 102 }

cItpSpLinkIPAddr4 OBJECT-TYPE
    SYNTAX InetAddress
--    Rsyntax OCTET STRING(SIZE(0..255))
    ACCESS read-write
    STATUS mandatory
    DESCRIPTION
        "When cItpSpLinkType is set to sctpIp then this object 
         contains the fourth of four possible local IP addresses 
         used to create the association supporting this link.
         When cItpSpLinkType is not set to sctpIp then no
         significance is to be placed on this value."
    ::= { cItpSpLinkTableEntry 103 }

cItpSpLinkLocalPort OBJECT-TYPE
    SYNTAX Gauge(0..65535)
    ACCESS read-write
    STATUS mandatory
    DESCRIPTION
        "When cItpSpLinkType is set to sctpIp then this object 
         contains the local port number used to create the
         association supporting this link.
         When cItpSpLinkType is not set to sctpIp then no
         significance is to be placed on this value."
    ::= { cItpSpLinkTableEntry 104 }

cItpSpLinkRemotePort OBJECT-TYPE
    SYNTAX Gauge(0..65535)
    ACCESS read-write
    STATUS mandatory
    DESCRIPTION
        "When cItpSpLinkType is set to sctpIp then this object 
         contains the remote port number used to create the
         association supporting this link.
         When cItpSpLinkType is not set to sctpIp then no
         significance is to be placed on this value."
    ::= { cItpSpLinkTableEntry 105 }

cItpSpLinkQosClass OBJECT-TYPE
    SYNTAX CItpTcQos
--    Rsyntax Gauge(0..7|255)
    ACCESS read-write
    STATUS mandatory
    DESCRIPTION
        "When cItpSpLinkType is set to sctpIp then this object 
         contains the quality of service class to be assigned
         to packets sent on this association.
         When cItpSpLinkType is not set to sctpIp then no
         significance is to be placed on this value."
    ::= { cItpSpLinkTableEntry 106 }

cItpSpLinkRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The object is used by a management station to 
         create or delete the row entry in cItpSpLinkTable  
         following the RowStatus textual convention."
    ::= { cItpSpLinkTableEntry 107 }

cItpSpLinkStateReason OBJECT-TYPE
    SYNTAX OCTET STRING(SIZE(1..2))
        -- BITS are:
        --   localInhibit(0)
        --   remoteInhibit(1)
        --   blocked(2)
    ACCESS read-only
    STATUS mandatory
    DESCRIPTION
        "This object provides additional information
         on the state of a link as follows.
          
         'localInhibit'  : Link has been inhibited by a local 
                           management operation.
         'remoteInhibit' : LInk has been inhibited by a remote
                           management operation.
         'blocked'       : Link is blocked because of a remote 
                           processor outage."
    ::= { cItpSpLinkTableEntry 108 }

cItpSpLinkDisplayName OBJECT-TYPE
    SYNTAX SnmpAdminString(SIZE(0..30))
--    Rsyntax OCTET STRING(SIZE(0..30))
    ACCESS read-write
    STATUS mandatory
    DESCRIPTION
        "A short identifier for each link linkset.
         This value can be set by system administrator
         or defaults to the linkset name and SLC 
         formatted as an ASCII string."
    ::= { cItpSpLinkTableEntry 109 }

cItpSpLinkDroppedPkts OBJECT-TYPE
    SYNTAX Counter
--  Units
--    packets
    ACCESS read-only
    STATUS mandatory
    DESCRIPTION
        "The number of packets that were dropped by this link."
    ::= { cItpSpLinkTableEntry 110 }

cItpSpLinkTransmittedLssu OBJECT-TYPE
    SYNTAX Counter
--  Units
--    LSSU
    ACCESS read-only
    STATUS mandatory
    DESCRIPTION
        "The number of Link Status Signal Units sent on this 
         link."
    ::= { cItpSpLinkTableEntry 111 }

cItpSpLinkReceivedLssu OBJECT-TYPE
    SYNTAX Counter
--  Units
--    LSSU
    ACCESS read-only
    STATUS mandatory
    DESCRIPTION
        "The number of Link Status Signal Units received on this
         link."
    ::= { cItpSpLinkTableEntry 112 }

cItpSpLinkProtocolDetails OBJECT-TYPE
    SYNTAX OCTET STRING(SIZE(1..2))
        -- BITS are:
        --   tcbcBuffering(0)
        --   tcocBuffering(1)
        --   tlacAdjacentSpRestarting(2)
        --   tlacEmergencyCoInProgress(3)
        --   tlacChangebackInProgress(4)
        --   tlacChangeoverInProgress(5)
        --   tlacChangeoverFailed(6)
        --   tlacInhibitRetry(7)
        --   tlacManagementRequest(8)
        --   tlacSpRestarting(9)
        --   tsrcChangeOverComplete(10)
        --   tsrcAdjacentSpRestart(11)
    ACCESS read-only
    STATUS mandatory
    DESCRIPTION
        "This object provide details on the protocol states
         for this link as follows.
         
         Changeback control(TCBC)         
               'tcbcBuffering': Changeback control is buffering data 
                                on this link.
               
         Changeover control(TCOC)
               'tcocBuffering': Changeover control is buffering data 
                                on this link
               
         Link availability control(TLAC)
               'tlacAdjacentSpRestarting': Adjacent Signalling point 
                                is restarting. 
               
               'tlacEmergencyCoInProgress': Emergency changeover is in
                                progress on this link.
                                
               'tlacChangebackInProgress': Changeback is in progress 
                                on this link.
                                
               'tlacChangeoverInProgress': Changeover is in progress 
                                on this link.
                       
               'tlacChangeoverFailed': The last changeover operation
                                failed on this link.
                                
               'tlacInhibitRetry': Inhibit command will be retried.
               
               'tlacManagementRequest': Management request in progress
                                for this link.
                                 
               'tlacSpRestarting': Signalling point is in the process 
                                of a restart.
               
         Signalling routing control(TSRC)
               'tsrcChangeOverComplete': Changeove request is complete.
               
               'tsrcAdjacentSpRestart': Adjacent Signalling Point is
                                restarting."
    ::= { cItpSpLinkTableEntry 113 }

cItpSpLinkLsacState OBJECT-TYPE
    SYNTAX INTEGER {
        undefined(1),
        inactive(2),
        active(3),
        activatingRestoring(4),
        failed(5),
        actT17wait(6),
        actAnsiWaitDeloaded(7),
        actItuWaitStmReady(8)
        }
    ACCESS read-only
    STATUS mandatory
    DESCRIPTION
        "Signalling link activity control state:
         'undefined(1)' - link is an undefined state
         'inactive(2)' - A Signalling link that is not in 
                         operation.
         'active(3)' - A Signalling link that is in 
                         operation.           
         'activatingRestoring(4)' - A Signalling that is not operational
                         and is being activated or restored.
         'failed(5)' - A Signalling link which is available 
                         (not blocked) is marked by level 3 as 
                         failed when a changeover order is 
                         received.            
         'actT17wait(6)' - Link activation has failed.  Link is 
                         placed into this state to wait for timer 
                         T17 to expire in order to avoid the 
                         oscillation of initial alignment failure
                         and link restart.       
         'actAnsiWaitDeloaded(7) - Waiting for change back 
                         acknowledgement (second attempt).
         'actItuWaitStmReady(8)' Wait for Signalling Traffic 
                         Management ready event."
    REFERENCE
        "Figure 37/Q.704 - Signalling link management;
         Signalling link activity control (LSAC)"
    ::= { cItpSpLinkTableEntry 114 }

cItpSpLinkTsrcState OBJECT-TYPE
    SYNTAX INTEGER {
        undefined(1),
        idle(2),
        wait5(3)
        }
    ACCESS read-only
    STATUS mandatory
    DESCRIPTION
        "Signalling traffic management routing control state:
           'undefined(1)' - link is an undefined state
           'idle(2)'      - traffic mangement is idle
           'wait5(3)'     - traffic management is active and 
                            in the sending status phase"
    REFERENCE
        "Figure 29/Q.704 - Signalling traffic management;
         Signalling routing control (TSRC)"
    ::= { cItpSpLinkTableEntry 115 }

cItpSpLinkTcocState OBJECT-TYPE
    SYNTAX INTEGER {
        undefined(1),
        idle(2),
        wait2(3),
        waitForAck(4),
        retrieving(5),
        wait5(6),
        wait7(7),
        wait8(8)
        }
    ACCESS read-only
    STATUS mandatory
    DESCRIPTION
        " Changeover control State:
           'undefined(1)'  - Link is an undefined state.
           'idle(2)'       - Link is available and idle.
           'wait2(3)'      - Wait for MTP2 to initialize link.
           'waitForAck(4)' - Waiting for changeover 
                             acknowledgement.
           'retrieving(5)' - Packets are being retrieved from 
                             link.
           'wait5(6)'      - Wait state when transitioning from 
                             idle state.
           'wait7(7)'      - Delay to avoid message mis-sequencing
                             on changeover
           'wait8(8)'      - Wait state prior to processing 
                             changeover order or emergency 
                             changeover order events."
    REFERENCE
        " Figure 30/Q.704 - Signalling traffic management;
          changeover control (TCOC)"
    ::= { cItpSpLinkTableEntry 116 }

cItpSpLinkTcocLocalBSNT OBJECT-TYPE
    SYNTAX CItpSpSequenceNumber
--    Rsyntax Gauge(0..65535)
    ACCESS read-only
    STATUS mandatory
    DESCRIPTION
        "The local backward sequence number to be transmitted."
    ::= { cItpSpLinkTableEntry 117 }

cItpSpLinkTcocRemoteBSNT OBJECT-TYPE
    SYNTAX CItpSpSequenceNumber
--    Rsyntax Gauge(0..65535)
    ACCESS read-only
    STATUS mandatory
    DESCRIPTION
        "The remote backward sequence number to be transmitted."
    ::= { cItpSpLinkTableEntry 118 }

cItpSpLinkTcbcState OBJECT-TYPE
    SYNTAX INTEGER {
        undefined(1),
        idle(2),
        firstAttempt(3),
        secondAttempt(4),
        timeControlledDiversion(5)
        }
    ACCESS read-only
    STATUS mandatory
    DESCRIPTION
        " Changeback control State:
           'undefined(1)'     - link is an undefined state.
           'idle(2)'          - Link is available and idle.
           'firstAttempt(3)'  - First attempt at changeback.
           'secondAttempt(4)' - Second attempt at changeback
           'timeControlledDiversion(5)' - Changeback using 
                              time controlled Diversion."
    ::= { cItpSpLinkTableEntry 119 }

cItpSpLinkReceivedSIB OBJECT-TYPE
    SYNTAX Counter
--  Units
--    SIB
    ACCESS read-only
    STATUS mandatory
    DESCRIPTION
        "The number of status indicator 'busy' link status signal
         units received on this link. The SIB indicates that
         level two is congested at the transmitting Signalling
         point."
    ::= { cItpSpLinkTableEntry 120 }

cItpSpLinkTransmittedSIB OBJECT-TYPE
    SYNTAX Counter
--  Units
--    SIB
    ACCESS read-only
    STATUS mandatory
    DESCRIPTION
        "The number of status indicator 'busy' link status signal
         units transmitted on this link. The SIB indicates that
         level two is congested at the transmitting Signalling
         point."
    ::= { cItpSpLinkTableEntry 121 }

cItpSpLinkMtp2ExpiredT01 OBJECT-TYPE
    SYNTAX Counter
    ACCESS read-only
    STATUS mandatory
    DESCRIPTION
        "The number of times the alignment ready timer has 
         expired on this link."
    ::= { cItpSpLinkTableEntry 122 }

cItpSpLinkMtp2ExpiredT02 OBJECT-TYPE
    SYNTAX Counter
    ACCESS read-only
    STATUS mandatory
    DESCRIPTION
        "The number of times the not alignment ready timer has
         expired on this link."
    ::= { cItpSpLinkTableEntry 123 }

cItpSpLinkMtp2ExpiredT03 OBJECT-TYPE
    SYNTAX Counter
    ACCESS read-only
    STATUS mandatory
    DESCRIPTION
        "The number of times the aligned timer has
         expired on this link."
    ::= { cItpSpLinkTableEntry 124 }

cItpSpLinkMtp2ExpiredT04 OBJECT-TYPE
    SYNTAX Counter
    ACCESS read-only
    STATUS mandatory
    DESCRIPTION
        "The number of times the proving period timer
         has expired on this link."
    ::= { cItpSpLinkTableEntry 125 }

cItpSpLinkMtp2ExpiredT05 OBJECT-TYPE
    SYNTAX Counter
    ACCESS read-only
    STATUS mandatory
    DESCRIPTION
        "The number of times the sending status indicator
         busy timer has expired on this link."
    ::= { cItpSpLinkTableEntry 126 }

cItpSpLinkMtp2ExpiredT06 OBJECT-TYPE
    SYNTAX Counter
    ACCESS read-only
    STATUS mandatory
    DESCRIPTION
        "The number of times the remote congestion
         timer has expired on this link."
    ::= { cItpSpLinkTableEntry 127 }

cItpSpLinkMtp2ExpiredT07 OBJECT-TYPE
    SYNTAX Counter
    ACCESS read-only
    STATUS mandatory
    DESCRIPTION
        "The number of times the excessive delay of 
         acknowledgement timer has expired on this link."
    ::= { cItpSpLinkTableEntry 128 }

cItpSpLinkOMAERMCount OBJECT-TYPE
    SYNTAX Counter
    ACCESS read-only
    STATUS mandatory
    DESCRIPTION
        "The number of times the Alignment Error Rate Monitor
         procedure was started on this link."
    ::= { cItpSpLinkTableEntry 129 }

cItpSpLinkOMAERMFailCount OBJECT-TYPE
    SYNTAX Counter
    ACCESS read-only
    STATUS mandatory
    DESCRIPTION
        "The number of times the Alignment Error Rate Monitor
         procedure failed on this link."
    ::= { cItpSpLinkTableEntry 130 }

cItpSpLinkOMSURMCount OBJECT-TYPE
    SYNTAX Counter
    ACCESS read-only
    STATUS mandatory
    DESCRIPTION
        "The number of times the Signal Unit Error Rate Monitor
         procedure was started on this link."
    ::= { cItpSpLinkTableEntry 131 }

cItpSpLinkOMSURMFailCount OBJECT-TYPE
    SYNTAX Counter
    ACCESS read-only
    STATUS mandatory
    DESCRIPTION
        "The number of times the Signal Unit Error Rate Monitor
         procedure failed on this link."
    ::= { cItpSpLinkTableEntry 132 }

cItpSpLinkPlanCapacityRcvd OBJECT-TYPE
    SYNTAX CItpSpLinkCapacity
--    Rsyntax Gauge(0|56000..2147483647)
--  Units
--    bits per second
    ACCESS read-write
    STATUS mandatory
    DESCRIPTION
        "An estimate of the number of bits per second that is
         expected to be received from this link.  This 
         object will be used in combination with 
         cItpSpUtilSampleInterval, cItpSpUtilThreshold, 
         cItpSpUtilThreshold and cItpSpLinkUtilThresholdRcvd
         to generate the cItpSpLinkRcvdUtilChange notification."
    ::= { cItpSpLinkTableEntry 133 }

cItpSpLinkUtilThresholdRcvd OBJECT-TYPE
    SYNTAX CItpSpPercentThreshold
--    Rsyntax Gauge(0..100)
--  Units
--    percent
    ACCESS read-write
    STATUS mandatory
    DESCRIPTION
        "This object specifies the threshold used to 
         to generate the cItpSpLinkRcvdUtilChange notification.  
         The value of zero indicates the threshold has not been
         defined at the link level and the value from the 
         cItpSpUtilThreshold object will be used to generate
         the cItpSpLinkRcvdUtilChange notification."
    DEFVAL { 0 }
    ::= { cItpSpLinkTableEntry 134 }

cItpSpLinkUtilizationRcvd OBJECT-TYPE
    SYNTAX CItpSpLinkUtilization
--    Rsyntax Gauge(0..999)
--  Units
--    percent
    ACCESS read-only
    STATUS mandatory
    DESCRIPTION
        "An estimate of the utilization of this link for traffic
         received on this link in the prior time period defined 
         by the cItpSpUtilSampleInterval object."
    ::= { cItpSpLinkTableEntry 135 }

cItpSpLinkUtilStateRcvd OBJECT-TYPE
    SYNTAX CItpSpLinkUtilizationState
--    Rsyntax INTEGER {
--        ?? enum value of zero may cause problems
--        unMonitored(0),
--        underThreshold(1),
--        overThreshold(2)
--        }
    ACCESS read-only
    STATUS mandatory
    DESCRIPTION
        "Link Utilization State for in bound traffic."
    ::= { cItpSpLinkTableEntry 136 }

cItpSpLinkL2BytesRcvd OBJECT-TYPE
    SYNTAX Counter
    ACCESS read-only
    STATUS mandatory
    DESCRIPTION
        "A count of the bytes received on the link including the 
         additional bytes required by underlying protocols.
         This provides a transport independent mechanism 
         for collection information on link utilization."
    ::= { cItpSpLinkTableEntry 137 }

cItpSpLinkPlanCapacitySent OBJECT-TYPE
    SYNTAX CItpSpLinkCapacity
--    Rsyntax Gauge(0|56000..2147483647)
--  Units
--    bits per second
    ACCESS read-write
    STATUS mandatory
    DESCRIPTION
        "An estimate of the number of bits per second that is
         expected to be sent on this link.  This object will 
         be used in combination with  cItpSpUtilSampleInterval, 
         cItpSpUtilThreshold and cItpSpLinkUtilThresholdRcvd to 
         generate the cItpSpLinkSentUtilChange notification."
    ::= { cItpSpLinkTableEntry 138 }

cItpSpLinkUtilThresholdSent OBJECT-TYPE
    SYNTAX CItpSpPercentThreshold
--    Rsyntax Gauge(0..100)
--  Units
--    percent
    ACCESS read-write
    STATUS mandatory
    DESCRIPTION
        "This object specifies the threshold used to generate the
         cItpSpLinkRcvdUtilChange notification.  The value of zero
         indicates the threshold has not been defined at the link 
         level and the value from the cItpSpUtilThreshold object
         will be used to generate the cItpSpLinkRcvdUtilChange 
         notification."
    DEFVAL { 0 }
    ::= { cItpSpLinkTableEntry 139 }

cItpSpLinkUtilizationSent OBJECT-TYPE
    SYNTAX CItpSpLinkUtilization
--    Rsyntax Gauge(0..999)
--  Units
--    percent
    ACCESS read-only
    STATUS mandatory
    DESCRIPTION
        "An estimate of the utilization of this link for traffic
         sent on this link in the prior time period defined 
         by the cItpSpUtilSampleInterval object."
    ::= { cItpSpLinkTableEntry 140 }

cItpSpLinkUtilStateSent OBJECT-TYPE
    SYNTAX CItpSpLinkUtilizationState
--    Rsyntax INTEGER {
--        ?? enum value of zero may cause problems
--        unMonitored(0),
--        underThreshold(1),
--        overThreshold(2)
--        }
    ACCESS read-only
    STATUS mandatory
    DESCRIPTION
        "Link Utilization State for out bound traffic."
    ::= { cItpSpLinkTableEntry 141 }

cItpSpLinkL2BytesSent OBJECT-TYPE
    SYNTAX Counter
    ACCESS read-only
    STATUS mandatory
    DESCRIPTION
        "A count of the bytes sent on the link including the 
         additional bytes required by underlying protocols.
         This provides a transport independent mechanism 
         for collection information on link utilization."
    ::= { cItpSpLinkTableEntry 142 }

cItpSpLsStateChangeNotifEnabled OBJECT-TYPE
    SYNTAX TruthValue
--    Rsyntax INTEGER {
--        true(1),
--        false(2)
--        }
    ACCESS read-write
    STATUS mandatory
    DESCRIPTION
        "The SP linkset notification truth value.
        'true'  Indicates that cItpSpLinksetStateChange
                notification is to be generated when the state
                changes. That is, the notification generation 
                is enabled.
        'false' Indicates that cItpSpLinksetStateChange
                notification generation is disabled."
    DEFVAL { false }
    ::= { cItpSpNotificationsEnable 1 }

cItpSpLnkStateChangeNotifEnabled OBJECT-TYPE
    SYNTAX TruthValue
--    Rsyntax INTEGER {
--        true(1),
--        false(2)
--        }
    ACCESS read-write
    STATUS mandatory
    DESCRIPTION
        "The SP link notification truth value.
        'true'  Indicates that cItpSpLinkStateChange
                notification is to be generated when the state
                changes. That is, the notification generation 
                is enabled.
        'false' Indicates that cItpSpLinkStateChange
                notification generation is disabled."
    DEFVAL { false }
    ::= { cItpSpNotificationsEnable 2 }

cItpSpCongestionNotifEnabled OBJECT-TYPE
    SYNTAX TruthValue
--    Rsyntax INTEGER {
--        true(1),
--        false(2)
--        }
    ACCESS read-write
    STATUS mandatory
    DESCRIPTION
        "The SP Congestion  notification truth value.
        'true'  Indicates that cItpSpCongestionChange
                notification is to be generated when the state
                changes. That is, the notification generation 
                is enabled.
        'false' Indicates that cItpSpCongestionChange
                notification generation is disabled."
    DEFVAL { false }
    ::= { cItpSpNotificationsEnable 3 }

cItpSpLinkUtilNotifEnabled OBJECT-TYPE
    SYNTAX TruthValue
--    Rsyntax INTEGER {
--        true(1),
--        false(2)
--        }
    ACCESS read-write
    STATUS mandatory
    DESCRIPTION
        "The SP link utilization  notification truth value.
        'true'  Indicates that the notification of link 
                utilization has been enabled.  That is, 
                the notification generation is enabled.
                
        'false' Indicates that the notification link 
                utilization has been disabled."
    DEFVAL { false }
    ::= { cItpSpNotificationsEnable 4 }

cItpSpLinksetStateChange TRAP-TYPE
-- Reverse mappable trap
    ENTERPRISE cItpSpMIBNotifs
    VARIABLES {
        cItpSpCLLICode, cItpSpLinksetState, 
        cItpSpLinksetDisplayName, cItpSpLinksetSourceDisplayPC, 
        cItpSpLinksetAdjacentDisplayPC }
--  Status
--    mandatory
    DESCRIPTION
        "The notification generated when a linkset
         changes to a new state.  The value of
         cItpSpLinksetState  indicates the new state."
    ::= 1

cItpSpLinkStateChange TRAP-TYPE
-- Reverse mappable trap
    ENTERPRISE cItpSpMIBNotifs
    VARIABLES {
        cItpSpCLLICode, cItpSpLinkState, cItpSpLinkDisplayName, 
        cItpSpLinksetSourceDisplayPC, 
        cItpSpLinksetAdjacentDisplayPC, cItpSpLinkStateReason }
--  Status
--    mandatory
    DESCRIPTION
        "The notification generated when a link
         changes to a new state.  The value of
         cItpSpLinkState  indicates the new state."
    ::= 2

cItpSpCongestionChange TRAP-TYPE
-- Reverse mappable trap
    ENTERPRISE cItpSpMIBNotifs
    VARIABLES {
        cItpSpCLLICode, cItpSpLinkCongestionState, 
        cItpSpLinkDisplayName, cItpSpLinksetSourceDisplayPC, 
        cItpSpLinksetAdjacentDisplayPC }
--  Status
--    mandatory
    DESCRIPTION
        "The notification generated when a link
         changes to a new congestion level as specified
         by cItpSpLinkCongestionState object."
    ::= 3

cItpSpLinkRcvdUtilChange TRAP-TYPE
-- Reverse mappable trap
    ENTERPRISE cItpSpMIBNotifs
    VARIABLES {
        cItpSpCLLICode, cItpSpLinkUtilStateRcvd, 
        cItpSpLinkDisplayName, cItpSpLinksetSourceDisplayPC, 
        cItpSpLinksetAdjacentDisplayPC, cItpSpLinkUtilizationRcvd }
--  Status
--    mandatory
    DESCRIPTION
        "The notification provide is generated when 
         the cItpSpLinkUtilStateRcvd changes states."
    ::= 4

cItpSpLinkSentUtilChange TRAP-TYPE
-- Reverse mappable trap
    ENTERPRISE cItpSpMIBNotifs
    VARIABLES {
        cItpSpCLLICode, cItpSpLinkUtilStateSent, 
        cItpSpLinkDisplayName, cItpSpLinksetSourceDisplayPC, 
        cItpSpLinksetAdjacentDisplayPC, cItpSpLinkUtilizationSent }
--  Status
--    mandatory
    DESCRIPTION
        "The notification provide is generated when 
         the cItpSpLinkUtilStateSent changes states."
    ::= 5

cItpSpScalarsGroup OBJECT IDENTIFIER ::= { cItpSpMIBGroups 1 }
-- OBJECT-GROUP
--  Status
--    deprecated
--  Descr
--    SP main objects.
--  objects
--    cItpSpVariant, cItpSpCLLICode, cItpSpDisplayName, 
--    cItpSpDescription, cItpSpMtp2T01, cItpSpMtp2T02, 
--    cItpSpMtp2T03, cItpSpMtp2T04E, cItpSpMtp2T04N, cItpSpMtp2T05, 
--    cItpSpMtp2T06, cItpSpMtp2T07, cItpSpMtp3T01, cItpSpMtp3T02, 
--    cItpSpMtp3T03, cItpSpMtp3T04, cItpSpMtp3T05, cItpSpMtp3T06, 
--    cItpSpMtp3T07, cItpSpMtp3T08, cItpSpMtp3T10, cItpSpMtp3T11, 
--    cItpSpMtp3T12, cItpSpMtp3T13, cItpSpMtp3T14, cItpSpMtp3T15, 
--    cItpSpMtp3T16, cItpSpMtp3T17, cItpSpMtp3T18, cItpSpMtp3T19, 
--    cItpSpMtp3T20, cItpSpMtp3T21, cItpSpMtp3T22, cItpSpMtp3T23, 
--    cItpSpMtp3T24, cItpSpMtp3T25, cItpSpMtp3T26, cItpSpMtp3T27, 
--    cItpSpMtp3T28, cItpSpMtp3T29, cItpSpMtp3T30, cItpSpMtp3T31, 
--    cItpSpMtp3T32, cItpSpMtp3T33, cItpSpMtp3T34, 
--    cItpSpTimerLinkTest, cItpSpTimerLinkMessage, 
--    cItpSpTimerLinkActRetry, cItpSpTFR, cItpSpCongestionsLevels, 
--    cItpSpFastRestart

cItpSpPointCodeGroup OBJECT IDENTIFIER ::= { cItpSpMIBGroups 2 }
-- OBJECT-GROUP
--  Status
--    mandatory
--  Descr
--    SP main objects.
--  objects
--    cItpSpPointCodeType, cItpSpPointCodeDisplay, 
--    cItpSpPointCodeRowStatus

cItpSpLinksetGroup OBJECT IDENTIFIER ::= { cItpSpMIBGroups 3 }
-- OBJECT-GROUP
--  Status
--    deprecated
--  Descr
--    SP linkset objects.
--  objects
--    cItpSpLinksetSourcePointCode, cItpSpLinksetSourceDisplayPC, 
--    cItpSpLinksetAdjacentPointCode, 
--    cItpSpLinksetAdjacentDisplayPC, cItpSpLinksetState, 
--    cItpSpLinksetInboundAcl, cItpSpLinksetOutboundAcl, 
--    cItpSpLinksetSnmmRTN, cItpSpLinksetSntmRTN, 
--    cItpSpLinksetSpare2RTN, cItpSpLinksetSccpRTN, 
--    cItpSpLinksetTupRTN, cItpSpLinksetIsupRTN, 
--    cItpSpLinksetDupcRTN, cItpSpLinksetDupfRTN, 
--    cItpSpLinksetMtupRTN, cItpSpLinksetBisupRTN, 
--    cItpSpLinksetSisupRTN, cItpSpLinksetSpare11RTN, 
--    cItpSpLinksetSpare12RTN, cItpSpLinksetSpare13RTN, 
--    cItpSpLinksetSpare14RTN, cItpSpLinksetSpare15RTN, 
--    cItpSpLinksetAccountingEnabled, cItpSpLinksetNumLinks, 
--    cItpSpLinksetDurationInService, 
--    cItpSpLinksetDurationOutService, cItpSpLinksetMtp2T01, 
--    cItpSpLinksetMtp2T02, cItpSpLinksetMtp2T03, 
--    cItpSpLinksetMtp2T04E, cItpSpLinksetMtp2T04N, 
--    cItpSpLinksetMtp2T05, cItpSpLinksetMtp2T06, 
--    cItpSpLinksetMtp2T07, cItpSpLinksetMtp3T01, 
--    cItpSpLinksetMtp3T02, cItpSpLinksetMtp3T03, 
--    cItpSpLinksetMtp3T04, cItpSpLinksetMtp3T05, 
--    cItpSpLinksetMtp3T06, cItpSpLinksetMtp3T07, 
--    cItpSpLinksetMtp3T08, cItpSpLinksetMtp3T10, 
--    cItpSpLinksetMtp3T11, cItpSpLinksetMtp3T12, 
--    cItpSpLinksetMtp3T13, cItpSpLinksetMtp3T14, 
--    cItpSpLinksetMtp3T15, cItpSpLinksetMtp3T16, 
--    cItpSpLinksetMtp3T17, cItpSpLinksetMtp3T18, 
--    cItpSpLinksetMtp3T19, cItpSpLinksetMtp3T20, 
--    cItpSpLinksetMtp3T21, cItpSpLinksetMtp3T22, 
--    cItpSpLinksetMtp3T23, cItpSpLinksetMtp3T24, 
--    cItpSpLinksetMtp3T25, cItpSpLinksetMtp3T26, 
--    cItpSpLinksetMtp3T27, cItpSpLinksetMtp3T28, 
--    cItpSpLinksetMtp3T29, cItpSpLinksetMtp3T30, 
--    cItpSpLinksetMtp3T31, cItpSpLinksetMtp3T32, 
--    cItpSpLinksetMtp3T33, cItpSpLinksetMtp3T34, 
--    cItpSpLinksetTimerLinkTest, cItpSpLinksetTimerLinkMessage, 
--    cItpSpLinksetTimerLinkActRetry, cItpSpLinksetPlanCapacity, 
--    cItpSpLinksetActPriority, cItpSpLinksetType, 
--    cItpSpLinksetRowStatus, cItpSpLinksetNi, 
--    cItpSpLinksetDisplayName, cItpSpLinksetDescription

cItpSpLinkGroup OBJECT IDENTIFIER ::= { cItpSpMIBGroups 4 }
-- OBJECT-GROUP
--  Status
--    deprecated
--  Descr
--    SP link objects.
--  objects
--    cItpSpLinkDescription, cItpSpLinkState, cItpSpLinkType, 
--    cItpSpLinkifIndex, cItpSpLinkSctpAssociation, 
--    cItpSpLinkMtp3PacketsRcvd, cItpSpLinkMtp3PacketsSent, 
--    cItpSpLinkMtp3BytesRcvd, cItpSpLinkMtp3BytesSent, 
--    cItpSpLinkMtp2T01, cItpSpLinkMtp2T02, cItpSpLinkMtp2T03, 
--    cItpSpLinkMtp2T04E, cItpSpLinkMtp2T04N, cItpSpLinkMtp2T05, 
--    cItpSpLinkMtp2T06, cItpSpLinkMtp2T07, cItpSpLinkMtp3T01, 
--    cItpSpLinkMtp3T02, cItpSpLinkMtp3T03, cItpSpLinkMtp3T04, 
--    cItpSpLinkMtp3T05, cItpSpLinkMtp3T06, cItpSpLinkMtp3T07, 
--    cItpSpLinkMtp3T08, cItpSpLinkMtp3T10, cItpSpLinkMtp3T11, 
--    cItpSpLinkMtp3T12, cItpSpLinkMtp3T13, cItpSpLinkMtp3T14, 
--    cItpSpLinkMtp3T15, cItpSpLinkMtp3T16, cItpSpLinkMtp3T17, 
--    cItpSpLinkMtp3T18, cItpSpLinkMtp3T19, cItpSpLinkMtp3T20, 
--    cItpSpLinkMtp3T21, cItpSpLinkMtp3T22, cItpSpLinkMtp3T23, 
--    cItpSpLinkMtp3T24, cItpSpLinkMtp3T25, cItpSpLinkMtp3T26, 
--    cItpSpLinkMtp3T27, cItpSpLinkMtp3T28, cItpSpLinkMtp3T29, 
--    cItpSpLinkMtp3T30, cItpSpLinkMtp3T31, cItpSpLinkMtp3T32, 
--    cItpSpLinkMtp3T33, cItpSpLinkMtp3T34, cItpSpLinkTimerLinkTest, 
--    cItpSpLinkTimerLinkMessage, cItpSpLinkTimerLinkActRetry, 
--    cItpSpLinkXmitQueueDepth, cItpSpLinkXmitQueueDepthHigh, 
--    cItpSpLinkXmitQueueDepthHighRT, cItpSpLinkCongestionState, 
--    cItpSpLinkCongestionAbate1, cItpSpLinkCongestionAbate2, 
--    cItpSpLinkCongestionAbate3, cItpSpLinkCongestionOnset1, 
--    cItpSpLinkCongestionOnset2, cItpSpLinkCongestionOnset3, 
--    cItpSpLinkSigLinkTest, cItpSpLinkQ752T1E1, cItpSpLinkQ752T1E2, 
--    cItpSpLinkQ752T1E3, cItpSpLinkQ752T1E4, cItpSpLinkQ752T1E5, 
--    cItpSpLinkQ752T1E6, cItpSpLinkQ752T1E7, cItpSpLinkQ752T1E8, 
--    cItpSpLinkQ752T1E9, cItpSpLinkQ752T1E10, cItpSpLinkQ752T1E11, 
--    cItpSpLinkQ752T2E1, cItpSpLinkQ752T2E5, cItpSpLinkQ752T2E6, 
--    cItpSpLinkQ752T2E7, cItpSpLinkQ752T2E9, cItpSpLinkQ752T2E10, 
--    cItpSpLinkQ752T2E15, cItpSpLinkQ752T2E16, cItpSpLinkQ752T2E18, 
--    cItpSpLinkMtp3PacketsRetrans, cItpSpLinkMtp3BytesRetrans, 
--    cItpSpLinkQ752T3E6, cItpSpLinkQ752T3E7, cItpSpLinkQ752T3E10L1, 
--    cItpSpLinkQ752T3E10L2, cItpSpLinkQ752T3E10L3, 
--    cItpSpLinkQ752T3E11L1, cItpSpLinkQ752T3E11L2, 
--    cItpSpLinkQ752T3E11L3, cItpSpLinkIPType1, cItpSpLinkIPType2, 
--    cItpSpLinkIPType3, cItpSpLinkIPType4, cItpSpLinkIPAddr1, 
--    cItpSpLinkIPAddr2, cItpSpLinkIPAddr3, cItpSpLinkIPAddr4, 
--    cItpSpLinkLocalPort, cItpSpLinkRemotePort, cItpSpLinkQosClass, 
--    cItpSpLinkRowStatus, cItpSpLinkStateReason, 
--    cItpSpLinkDisplayName

cItpSpNotificationsEnableGroup OBJECT IDENTIFIER ::= { cItpSpMIBGroups 5 }
-- OBJECT-GROUP
--  Status
--    deprecated
--  Descr
--    SP enable notification objects.
--  objects
--    cItpSpLsStateChangeNotifEnabled, 
--    cItpSpLnkStateChangeNotifEnabled, 
--    cItpSpCongestionNotifEnabled

cItpSpStatsGroup OBJECT IDENTIFIER ::= { cItpSpMIBGroups 7 }
-- OBJECT-GROUP
--  Status
--    deprecated
--  Descr
--    SP protocol statistics objects.
--  objects
--    cItpSpDistSccpUnseq, cItpSpSummaryRoutingException, 
--    cItpSpLinksetVariant, cItpSpLinkDroppedPkts, 
--    cItpSpLinkTransmittedLssu, cItpSpLinkReceivedLssu, 
--    cItpSpLinkProtocolDetails, cItpSpLinkLsacState, 
--    cItpSpLinkTsrcState, cItpSpLinkTcocState, 
--    cItpSpLinkTcocLocalBSNT, cItpSpLinkTcocRemoteBSNT, 
--    cItpSpLinkTcbcState, cItpSpLinkReceivedSIB, 
--    cItpSpLinkTransmittedSIB, cItpSpLinkMtp2ExpiredT01, 
--    cItpSpLinkMtp2ExpiredT02, cItpSpLinkMtp2ExpiredT03, 
--    cItpSpLinkMtp2ExpiredT04, cItpSpLinkMtp2ExpiredT05, 
--    cItpSpLinkMtp2ExpiredT06, cItpSpLinkMtp2ExpiredT07, 
--    cItpSpLinkOMAERMCount, cItpSpLinkOMAERMFailCount, 
--    cItpSpLinkOMSURMCount, cItpSpLinkOMSURMFailCount

cItpSpScalarsGroupRev2 OBJECT IDENTIFIER ::= { cItpSpMIBGroups 8 }
-- OBJECT-GROUP
--  Status
--    mandatory
--  Descr
--    SP main objects.
--  objects
--    cItpSpVariant, cItpSpCLLICode, cItpSpDisplayName, 
--    cItpSpDescription, cItpSpMtp2T01, cItpSpMtp2T02, 
--    cItpSpMtp2T03, cItpSpMtp2T04E, cItpSpMtp2T04N, cItpSpMtp2T05, 
--    cItpSpMtp2T06, cItpSpMtp2T07, cItpSpMtp3T01, cItpSpMtp3T02, 
--    cItpSpMtp3T03, cItpSpMtp3T04, cItpSpMtp3T05, cItpSpMtp3T06, 
--    cItpSpMtp3T07, cItpSpMtp3T08, cItpSpMtp3T10, cItpSpMtp3T11, 
--    cItpSpMtp3T12, cItpSpMtp3T13, cItpSpMtp3T14, cItpSpMtp3T15, 
--    cItpSpMtp3T16, cItpSpMtp3T17, cItpSpMtp3T18, cItpSpMtp3T19, 
--    cItpSpMtp3T20, cItpSpMtp3T21, cItpSpMtp3T22, cItpSpMtp3T23, 
--    cItpSpMtp3T24, cItpSpMtp3T25, cItpSpMtp3T26, cItpSpMtp3T27, 
--    cItpSpMtp3T28, cItpSpMtp3T29, cItpSpMtp3T30, cItpSpMtp3T31, 
--    cItpSpMtp3T32, cItpSpMtp3T33, cItpSpMtp3T34, 
--    cItpSpTimerLinkTest, cItpSpTimerLinkMessage, 
--    cItpSpTimerLinkActRetry, cItpSpTFR, cItpSpCongestionsLevels, 
--    cItpSpFastRestart, cItpSpDistSccpUnseq, 
--    cItpSpSummaryRoutingException, cItpSpUtilSampleInterval, 
--    cItpSpUtilThreshold, cItpSpUtilAbateDelta

cItpSpLinksetGroupRev2 OBJECT IDENTIFIER ::= { cItpSpMIBGroups 9 }
-- OBJECT-GROUP
--  Status
--    mandatory
--  Descr
--    SP linkset objects.
--  objects
--    cItpSpLinksetSourcePointCode, cItpSpLinksetSourceDisplayPC, 
--    cItpSpLinksetAdjacentPointCode, 
--    cItpSpLinksetAdjacentDisplayPC, cItpSpLinksetState, 
--    cItpSpLinksetInboundAcl, cItpSpLinksetOutboundAcl, 
--    cItpSpLinksetSnmmRTN, cItpSpLinksetSntmRTN, 
--    cItpSpLinksetSpare2RTN, cItpSpLinksetSccpRTN, 
--    cItpSpLinksetTupRTN, cItpSpLinksetIsupRTN, 
--    cItpSpLinksetDupcRTN, cItpSpLinksetDupfRTN, 
--    cItpSpLinksetMtupRTN, cItpSpLinksetBisupRTN, 
--    cItpSpLinksetSisupRTN, cItpSpLinksetSpare11RTN, 
--    cItpSpLinksetSpare12RTN, cItpSpLinksetSpare13RTN, 
--    cItpSpLinksetSpare14RTN, cItpSpLinksetSpare15RTN, 
--    cItpSpLinksetAccountingEnabled, cItpSpLinksetNumLinks, 
--    cItpSpLinksetDurationInService, 
--    cItpSpLinksetDurationOutService, cItpSpLinksetMtp2T01, 
--    cItpSpLinksetMtp2T02, cItpSpLinksetMtp2T03, 
--    cItpSpLinksetMtp2T04E, cItpSpLinksetMtp2T04N, 
--    cItpSpLinksetMtp2T05, cItpSpLinksetMtp2T06, 
--    cItpSpLinksetMtp2T07, cItpSpLinksetMtp3T01, 
--    cItpSpLinksetMtp3T02, cItpSpLinksetMtp3T03, 
--    cItpSpLinksetMtp3T04, cItpSpLinksetMtp3T05, 
--    cItpSpLinksetMtp3T06, cItpSpLinksetMtp3T07, 
--    cItpSpLinksetMtp3T08, cItpSpLinksetMtp3T10, 
--    cItpSpLinksetMtp3T11, cItpSpLinksetMtp3T12, 
--    cItpSpLinksetMtp3T13, cItpSpLinksetMtp3T14, 
--    cItpSpLinksetMtp3T15, cItpSpLinksetMtp3T16, 
--    cItpSpLinksetMtp3T17, cItpSpLinksetMtp3T18, 
--    cItpSpLinksetMtp3T19, cItpSpLinksetMtp3T20, 
--    cItpSpLinksetMtp3T21, cItpSpLinksetMtp3T22, 
--    cItpSpLinksetMtp3T23, cItpSpLinksetMtp3T24, 
--    cItpSpLinksetMtp3T25, cItpSpLinksetMtp3T26, 
--    cItpSpLinksetMtp3T27, cItpSpLinksetMtp3T28, 
--    cItpSpLinksetMtp3T29, cItpSpLinksetMtp3T30, 
--    cItpSpLinksetMtp3T31, cItpSpLinksetMtp3T32, 
--    cItpSpLinksetMtp3T33, cItpSpLinksetMtp3T34, 
--    cItpSpLinksetTimerLinkTest, cItpSpLinksetTimerLinkMessage, 
--    cItpSpLinksetTimerLinkActRetry, cItpSpLinksetActPriority, 
--    cItpSpLinksetType, cItpSpLinksetRowStatus, cItpSpLinksetNi, 
--    cItpSpLinksetDisplayName, cItpSpLinksetDescription, 
--    cItpSpLinksetVariant

cItpSpLinkGroupRev2 OBJECT IDENTIFIER ::= { cItpSpMIBGroups 10 }
-- OBJECT-GROUP
--  Status
--    mandatory
--  Descr
--    SP link objects.
--  objects
--    cItpSpLinkDescription, cItpSpLinkState, cItpSpLinkType, 
--    cItpSpLinkifIndex, cItpSpLinkSctpAssociation, 
--    cItpSpLinkMtp3PacketsRcvd, cItpSpLinkMtp3PacketsSent, 
--    cItpSpLinkMtp3BytesRcvd, cItpSpLinkMtp3BytesSent, 
--    cItpSpLinkMtp2T01, cItpSpLinkMtp2T02, cItpSpLinkMtp2T03, 
--    cItpSpLinkMtp2T04E, cItpSpLinkMtp2T04N, cItpSpLinkMtp2T05, 
--    cItpSpLinkMtp2T06, cItpSpLinkMtp2T07, cItpSpLinkMtp3T01, 
--    cItpSpLinkMtp3T02, cItpSpLinkMtp3T03, cItpSpLinkMtp3T04, 
--    cItpSpLinkMtp3T05, cItpSpLinkMtp3T06, cItpSpLinkMtp3T07, 
--    cItpSpLinkMtp3T08, cItpSpLinkMtp3T10, cItpSpLinkMtp3T11, 
--    cItpSpLinkMtp3T12, cItpSpLinkMtp3T13, cItpSpLinkMtp3T14, 
--    cItpSpLinkMtp3T15, cItpSpLinkMtp3T16, cItpSpLinkMtp3T17, 
--    cItpSpLinkMtp3T18, cItpSpLinkMtp3T19, cItpSpLinkMtp3T20, 
--    cItpSpLinkMtp3T21, cItpSpLinkMtp3T22, cItpSpLinkMtp3T23, 
--    cItpSpLinkMtp3T24, cItpSpLinkMtp3T25, cItpSpLinkMtp3T26, 
--    cItpSpLinkMtp3T27, cItpSpLinkMtp3T28, cItpSpLinkMtp3T29, 
--    cItpSpLinkMtp3T30, cItpSpLinkMtp3T31, cItpSpLinkMtp3T32, 
--    cItpSpLinkMtp3T33, cItpSpLinkMtp3T34, cItpSpLinkTimerLinkTest, 
--    cItpSpLinkTimerLinkMessage, cItpSpLinkTimerLinkActRetry, 
--    cItpSpLinkXmitQueueDepth, cItpSpLinkXmitQueueDepthHigh, 
--    cItpSpLinkXmitQueueDepthHighRT, cItpSpLinkCongestionState, 
--    cItpSpLinkCongestionAbate1, cItpSpLinkCongestionAbate2, 
--    cItpSpLinkCongestionAbate3, cItpSpLinkCongestionOnset1, 
--    cItpSpLinkCongestionOnset2, cItpSpLinkCongestionOnset3, 
--    cItpSpLinkSigLinkTest, cItpSpLinkQ752T1E1, cItpSpLinkQ752T1E2, 
--    cItpSpLinkQ752T1E3, cItpSpLinkQ752T1E4, cItpSpLinkQ752T1E5, 
--    cItpSpLinkQ752T1E6, cItpSpLinkQ752T1E7, cItpSpLinkQ752T1E8, 
--    cItpSpLinkQ752T1E9, cItpSpLinkQ752T1E10, cItpSpLinkQ752T1E11, 
--    cItpSpLinkQ752T2E1, cItpSpLinkQ752T2E5, cItpSpLinkQ752T2E6, 
--    cItpSpLinkQ752T2E7, cItpSpLinkQ752T2E9, cItpSpLinkQ752T2E10, 
--    cItpSpLinkQ752T2E15, cItpSpLinkQ752T2E16, cItpSpLinkQ752T2E18, 
--    cItpSpLinkMtp3PacketsRetrans, cItpSpLinkMtp3BytesRetrans, 
--    cItpSpLinkQ752T3E6, cItpSpLinkQ752T3E7, cItpSpLinkQ752T3E10L1, 
--    cItpSpLinkQ752T3E10L2, cItpSpLinkQ752T3E10L3, 
--    cItpSpLinkQ752T3E11L1, cItpSpLinkQ752T3E11L2, 
--    cItpSpLinkQ752T3E11L3, cItpSpLinkIPType1, cItpSpLinkIPType2, 
--    cItpSpLinkIPType3, cItpSpLinkIPType4, cItpSpLinkIPAddr1, 
--    cItpSpLinkIPAddr2, cItpSpLinkIPAddr3, cItpSpLinkIPAddr4, 
--    cItpSpLinkLocalPort, cItpSpLinkRemotePort, cItpSpLinkQosClass, 
--    cItpSpLinkRowStatus, cItpSpLinkStateReason, 
--    cItpSpLinkDisplayName, cItpSpLinkDroppedPkts, 
--    cItpSpLinkTransmittedLssu, cItpSpLinkReceivedLssu, 
--    cItpSpLinkProtocolDetails, cItpSpLinkLsacState, 
--    cItpSpLinkTsrcState, cItpSpLinkTcocState, 
--    cItpSpLinkTcocLocalBSNT, cItpSpLinkTcocRemoteBSNT, 
--    cItpSpLinkTcbcState, cItpSpLinkReceivedSIB, 
--    cItpSpLinkTransmittedSIB, cItpSpLinkMtp2ExpiredT01, 
--    cItpSpLinkMtp2ExpiredT02, cItpSpLinkMtp2ExpiredT03, 
--    cItpSpLinkMtp2ExpiredT04, cItpSpLinkMtp2ExpiredT05, 
--    cItpSpLinkMtp2ExpiredT06, cItpSpLinkMtp2ExpiredT07, 
--    cItpSpLinkOMAERMCount, cItpSpLinkOMAERMFailCount, 
--    cItpSpLinkOMSURMCount, cItpSpLinkOMSURMFailCount, 
--    cItpSpLinkPlanCapacityRcvd, cItpSpLinkUtilThresholdRcvd, 
--    cItpSpLinkUtilizationRcvd, cItpSpLinkUtilStateRcvd, 
--    cItpSpLinkL2BytesRcvd, cItpSpLinkPlanCapacitySent, 
--    cItpSpLinkUtilThresholdSent, cItpSpLinkUtilizationSent, 
--    cItpSpLinkUtilStateSent, cItpSpLinkL2BytesSent

cItpSpNotificationsEnableGroupRev2 OBJECT IDENTIFIER ::= { cItpSpMIBGroups 11 }
-- OBJECT-GROUP
--  Status
--    mandatory
--  Descr
--    SP enable notification objects.
--  objects
--    cItpSpLsStateChangeNotifEnabled, 
--    cItpSpLnkStateChangeNotifEnabled, 
--    cItpSpCongestionNotifEnabled, cItpSpLinkUtilNotifEnabled

cItpSpNotificationsGroup OBJECT IDENTIFIER ::= { cItpSpMIBGroups 6 }
-- NOTIFICATION-GROUP
--  Status
--    deprecated
--  Descr
--    SP notification objects.
--  notifications
--    cItpSpLinksetStateChange, cItpSpLinkStateChange, 
--    cItpSpCongestionChange

cItpSpNotificationsGroupRev2 OBJECT IDENTIFIER ::= { cItpSpMIBGroups 12 }
-- NOTIFICATION-GROUP
--  Status
--    mandatory
--  Descr
--    SP notification objects.
--  notifications
--    cItpSpLinksetStateChange, cItpSpLinkStateChange, 
--    cItpSpCongestionChange, cItpSpLinkRcvdUtilChange, 
--    cItpSpLinkSentUtilChange

cItpSpMIBCompliance OBJECT IDENTIFIER ::= { cItpSpMIBCompliances 1 }
-- MODULE-COMPLIANCE
--  Status
--    deprecated
--  Descr
--    The compliance statement for entities which implement
--    the Cisco SP MIB
--  Module
--    >>current<<
--   MandGroup
--    cItpSpScalarsGroup
--   MandGroup
--    cItpSpPointCodeGroup
--   MandGroup
--    cItpSpLinksetGroup
--   MandGroup
--    cItpSpLinkGroup
--   MandGroup
--    cItpSpNotificationsEnableGroup
--   MandGroup
--    cItpSpNotificationsGroup
--   ObjVar
--    cItpSpVariant
--   ObjVar
--    cItpSpCLLICode
--   ObjVar
--    cItpSpDisplayName
--   ObjVar
--    cItpSpDescription
--   ObjVar
--    cItpSpMtp2T01
--   ObjVar
--    cItpSpMtp2T02
--   ObjVar
--    cItpSpMtp2T03
--   ObjVar
--    cItpSpMtp2T04E
--   ObjVar
--    cItpSpMtp2T04N
--   ObjVar
--    cItpSpMtp2T05
--   ObjVar
--    cItpSpMtp2T06
--   ObjVar
--    cItpSpMtp2T07
--   ObjVar
--    cItpSpMtp3T01
--   ObjVar
--    cItpSpMtp3T02
--   ObjVar
--    cItpSpMtp3T03
--   ObjVar
--    cItpSpMtp3T04
--   ObjVar
--    cItpSpMtp3T05
--   ObjVar
--    cItpSpMtp3T06
--   ObjVar
--    cItpSpMtp3T07
--   ObjVar
--    cItpSpMtp3T08
--   ObjVar
--    cItpSpMtp3T10
--   ObjVar
--    cItpSpMtp3T11
--   ObjVar
--    cItpSpMtp3T12
--   ObjVar
--    cItpSpMtp3T13
--   ObjVar
--    cItpSpMtp3T14
--   ObjVar
--    cItpSpMtp3T15
--   ObjVar
--    cItpSpMtp3T16
--   ObjVar
--    cItpSpMtp3T17
--   ObjVar
--    cItpSpMtp3T18
--   ObjVar
--    cItpSpMtp3T19
--   ObjVar
--    cItpSpMtp3T20
--   ObjVar
--    cItpSpMtp3T21
--   ObjVar
--    cItpSpMtp3T22
--   ObjVar
--    cItpSpMtp3T23
--   ObjVar
--    cItpSpMtp3T24
--   ObjVar
--    cItpSpMtp3T25
--   ObjVar
--    cItpSpMtp3T26
--   ObjVar
--    cItpSpMtp3T27
--   ObjVar
--    cItpSpMtp3T28
--   ObjVar
--    cItpSpMtp3T29
--   ObjVar
--    cItpSpMtp3T30
--   ObjVar
--    cItpSpMtp3T31
--   ObjVar
--    cItpSpMtp3T32
--   ObjVar
--    cItpSpMtp3T33
--   ObjVar
--    cItpSpMtp3T34
--   ObjVar
--    cItpSpTimerLinkTest
--   ObjVar
--    cItpSpTimerLinkMessage
--   ObjVar
--    cItpSpTimerLinkActRetry
--   ObjVar
--    cItpSpTFR
--   ObjVar
--    cItpSpCongestionsLevels
--   ObjVar
--    cItpSpFastRestart
--   ObjVar
--    cItpSpPointCodeType
--   ObjVar
--    cItpSpPointCodeRowStatus
--   ObjVar
--    cItpSpLinksetSourcePointCode
--   ObjVar
--    cItpSpLinksetAdjacentPointCode
--   ObjVar
--    cItpSpLinksetInboundAcl
--   ObjVar
--    cItpSpLinksetOutboundAcl
--   ObjVar
--    cItpSpLinksetSnmmRTN
--   ObjVar
--    cItpSpLinksetSntmRTN
--   ObjVar
--    cItpSpLinksetSpare2RTN
--   ObjVar
--    cItpSpLinksetSccpRTN
--   ObjVar
--    cItpSpLinksetTupRTN
--   ObjVar
--    cItpSpLinksetIsupRTN
--   ObjVar
--    cItpSpLinksetDupcRTN
--   ObjVar
--    cItpSpLinksetDupfRTN
--   ObjVar
--    cItpSpLinksetMtupRTN
--   ObjVar
--    cItpSpLinksetBisupRTN
--   ObjVar
--    cItpSpLinksetSisupRTN
--   ObjVar
--    cItpSpLinksetSpare11RTN
--   ObjVar
--    cItpSpLinksetSpare12RTN
--   ObjVar
--    cItpSpLinksetSpare13RTN
--   ObjVar
--    cItpSpLinksetSpare14RTN
--   ObjVar
--    cItpSpLinksetSpare15RTN
--   ObjVar
--    cItpSpLinksetAccountingEnabled
--   ObjVar
--    cItpSpLinksetMtp2T01
--   ObjVar
--    cItpSpLinksetMtp2T02
--   ObjVar
--    cItpSpLinksetMtp2T03
--   ObjVar
--    cItpSpLinksetMtp2T04E
--   ObjVar
--    cItpSpLinksetMtp2T04N
--   ObjVar
--    cItpSpLinksetMtp2T05
--   ObjVar
--    cItpSpLinksetMtp2T06
--   ObjVar
--    cItpSpLinksetMtp2T07
--   ObjVar
--    cItpSpLinksetMtp3T01
--   ObjVar
--    cItpSpLinksetMtp3T02
--   ObjVar
--    cItpSpLinksetMtp3T03
--   ObjVar
--    cItpSpLinksetMtp3T04
--   ObjVar
--    cItpSpLinksetMtp3T05
--   ObjVar
--    cItpSpLinksetMtp3T06
--   ObjVar
--    cItpSpLinksetMtp3T07
--   ObjVar
--    cItpSpLinksetMtp3T08
--   ObjVar
--    cItpSpLinksetMtp3T10
--   ObjVar
--    cItpSpLinksetMtp3T11
--   ObjVar
--    cItpSpLinksetMtp3T12
--   ObjVar
--    cItpSpLinksetMtp3T13
--   ObjVar
--    cItpSpLinksetMtp3T14
--   ObjVar
--    cItpSpLinksetMtp3T15
--   ObjVar
--    cItpSpLinksetMtp3T16
--   ObjVar
--    cItpSpLinksetMtp3T17
--   ObjVar
--    cItpSpLinksetMtp3T18
--   ObjVar
--    cItpSpLinksetMtp3T19
--   ObjVar
--    cItpSpLinksetMtp3T20
--   ObjVar
--    cItpSpLinksetMtp3T21
--   ObjVar
--    cItpSpLinksetMtp3T22
--   ObjVar
--    cItpSpLinksetMtp3T23
--   ObjVar
--    cItpSpLinksetMtp3T24
--   ObjVar
--    cItpSpLinksetMtp3T25
--   ObjVar
--    cItpSpLinksetMtp3T26
--   ObjVar
--    cItpSpLinksetMtp3T27
--   ObjVar
--    cItpSpLinksetMtp3T28
--   ObjVar
--    cItpSpLinksetMtp3T29
--   ObjVar
--    cItpSpLinksetMtp3T30
--   ObjVar
--    cItpSpLinksetMtp3T31
--   ObjVar
--    cItpSpLinksetMtp3T32
--   ObjVar
--    cItpSpLinksetMtp3T33
--   ObjVar
--    cItpSpLinksetMtp3T34
--   ObjVar
--    cItpSpLinksetTimerLinkTest
--   ObjVar
--    cItpSpLinksetTimerLinkMessage
--   ObjVar
--    cItpSpLinksetTimerLinkActRetry
--   ObjVar
--    cItpSpLinksetPlanCapacity
--   ObjVar
--    cItpSpLinksetActPriority
--   ObjVar
--    cItpSpLinksetType
--   ObjVar
--    cItpSpLinksetRowStatus
--   ObjVar
--    cItpSpLinksetNi
--   ObjVar
--    cItpSpLinksetDisplayName
--   ObjVar
--    cItpSpLinksetDescription
--   ObjVar
--    cItpSpLinkDescription
--   ObjVar
--    cItpSpLinkType
--   ObjVar
--    cItpSpLinkifIndex
--   ObjVar
--    cItpSpLinkMtp2T01
--   ObjVar
--    cItpSpLinkMtp2T02
--   ObjVar
--    cItpSpLinkMtp2T03
--   ObjVar
--    cItpSpLinkMtp2T04E
--   ObjVar
--    cItpSpLinkMtp2T04N
--   ObjVar
--    cItpSpLinkMtp2T05
--   ObjVar
--    cItpSpLinkMtp2T06
--   ObjVar
--    cItpSpLinkMtp2T07
--   ObjVar
--    cItpSpLinkMtp3T01
--   ObjVar
--    cItpSpLinkMtp3T02
--   ObjVar
--    cItpSpLinkMtp3T03
--   ObjVar
--    cItpSpLinkMtp3T04
--   ObjVar
--    cItpSpLinkMtp3T05
--   ObjVar
--    cItpSpLinkMtp3T06
--   ObjVar
--    cItpSpLinkMtp3T07
--   ObjVar
--    cItpSpLinkMtp3T08
--   ObjVar
--    cItpSpLinkMtp3T10
--   ObjVar
--    cItpSpLinkMtp3T11
--   ObjVar
--    cItpSpLinkMtp3T12
--   ObjVar
--    cItpSpLinkMtp3T13
--   ObjVar
--    cItpSpLinkMtp3T14
--   ObjVar
--    cItpSpLinkMtp3T15
--   ObjVar
--    cItpSpLinkMtp3T16
--   ObjVar
--    cItpSpLinkMtp3T17
--   ObjVar
--    cItpSpLinkMtp3T18
--   ObjVar
--    cItpSpLinkMtp3T19
--   ObjVar
--    cItpSpLinkMtp3T20
--   ObjVar
--    cItpSpLinkMtp3T21
--   ObjVar
--    cItpSpLinkMtp3T22
--   ObjVar
--    cItpSpLinkMtp3T23
--   ObjVar
--    cItpSpLinkMtp3T24
--   ObjVar
--    cItpSpLinkMtp3T25
--   ObjVar
--    cItpSpLinkMtp3T26
--   ObjVar
--    cItpSpLinkMtp3T27
--   ObjVar
--    cItpSpLinkMtp3T28
--   ObjVar
--    cItpSpLinkMtp3T29
--   ObjVar
--    cItpSpLinkMtp3T30
--   ObjVar
--    cItpSpLinkMtp3T31
--   ObjVar
--    cItpSpLinkMtp3T32
--   ObjVar
--    cItpSpLinkMtp3T33
--   ObjVar
--    cItpSpLinkMtp3T34
--   ObjVar
--    cItpSpLinkTimerLinkTest
--   ObjVar
--    cItpSpLinkTimerLinkMessage
--   ObjVar
--    cItpSpLinkTimerLinkActRetry
--   ObjVar
--    cItpSpLinkXmitQueueDepthHigh
--   ObjVar
--    cItpSpLinkCongestionAbate1
--   ObjVar
--    cItpSpLinkCongestionAbate2
--   ObjVar
--    cItpSpLinkCongestionAbate3
--   ObjVar
--    cItpSpLinkCongestionOnset1
--   ObjVar
--    cItpSpLinkCongestionOnset2
--   ObjVar
--    cItpSpLinkCongestionOnset3
--   ObjVar
--    cItpSpLinkSigLinkTest
--   ObjVar
--    cItpSpLinkIPType1
--   ObjVar
--    cItpSpLinkIPType2
--   ObjVar
--    cItpSpLinkIPType3
--   ObjVar
--    cItpSpLinkIPType4
--   ObjVar
--    cItpSpLinkIPAddr1
--   ObjVar
--    cItpSpLinkIPAddr2
--   ObjVar
--    cItpSpLinkIPAddr3
--   ObjVar
--    cItpSpLinkIPAddr4
--   ObjVar
--    cItpSpLinkLocalPort
--   ObjVar
--    cItpSpLinkRemotePort
--   ObjVar
--    cItpSpLinkQosClass
--   ObjVar
--    cItpSpLinkRowStatus
--   ObjVar
--    cItpSpLinkDisplayName

cItpSpMIBComplianceRev1 OBJECT IDENTIFIER ::= { cItpSpMIBCompliances 2 }
-- MODULE-COMPLIANCE
--  Status
--    deprecated
--  Descr
--    The compliance statement for entities which implement
--    the Cisco SP MIB
--  Module
--    >>current<<
--   MandGroup
--    cItpSpScalarsGroup
--   MandGroup
--    cItpSpPointCodeGroup
--   MandGroup
--    cItpSpLinksetGroup
--   MandGroup
--    cItpSpLinkGroup
--   MandGroup
--    cItpSpNotificationsEnableGroup
--   MandGroup
--    cItpSpNotificationsGroup
--   MandGroup
--    cItpSpStatsGroup
--   ObjVar
--    cItpSpVariant
--   ObjVar
--    cItpSpCLLICode
--   ObjVar
--    cItpSpDisplayName
--   ObjVar
--    cItpSpDescription
--   ObjVar
--    cItpSpMtp2T01
--   ObjVar
--    cItpSpMtp2T02
--   ObjVar
--    cItpSpMtp2T03
--   ObjVar
--    cItpSpMtp2T04E
--   ObjVar
--    cItpSpMtp2T04N
--   ObjVar
--    cItpSpMtp2T05
--   ObjVar
--    cItpSpMtp2T06
--   ObjVar
--    cItpSpMtp2T07
--   ObjVar
--    cItpSpMtp3T01
--   ObjVar
--    cItpSpMtp3T02
--   ObjVar
--    cItpSpMtp3T03
--   ObjVar
--    cItpSpMtp3T04
--   ObjVar
--    cItpSpMtp3T05
--   ObjVar
--    cItpSpMtp3T06
--   ObjVar
--    cItpSpMtp3T07
--   ObjVar
--    cItpSpMtp3T08
--   ObjVar
--    cItpSpMtp3T10
--   ObjVar
--    cItpSpMtp3T11
--   ObjVar
--    cItpSpMtp3T12
--   ObjVar
--    cItpSpMtp3T13
--   ObjVar
--    cItpSpMtp3T14
--   ObjVar
--    cItpSpMtp3T15
--   ObjVar
--    cItpSpMtp3T16
--   ObjVar
--    cItpSpMtp3T17
--   ObjVar
--    cItpSpMtp3T18
--   ObjVar
--    cItpSpMtp3T19
--   ObjVar
--    cItpSpMtp3T20
--   ObjVar
--    cItpSpMtp3T21
--   ObjVar
--    cItpSpMtp3T22
--   ObjVar
--    cItpSpMtp3T23
--   ObjVar
--    cItpSpMtp3T24
--   ObjVar
--    cItpSpMtp3T25
--   ObjVar
--    cItpSpMtp3T26
--   ObjVar
--    cItpSpMtp3T27
--   ObjVar
--    cItpSpMtp3T28
--   ObjVar
--    cItpSpMtp3T29
--   ObjVar
--    cItpSpMtp3T30
--   ObjVar
--    cItpSpMtp3T31
--   ObjVar
--    cItpSpMtp3T32
--   ObjVar
--    cItpSpMtp3T33
--   ObjVar
--    cItpSpMtp3T34
--   ObjVar
--    cItpSpTimerLinkTest
--   ObjVar
--    cItpSpTimerLinkMessage
--   ObjVar
--    cItpSpTimerLinkActRetry
--   ObjVar
--    cItpSpTFR
--   ObjVar
--    cItpSpCongestionsLevels
--   ObjVar
--    cItpSpFastRestart
--   ObjVar
--    cItpSpDistSccpUnseq
--   ObjVar
--    cItpSpSummaryRoutingException
--   ObjVar
--    cItpSpPointCodeType
--   ObjVar
--    cItpSpPointCodeRowStatus
--   ObjVar
--    cItpSpLinksetSourcePointCode
--   ObjVar
--    cItpSpLinksetAdjacentPointCode
--   ObjVar
--    cItpSpLinksetInboundAcl
--   ObjVar
--    cItpSpLinksetOutboundAcl
--   ObjVar
--    cItpSpLinksetSnmmRTN
--   ObjVar
--    cItpSpLinksetSntmRTN
--   ObjVar
--    cItpSpLinksetSpare2RTN
--   ObjVar
--    cItpSpLinksetSccpRTN
--   ObjVar
--    cItpSpLinksetTupRTN
--   ObjVar
--    cItpSpLinksetIsupRTN
--   ObjVar
--    cItpSpLinksetDupcRTN
--   ObjVar
--    cItpSpLinksetDupfRTN
--   ObjVar
--    cItpSpLinksetMtupRTN
--   ObjVar
--    cItpSpLinksetBisupRTN
--   ObjVar
--    cItpSpLinksetSisupRTN
--   ObjVar
--    cItpSpLinksetSpare11RTN
--   ObjVar
--    cItpSpLinksetSpare12RTN
--   ObjVar
--    cItpSpLinksetSpare13RTN
--   ObjVar
--    cItpSpLinksetSpare14RTN
--   ObjVar
--    cItpSpLinksetSpare15RTN
--   ObjVar
--    cItpSpLinksetAccountingEnabled
--   ObjVar
--    cItpSpLinksetMtp2T01
--   ObjVar
--    cItpSpLinksetMtp2T02
--   ObjVar
--    cItpSpLinksetMtp2T03
--   ObjVar
--    cItpSpLinksetMtp2T04E
--   ObjVar
--    cItpSpLinksetMtp2T04N
--   ObjVar
--    cItpSpLinksetMtp2T05
--   ObjVar
--    cItpSpLinksetMtp2T06
--   ObjVar
--    cItpSpLinksetMtp2T07
--   ObjVar
--    cItpSpLinksetMtp3T01
--   ObjVar
--    cItpSpLinksetMtp3T02
--   ObjVar
--    cItpSpLinksetMtp3T03
--   ObjVar
--    cItpSpLinksetMtp3T04
--   ObjVar
--    cItpSpLinksetMtp3T05
--   ObjVar
--    cItpSpLinksetMtp3T06
--   ObjVar
--    cItpSpLinksetMtp3T07
--   ObjVar
--    cItpSpLinksetMtp3T08
--   ObjVar
--    cItpSpLinksetMtp3T10
--   ObjVar
--    cItpSpLinksetMtp3T11
--   ObjVar
--    cItpSpLinksetMtp3T12
--   ObjVar
--    cItpSpLinksetMtp3T13
--   ObjVar
--    cItpSpLinksetMtp3T14
--   ObjVar
--    cItpSpLinksetMtp3T15
--   ObjVar
--    cItpSpLinksetMtp3T16
--   ObjVar
--    cItpSpLinksetMtp3T17
--   ObjVar
--    cItpSpLinksetMtp3T18
--   ObjVar
--    cItpSpLinksetMtp3T19
--   ObjVar
--    cItpSpLinksetMtp3T20
--   ObjVar
--    cItpSpLinksetMtp3T21
--   ObjVar
--    cItpSpLinksetMtp3T22
--   ObjVar
--    cItpSpLinksetMtp3T23
--   ObjVar
--    cItpSpLinksetMtp3T24
--   ObjVar
--    cItpSpLinksetMtp3T25
--   ObjVar
--    cItpSpLinksetMtp3T26
--   ObjVar
--    cItpSpLinksetMtp3T27
--   ObjVar
--    cItpSpLinksetMtp3T28
--   ObjVar
--    cItpSpLinksetMtp3T29
--   ObjVar
--    cItpSpLinksetMtp3T30
--   ObjVar
--    cItpSpLinksetMtp3T31
--   ObjVar
--    cItpSpLinksetMtp3T32
--   ObjVar
--    cItpSpLinksetMtp3T33
--   ObjVar
--    cItpSpLinksetMtp3T34
--   ObjVar
--    cItpSpLinksetTimerLinkTest
--   ObjVar
--    cItpSpLinksetTimerLinkMessage
--   ObjVar
--    cItpSpLinksetTimerLinkActRetry
--   ObjVar
--    cItpSpLinksetPlanCapacity
--   ObjVar
--    cItpSpLinksetActPriority
--   ObjVar
--    cItpSpLinksetType
--   ObjVar
--    cItpSpLinksetRowStatus
--   ObjVar
--    cItpSpLinksetNi
--   ObjVar
--    cItpSpLinksetDisplayName
--   ObjVar
--    cItpSpLinksetDescription
--   ObjVar
--    cItpSpLinksetVariant
--   ObjVar
--    cItpSpLinkDescription
--   ObjVar
--    cItpSpLinkType
--   ObjVar
--    cItpSpLinkifIndex
--   ObjVar
--    cItpSpLinkMtp2T01
--   ObjVar
--    cItpSpLinkMtp2T02
--   ObjVar
--    cItpSpLinkMtp2T03
--   ObjVar
--    cItpSpLinkMtp2T04E
--   ObjVar
--    cItpSpLinkMtp2T04N
--   ObjVar
--    cItpSpLinkMtp2T05
--   ObjVar
--    cItpSpLinkMtp2T06
--   ObjVar
--    cItpSpLinkMtp2T07
--   ObjVar
--    cItpSpLinkMtp3T01
--   ObjVar
--    cItpSpLinkMtp3T02
--   ObjVar
--    cItpSpLinkMtp3T03
--   ObjVar
--    cItpSpLinkMtp3T04
--   ObjVar
--    cItpSpLinkMtp3T05
--   ObjVar
--    cItpSpLinkMtp3T06
--   ObjVar
--    cItpSpLinkMtp3T07
--   ObjVar
--    cItpSpLinkMtp3T08
--   ObjVar
--    cItpSpLinkMtp3T10
--   ObjVar
--    cItpSpLinkMtp3T11
--   ObjVar
--    cItpSpLinkMtp3T12
--   ObjVar
--    cItpSpLinkMtp3T13
--   ObjVar
--    cItpSpLinkMtp3T14
--   ObjVar
--    cItpSpLinkMtp3T15
--   ObjVar
--    cItpSpLinkMtp3T16
--   ObjVar
--    cItpSpLinkMtp3T17
--   ObjVar
--    cItpSpLinkMtp3T18
--   ObjVar
--    cItpSpLinkMtp3T19
--   ObjVar
--    cItpSpLinkMtp3T20
--   ObjVar
--    cItpSpLinkMtp3T21
--   ObjVar
--    cItpSpLinkMtp3T22
--   ObjVar
--    cItpSpLinkMtp3T23
--   ObjVar
--    cItpSpLinkMtp3T24
--   ObjVar
--    cItpSpLinkMtp3T25
--   ObjVar
--    cItpSpLinkMtp3T26
--   ObjVar
--    cItpSpLinkMtp3T27
--   ObjVar
--    cItpSpLinkMtp3T28
--   ObjVar
--    cItpSpLinkMtp3T29
--   ObjVar
--    cItpSpLinkMtp3T30
--   ObjVar
--    cItpSpLinkMtp3T31
--   ObjVar
--    cItpSpLinkMtp3T32
--   ObjVar
--    cItpSpLinkMtp3T33
--   ObjVar
--    cItpSpLinkMtp3T34
--   ObjVar
--    cItpSpLinkTimerLinkTest
--   ObjVar
--    cItpSpLinkTimerLinkMessage
--   ObjVar
--    cItpSpLinkTimerLinkActRetry
--   ObjVar
--    cItpSpLinkXmitQueueDepthHigh
--   ObjVar
--    cItpSpLinkCongestionAbate1
--   ObjVar
--    cItpSpLinkCongestionAbate2
--   ObjVar
--    cItpSpLinkCongestionAbate3
--   ObjVar
--    cItpSpLinkCongestionOnset1
--   ObjVar
--    cItpSpLinkCongestionOnset2
--   ObjVar
--    cItpSpLinkCongestionOnset3
--   ObjVar
--    cItpSpLinkSigLinkTest
--   ObjVar
--    cItpSpLinkIPType1
--   ObjVar
--    cItpSpLinkIPType2
--   ObjVar
--    cItpSpLinkIPType3
--   ObjVar
--    cItpSpLinkIPType4
--   ObjVar
--    cItpSpLinkIPAddr1
--   ObjVar
--    cItpSpLinkIPAddr2
--   ObjVar
--    cItpSpLinkIPAddr3
--   ObjVar
--    cItpSpLinkIPAddr4
--   ObjVar
--    cItpSpLinkLocalPort
--   ObjVar
--    cItpSpLinkRemotePort
--   ObjVar
--    cItpSpLinkQosClass
--   ObjVar
--    cItpSpLinkRowStatus
--   ObjVar
--    cItpSpLinkDisplayName

cItpSpMIBComplianceRev2 OBJECT IDENTIFIER ::= { cItpSpMIBCompliances 3 }
-- MODULE-COMPLIANCE
--  Status
--    mandatory
--  Descr
--    The compliance statement for entities which implement
--     the Cisco SP MIB
--  Module
--    >>current<<
--   MandGroup
--    cItpSpPointCodeGroup
--   MandGroup
--    cItpSpScalarsGroupRev2
--   MandGroup
--    cItpSpLinksetGroupRev2
--   MandGroup
--    cItpSpLinkGroupRev2
--   MandGroup
--    cItpSpNotificationsEnableGroupRev2
--   MandGroup
--    cItpSpNotificationsGroupRev2
--   ObjVar
--    cItpSpVariant
--   ObjVar
--    cItpSpCLLICode
--   ObjVar
--    cItpSpDisplayName
--   ObjVar
--    cItpSpDescription
--   ObjVar
--    cItpSpMtp2T01
--   ObjVar
--    cItpSpMtp2T02
--   ObjVar
--    cItpSpMtp2T03
--   ObjVar
--    cItpSpMtp2T04E
--   ObjVar
--    cItpSpMtp2T04N
--   ObjVar
--    cItpSpMtp2T05
--   ObjVar
--    cItpSpMtp2T06
--   ObjVar
--    cItpSpMtp2T07
--   ObjVar
--    cItpSpMtp3T01
--   ObjVar
--    cItpSpMtp3T02
--   ObjVar
--    cItpSpMtp3T03
--   ObjVar
--    cItpSpMtp3T04
--   ObjVar
--    cItpSpMtp3T05
--   ObjVar
--    cItpSpMtp3T06
--   ObjVar
--    cItpSpMtp3T07
--   ObjVar
--    cItpSpMtp3T08
--   ObjVar
--    cItpSpMtp3T10
--   ObjVar
--    cItpSpMtp3T11
--   ObjVar
--    cItpSpMtp3T12
--   ObjVar
--    cItpSpMtp3T13
--   ObjVar
--    cItpSpMtp3T14
--   ObjVar
--    cItpSpMtp3T15
--   ObjVar
--    cItpSpMtp3T16
--   ObjVar
--    cItpSpMtp3T17
--   ObjVar
--    cItpSpMtp3T18
--   ObjVar
--    cItpSpMtp3T19
--   ObjVar
--    cItpSpMtp3T20
--   ObjVar
--    cItpSpMtp3T21
--   ObjVar
--    cItpSpMtp3T22
--   ObjVar
--    cItpSpMtp3T23
--   ObjVar
--    cItpSpMtp3T24
--   ObjVar
--    cItpSpMtp3T25
--   ObjVar
--    cItpSpMtp3T26
--   ObjVar
--    cItpSpMtp3T27
--   ObjVar
--    cItpSpMtp3T28
--   ObjVar
--    cItpSpMtp3T29
--   ObjVar
--    cItpSpMtp3T30
--   ObjVar
--    cItpSpMtp3T31
--   ObjVar
--    cItpSpMtp3T32
--   ObjVar
--    cItpSpMtp3T33
--   ObjVar
--    cItpSpMtp3T34
--   ObjVar
--    cItpSpTimerLinkTest
--   ObjVar
--    cItpSpTimerLinkMessage
--   ObjVar
--    cItpSpTimerLinkActRetry
--   ObjVar
--    cItpSpTFR
--   ObjVar
--    cItpSpCongestionsLevels
--   ObjVar
--    cItpSpFastRestart
--   ObjVar
--    cItpSpDistSccpUnseq
--   ObjVar
--    cItpSpSummaryRoutingException
--   ObjVar
--    cItpSpPointCodeType
--   ObjVar
--    cItpSpPointCodeRowStatus
--   ObjVar
--    cItpSpLinksetSourcePointCode
--   ObjVar
--    cItpSpLinksetAdjacentPointCode
--   ObjVar
--    cItpSpLinksetInboundAcl
--   ObjVar
--    cItpSpLinksetOutboundAcl
--   ObjVar
--    cItpSpLinksetSnmmRTN
--   ObjVar
--    cItpSpLinksetSntmRTN
--   ObjVar
--    cItpSpLinksetSpare2RTN
--   ObjVar
--    cItpSpLinksetSccpRTN
--   ObjVar
--    cItpSpLinksetTupRTN
--   ObjVar
--    cItpSpLinksetIsupRTN
--   ObjVar
--    cItpSpLinksetDupcRTN
--   ObjVar
--    cItpSpLinksetDupfRTN
--   ObjVar
--    cItpSpLinksetMtupRTN
--   ObjVar
--    cItpSpLinksetBisupRTN
--   ObjVar
--    cItpSpLinksetSisupRTN
--   ObjVar
--    cItpSpLinksetSpare11RTN
--   ObjVar
--    cItpSpLinksetSpare12RTN
--   ObjVar
--    cItpSpLinksetSpare13RTN
--   ObjVar
--    cItpSpLinksetSpare14RTN
--   ObjVar
--    cItpSpLinksetSpare15RTN
--   ObjVar
--    cItpSpLinksetAccountingEnabled
--   ObjVar
--    cItpSpLinksetMtp2T01
--   ObjVar
--    cItpSpLinksetMtp2T02
--   ObjVar
--    cItpSpLinksetMtp2T03
--   ObjVar
--    cItpSpLinksetMtp2T04E
--   ObjVar
--    cItpSpLinksetMtp2T04N
--   ObjVar
--    cItpSpLinksetMtp2T05
--   ObjVar
--    cItpSpLinksetMtp2T06
--   ObjVar
--    cItpSpLinksetMtp2T07
--   ObjVar
--    cItpSpLinksetMtp3T01
--   ObjVar
--    cItpSpLinksetMtp3T02
--   ObjVar
--    cItpSpLinksetMtp3T03
--   ObjVar
--    cItpSpLinksetMtp3T04
--   ObjVar
--    cItpSpLinksetMtp3T05
--   ObjVar
--    cItpSpLinksetMtp3T06
--   ObjVar
--    cItpSpLinksetMtp3T07
--   ObjVar
--    cItpSpLinksetMtp3T08
--   ObjVar
--    cItpSpLinksetMtp3T10
--   ObjVar
--    cItpSpLinksetMtp3T11
--   ObjVar
--    cItpSpLinksetMtp3T12
--   ObjVar
--    cItpSpLinksetMtp3T13
--   ObjVar
--    cItpSpLinksetMtp3T14
--   ObjVar
--    cItpSpLinksetMtp3T15
--   ObjVar
--    cItpSpLinksetMtp3T16
--   ObjVar
--    cItpSpLinksetMtp3T17
--   ObjVar
--    cItpSpLinksetMtp3T18
--   ObjVar
--    cItpSpLinksetMtp3T19
--   ObjVar
--    cItpSpLinksetMtp3T20
--   ObjVar
--    cItpSpLinksetMtp3T21
--   ObjVar
--    cItpSpLinksetMtp3T22
--   ObjVar
--    cItpSpLinksetMtp3T23
--   ObjVar
--    cItpSpLinksetMtp3T24
--   ObjVar
--    cItpSpLinksetMtp3T25
--   ObjVar
--    cItpSpLinksetMtp3T26
--   ObjVar
--    cItpSpLinksetMtp3T27
--   ObjVar
--    cItpSpLinksetMtp3T28
--   ObjVar
--    cItpSpLinksetMtp3T29
--   ObjVar
--    cItpSpLinksetMtp3T30
--   ObjVar
--    cItpSpLinksetMtp3T31
--   ObjVar
--    cItpSpLinksetMtp3T32
--   ObjVar
--    cItpSpLinksetMtp3T33
--   ObjVar
--    cItpSpLinksetMtp3T34
--   ObjVar
--    cItpSpLinksetTimerLinkTest
--   ObjVar
--    cItpSpLinksetTimerLinkMessage
--   ObjVar
--    cItpSpLinksetTimerLinkActRetry
--   ObjVar
--    cItpSpLinksetActPriority
--   ObjVar
--    cItpSpLinksetType
--   ObjVar
--    cItpSpLinksetRowStatus
--   ObjVar
--    cItpSpLinksetNi
--   ObjVar
--    cItpSpLinksetDisplayName
--   ObjVar
--    cItpSpLinksetDescription
--   ObjVar
--    cItpSpLinksetVariant
--   ObjVar
--    cItpSpLinkDescription
--   ObjVar
--    cItpSpLinkType
--   ObjVar
--    cItpSpLinkifIndex
--   ObjVar
--    cItpSpLinkMtp2T01
--   ObjVar
--    cItpSpLinkMtp2T02
--   ObjVar
--    cItpSpLinkMtp2T03
--   ObjVar
--    cItpSpLinkMtp2T04E
--   ObjVar
--    cItpSpLinkMtp2T04N
--   ObjVar
--    cItpSpLinkMtp2T05
--   ObjVar
--    cItpSpLinkMtp2T06
--   ObjVar
--    cItpSpLinkMtp2T07
--   ObjVar
--    cItpSpLinkMtp3T01
--   ObjVar
--    cItpSpLinkMtp3T02
--   ObjVar
--    cItpSpLinkMtp3T03
--   ObjVar
--    cItpSpLinkMtp3T04
--   ObjVar
--    cItpSpLinkMtp3T05
--   ObjVar
--    cItpSpLinkMtp3T06
--   ObjVar
--    cItpSpLinkMtp3T07
--   ObjVar
--    cItpSpLinkMtp3T08
--   ObjVar
--    cItpSpLinkMtp3T10
--   ObjVar
--    cItpSpLinkMtp3T11
--   ObjVar
--    cItpSpLinkMtp3T12
--   ObjVar
--    cItpSpLinkMtp3T13
--   ObjVar
--    cItpSpLinkMtp3T14
--   ObjVar
--    cItpSpLinkMtp3T15
--   ObjVar
--    cItpSpLinkMtp3T16
--   ObjVar
--    cItpSpLinkMtp3T17
--   ObjVar
--    cItpSpLinkMtp3T18
--   ObjVar
--    cItpSpLinkMtp3T19
--   ObjVar
--    cItpSpLinkMtp3T20
--   ObjVar
--    cItpSpLinkMtp3T21
--   ObjVar
--    cItpSpLinkMtp3T22
--   ObjVar
--    cItpSpLinkMtp3T23
--   ObjVar
--    cItpSpLinkMtp3T24
--   ObjVar
--    cItpSpLinkMtp3T25
--   ObjVar
--    cItpSpLinkMtp3T26
--   ObjVar
--    cItpSpLinkMtp3T27
--   ObjVar
--    cItpSpLinkMtp3T28
--   ObjVar
--    cItpSpLinkMtp3T29
--   ObjVar
--    cItpSpLinkMtp3T30
--   ObjVar
--    cItpSpLinkMtp3T31
--   ObjVar
--    cItpSpLinkMtp3T32
--   ObjVar
--    cItpSpLinkMtp3T33
--   ObjVar
--    cItpSpLinkMtp3T34
--   ObjVar
--    cItpSpLinkTimerLinkTest
--   ObjVar
--    cItpSpLinkTimerLinkMessage
--   ObjVar
--    cItpSpLinkTimerLinkActRetry
--   ObjVar
--    cItpSpLinkXmitQueueDepthHigh
--   ObjVar
--    cItpSpLinkCongestionAbate1
--   ObjVar
--    cItpSpLinkCongestionAbate2
--   ObjVar
--    cItpSpLinkCongestionAbate3
--   ObjVar
--    cItpSpLinkCongestionOnset1
--   ObjVar
--    cItpSpLinkCongestionOnset2
--   ObjVar
--    cItpSpLinkCongestionOnset3
--   ObjVar
--    cItpSpLinkSigLinkTest
--   ObjVar
--    cItpSpLinkIPType1
--   ObjVar
--    cItpSpLinkIPType2
--   ObjVar
--    cItpSpLinkIPType3
--   ObjVar
--    cItpSpLinkIPType4
--   ObjVar
--    cItpSpLinkIPAddr1
--   ObjVar
--    cItpSpLinkIPAddr2
--   ObjVar
--    cItpSpLinkIPAddr3
--   ObjVar
--    cItpSpLinkIPAddr4
--   ObjVar
--    cItpSpLinkLocalPort
--   ObjVar
--    cItpSpLinkRemotePort
--   ObjVar
--    cItpSpLinkQosClass
--   ObjVar
--    cItpSpLinkRowStatus
--   ObjVar
--    cItpSpLinkDisplayName
--   ObjVar
--    cItpSpLinkPlanCapacitySent
--   ObjVar
--    cItpSpLinkPlanCapacityRcvd


END
