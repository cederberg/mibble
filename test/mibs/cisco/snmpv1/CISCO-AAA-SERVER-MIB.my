-- MIB created 5/02/100 19:13:54, by
--   SMIC (the next generation) version 1.6.29, November 22, 1994.

CISCO-AAA-SERVER-MIB DEFINITIONS ::= BEGIN

-- From file: "CISCO-AAA-SERVER-MIB.my"

IMPORTS
    Counter32, IpAddress
            FROM SNMPv2-SMI-v1
    OBJECT-TYPE
            FROM RFC-1212
    TRAP-TYPE
            FROM RFC-1215
    TimeInterval, DisplayString, TruthValue, RowStatus
            FROM SNMPv2-TC-v1
    Unsigned32
            FROM CISCO-TC
    ciscoExperiment
            FROM CISCO-SMI;

ciscoAAAServerMIB OBJECT IDENTIFIER ::= { ciscoExperiment 56 }
-- MODULE-IDENTITY
--  LastUpdated
--    200001200000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-aaa@cisco.com
--  Descr
--    The MIB module for monitoring communications and status
--     of AAA Server operation
--  RevDate
--    200001200000Z
--  RevDescr
--    Added objects to support AAA server configuration
--              casConfigTable
--                 casProtocol
--                 casIndex
--                 casAddress
--                 casAuthenPort
--                 casAcctPort
--                 casConfigRowStatus

cAAAServerMIBObjects OBJECT IDENTIFIER ::= { ciscoAAAServerMIB 1 }
casConfig       OBJECT IDENTIFIER ::= { cAAAServerMIBObjects 1 }
casStatistics   OBJECT IDENTIFIER ::= { cAAAServerMIBObjects 2 }
cAAAServerMIBNotificationPrefix OBJECT IDENTIFIER ::= { ciscoAAAServerMIB 2 }
cAAAServerMIBNotifications OBJECT IDENTIFIER ::= { cAAAServerMIBNotificationPrefix 0 }
cAAAServerMIBConformance OBJECT IDENTIFIER ::= { ciscoAAAServerMIB 3 }
casMIBCompliances OBJECT IDENTIFIER ::= { cAAAServerMIBConformance 1 }
casMIBGroups    OBJECT IDENTIFIER ::= { cAAAServerMIBConformance 2 }

casServerStateChangeEnable OBJECT-TYPE
    SYNTAX TruthValue
--    Rsyntax INTEGER {
--        true(1),
--        false(2)
--        }
    ACCESS read-write
    STATUS mandatory
    DESCRIPTION
        "This variable controls the generation of 
         casServerStateChange notification.
        
         When this variable is true(1), generation of
         casServerStateChange notifications is enabled.  
         When this variable is false(2), generation of
         casServerStateChange notifications is disabled.
        
         The default value is false(2)."
    ::= { casConfig 1 }

casConfigTable OBJECT-TYPE
    SYNTAX SEQUENCE OF CasConfigEntry
    ACCESS not-accessible
    STATUS mandatory
    DESCRIPTION
        "This table shows current configurations for each
         AAA server, allows existing servers to be removed
         and new ones to be created."
    ::= { casConfig 2 }

casConfigEntry OBJECT-TYPE
    SYNTAX CasConfigEntry
    ACCESS not-accessible
    STATUS mandatory
    DESCRIPTION
        "An AAA server configuration identified by its protocol
         and its index.
        
         An entry is created/removed when a server is defined
         or undefined with IOS configuration commands via 
         CLI or by issuing appropriate sets to this table 
         using snmp.
        
         A management station wishing to create an entry should
         first generate a random number to be used as the index 
         to this sparse table.  The station should then create the 
         associated instance of the row status and row index objects.  
         It must also, either in the same or in successive PDUs, 
         create an instance of casAddress where casAddress is the 
         IP address of the server to be added.
        
         It should also modify the default values for casAuthenPort, 
         casAcctPort if the defaults are not appropriate.
        
         If casKey is a zero-length string or is not explicitly set,
         then the global key will be used.  Otherwise, this value
         is used as the key for this server instance.
        
         Once the appropriate instance of all the configuration
         objects have been created, either by an explicit SNMP set
         request or by default, the row status should be set to
         active(1) to initiate the request.  
        
         After the AAA server is made active, the entry can not be 
         modified - the only allowed operation after this is to 
         destroy the entry by setting casConfigRowStatus to destroy(6).
        
         casPriority is automatically assigned once the entry is
         made active and reflects the relative priority of the 
         defined server with respect to already configured servers.
         Newly-created servers will be assigned the lowest priority.
         To reassign server priorities to existing server entries,
         it may be necessary to destroy and recreate entries in order
         of priority.
        
         Entries in this table with casConfigRowStatus equal to
         active(1) remain in the table until destroyed.  
        
         Entries in this table with casConfigRowStatus equal to 
         values other than active(1) will be destroyed after timeout
         (5 minutes).   
        
         If a server address being created via SNMP exists already
         in another active casConfigEntry, then a newly created row
         can not be made active until the original row with the 
         with the same server address value is destroyed.
        
         Upon reload, casIndex values may be changed, but the
         priorities that were saved before reload will be retained,
         with lowest priority number corresponding to the higher 
         priority servers.
         "
    INDEX { casProtocol, casIndex }
    ::= { casConfigTable 1 }

CasConfigEntry ::= SEQUENCE {
    casProtocol INTEGER,
    casIndex Unsigned32,
    casAddress IpAddress,
    casAuthenPort INTEGER,
    casAcctPort INTEGER,
    casKey DisplayString,
    casPriority Unsigned32,
    casConfigRowStatus RowStatus
    }

casProtocol OBJECT-TYPE
    SYNTAX INTEGER {
        tacacsplus(1),
        radius(2)
        }
    ACCESS not-accessible
    STATUS mandatory
    DESCRIPTION
        "Protocol used with this server.
        
             tacacsplus(1) - TACACS+
        
             radius(2)     - RADIUS
        
            "
    REFERENCE
        "
         RFC 2138 Remote Authentication Dial In User Service (RADIUS)
         RFC 2139 RADIUS Accounting
         The TACACS+ Protocol Version 1.78, Internet Draft"
    ::= { casConfigEntry 1 }

casIndex OBJECT-TYPE
    SYNTAX Unsigned32(1..4294967295)
--    Rsyntax Gauge32(1..4294967295)
    ACCESS not-accessible
    STATUS mandatory
    DESCRIPTION
        "A management station wishing to initiate a new AAA server
         configuration should use a random value for this object
         when creating an instance of casConfigEntry.
          
         The RowStatus semantics of the casConfigRowStatus object
         will prevent access conflicts.
        
         If the randomly chosen casIndex value for row creation 
         is already in use by an existing entry, snmp set to the 
         casIndex value will fail."
    ::= { casConfigEntry 2 }

casAddress OBJECT-TYPE
    SYNTAX IpAddress
    ACCESS read-write
    STATUS mandatory
    DESCRIPTION
        "The IP address of the server."
    ::= { casConfigEntry 3 }

casAuthenPort OBJECT-TYPE
    SYNTAX INTEGER(0..65535)
    ACCESS read-write
    STATUS mandatory
    DESCRIPTION
        "UDP/TCP port used for authentication in the configuration
        
         For TACACS+, this object should be explictly set.
         
         Default value is the IOS default for radius: 1645."
    DEFVAL { 1645 }
    ::= { casConfigEntry 4 }

casAcctPort OBJECT-TYPE
    SYNTAX INTEGER(0..65535)
    ACCESS read-write
    STATUS mandatory
    DESCRIPTION
        "UDP/TCP port used for accounting service in the configuration
        
         For TACACS+, the value of casAcctPort is ignored.  
         casAuthenPort will be used instead.
        
         Default value is the IOS default for radius: 1646."
    DEFVAL { 1646 }
    ::= { casConfigEntry 5 }

casKey OBJECT-TYPE
    SYNTAX DisplayString
--    Rsyntax OCTET STRING(SIZE(0..255))
    ACCESS read-write
    STATUS mandatory
    DESCRIPTION
        "The server key to be used with this server.
        
         Retrieving the value of this object via SNMP will 
         return an empty string for security reasons."
    DEFVAL { "" }
    ::= { casConfigEntry 6 }

casPriority OBJECT-TYPE
    SYNTAX Unsigned32(1..4294967295)
--    Rsyntax Gauge32(1..4294967295)
    ACCESS read-only
    STATUS mandatory
    DESCRIPTION
        "A number that indicates the priority of the server in
         this entry.  Lower numbers indicate higher priority."
    ::= { casConfigEntry 7 }

casConfigRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "The status of this table entry.  Once the entry status is
         set to active, the associated entry cannot be modified
         except destroyed by setting this object to destroy(6)."
    ::= { casConfigEntry 8 }

casStatisticsTable OBJECT-TYPE
    SYNTAX SEQUENCE OF CasStatisticsEntry
    ACCESS not-accessible
    STATUS mandatory
    DESCRIPTION
        "
         Table providing statistics for each server."
    ::= { casStatistics 1 }

casStatisticsEntry OBJECT-TYPE
    SYNTAX CasStatisticsEntry
    ACCESS not-accessible
    STATUS mandatory
    DESCRIPTION
        "Statistical information about a particular server.
        
         Objects in this table are read-only and appear
         automatically whenever a row in the casConfigTable
         is made active.
        
         Objects in this table disappear when casConfigRowStatus
         for the corresponding casConfigEntry is set to the 
         destroy(6) state."
    INDEX { casProtocol, casIndex }
-- Augments casConfigEntry
    ::= { casStatisticsTable 1 }

CasStatisticsEntry ::= SEQUENCE {
    casAuthenRequests Counter32,
    casAuthenRequestTimeouts Counter32,
    casAuthenUnexpectedResponses Counter32,
    casAuthenServerErrorResponses Counter32,
    casAuthenIncorrectResponses Counter32,
    casAuthenResponseTime TimeInterval,
    casAuthenTransactionSuccesses Counter32,
    casAuthenTransactionFailures Counter32,
    casAuthorRequests Counter32,
    casAuthorRequestTimeouts Counter32,
    casAuthorUnexpectedResponses Counter32,
    casAuthorServerErrorResponses Counter32,
    casAuthorIncorrectResponses Counter32,
    casAuthorResponseTime TimeInterval,
    casAuthorTransactionSuccesses Counter32,
    casAuthorTransactionFailures Counter32,
    casAcctRequests Counter32,
    casAcctRequestTimeouts Counter32,
    casAcctUnexpectedResponses Counter32,
    casAcctServerErrorResponses Counter32,
    casAcctIncorrectResponses Counter32,
    casAcctResponseTime TimeInterval,
    casAcctTransactionSuccesses Counter32,
    casAcctTransactionFailures Counter32,
    casState INTEGER,
    casCurrentStateDuration TimeInterval,
    casPreviousStateDuration TimeInterval,
    casTotalDeadTime TimeInterval,
    casDeadCount Counter32
    }

casAuthenRequests OBJECT-TYPE
    SYNTAX Counter32
    ACCESS read-only
    STATUS mandatory
    DESCRIPTION
        "The number of authentication requests sent to
         this server since it is made active.  
        
         Retransmissions due to request timeouts are
         counted as distinct requests."
    ::= { casStatisticsEntry 1 }

casAuthenRequestTimeouts OBJECT-TYPE
    SYNTAX Counter32
    ACCESS read-only
    STATUS mandatory
    DESCRIPTION
        "The number of authentication requests which have
         timed out since it is made active.
        
         A timeout results in a retransmission of the request
         If the maximum number of attempts has been reached,
         no further retransmissions will be attempted."
    ::= { casStatisticsEntry 2 }

casAuthenUnexpectedResponses OBJECT-TYPE
    SYNTAX Counter32
    ACCESS read-only
    STATUS mandatory
    DESCRIPTION
        "The number of unexpected authentication responses received
         from this server since it is made active.
        
         An example is a delayed response to a request which had
         already timed out."
    ::= { casStatisticsEntry 3 }

casAuthenServerErrorResponses OBJECT-TYPE
    SYNTAX Counter32
    ACCESS read-only
    STATUS mandatory
    DESCRIPTION
        "The number of server ERROR authentication responses
         received from this server since it is made active.
        
         These are responses indicating that the server itself
         has identified an error with its authentication
         operation."
    ::= { casStatisticsEntry 4 }

casAuthenIncorrectResponses OBJECT-TYPE
    SYNTAX Counter32
    ACCESS read-only
    STATUS mandatory
    DESCRIPTION
        "The number of authentication responses which could not
         be processed since it is made active.
        
         Reasons include inability to decrypt the response,
         invalid fields, or the response is not valid based on
         the request."
    ::= { casStatisticsEntry 5 }

casAuthenResponseTime OBJECT-TYPE
    SYNTAX TimeInterval
--    Rsyntax INTEGER(0..2147483647)
    ACCESS read-only
    STATUS mandatory
    DESCRIPTION
        "Average response time for authentication requests sent
         to this server, excluding timeouts, since system
         re-initialization."
    ::= { casStatisticsEntry 6 }

casAuthenTransactionSuccesses OBJECT-TYPE
    SYNTAX Counter32
    ACCESS read-only
    STATUS mandatory
    DESCRIPTION
        "The number of authentication transactions with this
         server which succeeded since it is made active.
        
         A transaction may include multiple request
         retransmissions if timeouts occur.
        
         A transaction is successful if the server responds
         with either an authentication pass or fail."
    ::= { casStatisticsEntry 7 }

casAuthenTransactionFailures OBJECT-TYPE
    SYNTAX Counter32
    ACCESS read-only
    STATUS mandatory
    DESCRIPTION
        "The number of authentication transactions with this
         server which failed since it is made active.
        
         A transaction may include multiple request
         retransmissions if timeouts occur.
        
         A transaction failure occurs if maximum resends have
         been met or the server aborts the transaction."
    ::= { casStatisticsEntry 8 }

casAuthorRequests OBJECT-TYPE
    SYNTAX Counter32
    ACCESS read-only
    STATUS mandatory
    DESCRIPTION
        "The number of authorization requests sent to
         this server since it is made active.
        
         Retransmissions due to request timeouts are
         counted as distinct requests.
        
         This object is not instantiated for protocols which do
         not support a distinct authorization function."
    ::= { casStatisticsEntry 9 }

casAuthorRequestTimeouts OBJECT-TYPE
    SYNTAX Counter32
    ACCESS read-only
    STATUS mandatory
    DESCRIPTION
        "The number of authorization requests which have
         timed out since it is made active.
        
         A timeout results in a retransmission of the request
         If the maximum number of attempts has been reached,
         no further retransmissions will be attempted.
         
         This object is not instantiated for protocols which do
         not support a distinct authorization function."
    ::= { casStatisticsEntry 10 }

casAuthorUnexpectedResponses OBJECT-TYPE
    SYNTAX Counter32
    ACCESS read-only
    STATUS mandatory
    DESCRIPTION
        "The number of unexpected authorization responses received
         from this server since it is made active.
        
         An example is a delayed response to a request which
         had already timed out.
        
         This object is not instantiated for protocols which do
         not support a distinct authorization function."
    ::= { casStatisticsEntry 11 }

casAuthorServerErrorResponses OBJECT-TYPE
    SYNTAX Counter32
    ACCESS read-only
    STATUS mandatory
    DESCRIPTION
        "The number of server ERROR authorization responses
         received from this server since it is made active.
        
         These are responses indicating that the server itself
         has identified an error with its authorization
         operation.
        
         This object is not instantiated for protocols which do
         not support a distinct authorization function."
    ::= { casStatisticsEntry 12 }

casAuthorIncorrectResponses OBJECT-TYPE
    SYNTAX Counter32
    ACCESS read-only
    STATUS mandatory
    DESCRIPTION
        "The number of authorization responses which could not
         be processed since it is made active.
        
         Reasons include inability to decrypt the response,
         invalid fields, or the response is not valid based on
         the request.
        
         This object is not instantiated for protocols which do
         not support a distinct authorization function."
    ::= { casStatisticsEntry 13 }

casAuthorResponseTime OBJECT-TYPE
    SYNTAX TimeInterval
--    Rsyntax INTEGER(0..2147483647)
    ACCESS read-only
    STATUS mandatory
    DESCRIPTION
        "Average response time for authorization requests sent
         to this server, excluding timeouts, since system
         re-initialization.
        
         This object is not instantiated for protocols which do
         not support a distinct authorization function."
    ::= { casStatisticsEntry 14 }

casAuthorTransactionSuccesses OBJECT-TYPE
    SYNTAX Counter32
    ACCESS read-only
    STATUS mandatory
    DESCRIPTION
        "The number of authorization transactions with this
         server which succeeded since it is made active.
        
         A transaction may include multiple request
         retransmissions if timeouts occur.
        
         A transaction is successful if the server responds
         with either an authorization pass or fail.
        
         This object is not instantiated for protocols which do
         not support a distinct authorization function."
    ::= { casStatisticsEntry 15 }

casAuthorTransactionFailures OBJECT-TYPE
    SYNTAX Counter32
    ACCESS read-only
    STATUS mandatory
    DESCRIPTION
        "The number of authorization transactions with this
         server which failed since it is made active.
        
         A transaction may include multiple request
         retransmissions if timeouts occur.
        
         A transaction failure occurs if maximum resends have
         been met or the server aborts the transaction.
        
         This object is not instantiated for protocols which do
         not support a distinct authorization function."
    ::= { casStatisticsEntry 16 }

casAcctRequests OBJECT-TYPE
    SYNTAX Counter32
    ACCESS read-only
    STATUS mandatory
    DESCRIPTION
        "The number of accounting requests sent to
         this server since system re-initialization.
        
         Retransmissions due to request timeouts are
         counted as distinct requests."
    ::= { casStatisticsEntry 17 }

casAcctRequestTimeouts OBJECT-TYPE
    SYNTAX Counter32
    ACCESS read-only
    STATUS mandatory
    DESCRIPTION
        "The number of accounting requests which have
         timed out since system re-initialization.
        
         A timeout results in a retransmission of the request
         If the maximum number of attempts has been reached,
         no further retransmissions will be attempted.
         "
    ::= { casStatisticsEntry 18 }

casAcctUnexpectedResponses OBJECT-TYPE
    SYNTAX Counter32
    ACCESS read-only
    STATUS mandatory
    DESCRIPTION
        "The number of unexpected accounting responses received
         from this server since system re-initialization.
        
         An example is a delayed response to a request which had
         already timed out."
    ::= { casStatisticsEntry 19 }

casAcctServerErrorResponses OBJECT-TYPE
    SYNTAX Counter32
    ACCESS read-only
    STATUS mandatory
    DESCRIPTION
        "The number of server ERROR accounting responses received
         from this server since system re-initialization.
        
         These are responses indicating that the server itself
         has identified an error with its accounting
         operation."
    ::= { casStatisticsEntry 20 }

casAcctIncorrectResponses OBJECT-TYPE
    SYNTAX Counter32
    ACCESS read-only
    STATUS mandatory
    DESCRIPTION
        "The number of accounting responses which could not
         be processed since system re-initialization.
        
         Reasons include inability to decrypt the response,
         invalid fields, or the response is not valid based on
         the request."
    ::= { casStatisticsEntry 21 }

casAcctResponseTime OBJECT-TYPE
    SYNTAX TimeInterval
--    Rsyntax INTEGER(0..2147483647)
    ACCESS read-only
    STATUS mandatory
    DESCRIPTION
        "Average response time for accounting requests sent
         to this server,, since system re-initialization
         excluding timeouts."
    ::= { casStatisticsEntry 22 }

casAcctTransactionSuccesses OBJECT-TYPE
    SYNTAX Counter32
    ACCESS read-only
    STATUS mandatory
    DESCRIPTION
        "The number of accounting transactions with this
         server which succeeded since system re-initialization.
        
         A transaction may include multiple request
         retransmissions if timeouts occur.
        
         A transaction is successful if the server responds
         with either an accounting pass or fail."
    ::= { casStatisticsEntry 23 }

casAcctTransactionFailures OBJECT-TYPE
    SYNTAX Counter32
    ACCESS read-only
    STATUS mandatory
    DESCRIPTION
        "The number of accounting transactions with this
         server which failed since system re-initialization.
        
         A transaction may include multiple request
         retransmissions if timeouts occur.
        
         A transaction failure occurs if maximum resends have
         been met or the server aborts the transaction."
    ::= { casStatisticsEntry 24 }

casState OBJECT-TYPE
    SYNTAX INTEGER {
        up(1),
        dead(2)
        }
    ACCESS read-only
    STATUS mandatory
    DESCRIPTION
        "Current state of this server.
        
             up(1)   - Server responding to requests
        
             dead(2) - Server failed to respond
        
         A server is marked dead if it does not respond after
         maximum retransmissions.
        
         A server is marked up again either after a waiting
         period or if some response is received from it.
        
         The initial value of casState is 'up(1)' at system
         re-initialization. This will only transistion to 'dead(2)'
         if an attempt to communicate fails."
    ::= { casStatisticsEntry 25 }

casCurrentStateDuration OBJECT-TYPE
    SYNTAX TimeInterval
--    Rsyntax INTEGER(0..2147483647)
    ACCESS read-only
    STATUS mandatory
    DESCRIPTION
        "This object provides the elapsed time the server has
         been in its current state as shown in casState."
    ::= { casStatisticsEntry 26 }

casPreviousStateDuration OBJECT-TYPE
    SYNTAX TimeInterval
--    Rsyntax INTEGER(0..2147483647)
    ACCESS read-only
    STATUS mandatory
    DESCRIPTION
        "This object provides the elapsed time the server was
         been in its previous state prior to the most recent
         transistion of casState.
        
         This value is zero if the server has not changed state."
    ::= { casStatisticsEntry 27 }

casTotalDeadTime OBJECT-TYPE
    SYNTAX TimeInterval
--    Rsyntax INTEGER(0..2147483647)
    ACCESS read-only
    STATUS mandatory
    DESCRIPTION
        "The total elapsed time this server's casState has
         had the value 'dead(2)' since system re-initialization."
    ::= { casStatisticsEntry 28 }

casDeadCount OBJECT-TYPE
    SYNTAX Counter32
    ACCESS read-only
    STATUS mandatory
    DESCRIPTION
        "The number of times this server's casState has
         transitioned to 'dead(2)' since system re-initialization."
    ::= { casStatisticsEntry 29 }

casServerStateChange TRAP-TYPE
-- Reverse mappable trap
    ENTERPRISE cAAAServerMIBNotificationPrefix
    VARIABLES {
        casState, casPreviousStateDuration, casTotalDeadTime }
--  Status
--    mandatory
    DESCRIPTION
        "An AAA server state change notification is generated
         whenever casState changes value."
    ::= 1

casStatisticsGroup OBJECT IDENTIFIER ::= { casMIBGroups 1 }
-- OBJECT-GROUP
--  Status
--    mandatory
--  Descr
--    Objects for providing AAA server statistics and status.
--  objects
--    casAuthenRequests, casAuthenRequestTimeouts, 
--    casAuthenUnexpectedResponses, casAuthenServerErrorResponses, 
--    casAuthenIncorrectResponses, casAuthenResponseTime, 
--    casAuthenTransactionSuccesses, casAuthenTransactionFailures, 
--    casAuthorRequests, casAuthorRequestTimeouts, 
--    casAuthorUnexpectedResponses, casAuthorServerErrorResponses, 
--    casAuthorIncorrectResponses, casAuthorResponseTime, 
--    casAuthorTransactionSuccesses, casAuthorTransactionFailures, 
--    casAcctRequests, casAcctRequestTimeouts, 
--    casAcctUnexpectedResponses, casAcctServerErrorResponses, 
--    casAcctIncorrectResponses, casAcctResponseTime, 
--    casAcctTransactionSuccesses, casAcctTransactionFailures, 
--    casState, casCurrentStateDuration, casPreviousStateDuration, 
--    casTotalDeadTime, casDeadCount

casConfigGroup OBJECT IDENTIFIER ::= { casMIBGroups 2 }
-- OBJECT-GROUP
--  Status
--    mandatory
--  Descr
--    Objects for configuring the AAA servers.
--  objects
--    casServerStateChangeEnable, casAddress, casAuthenPort, 
--    casAcctPort, casKey, casPriority, casConfigRowStatus

casMIBCompliance OBJECT IDENTIFIER ::= { casMIBCompliances 1 }
-- MODULE-COMPLIANCE
--  Status
--    mandatory
--  Descr
--    The compliance statement for entities which
--     implement the CISCO AAA Server MIB
--  Module
--    >>current<<
--   MandGroup
--    casConfigGroup
--   MandGroup
--    casStatisticsGroup
--   ObjVar
--    casAddress
--   ObjVar
--    casAuthenPort
--   ObjVar
--    casAcctPort
--   ObjVar
--    casKey
--   ObjVar
--    casConfigRowStatus


END
