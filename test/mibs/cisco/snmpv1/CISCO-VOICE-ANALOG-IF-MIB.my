-- MIB created 6/25/99 12:57:44, by
--   SMIC (the next generation) version 1.6.29, November 22, 1994.

CISCO-VOICE-ANALOG-IF-MIB DEFINITIONS ::= BEGIN

-- From file: "CISCO-VOICE-ANALOG-IF-MIB.my"

IMPORTS
    Integer32, Counter32
            FROM SNMPv2-SMI-v1
    OBJECT-TYPE
            FROM RFC-1212
    TruthValue
            FROM SNMPv2-TC-v1
    ifIndex
            FROM IF-MIB
    ciscoMgmt
            FROM CISCO-SMI;

ciscoVoiceAnalogIfMIB OBJECT IDENTIFIER ::= { ciscoMgmt 62 }
-- MODULE-IDENTITY
--  LastUpdated
--    9605150000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-voice@cisco.com
--  Descr
--    Analog Voice Interface MIB module.
--     This MIB manages the E&M, FXO, FXS         
--     Interfaces in the router.

cvaIfObjects    OBJECT IDENTIFIER ::= { ciscoVoiceAnalogIfMIB 1 }
cvaIfGeneralObjects OBJECT IDENTIFIER ::= { cvaIfObjects 1 }
cvaIfEMObjects  OBJECT IDENTIFIER ::= { cvaIfObjects 2 }
cvaIfFXOObjects OBJECT IDENTIFIER ::= { cvaIfObjects 3 }
cvaIfFXSObjects OBJECT IDENTIFIER ::= { cvaIfObjects 4 }
cvaIfMIBConformance OBJECT IDENTIFIER ::= { ciscoVoiceAnalogIfMIB 3 }
cvaIfMIBCompliances OBJECT IDENTIFIER ::= { cvaIfMIBConformance 1 }
cvaIfMIBGroups  OBJECT IDENTIFIER ::= { cvaIfMIBConformance 2 }

cvaIfCfgTable OBJECT-TYPE
    SYNTAX SEQUENCE OF CvaIfCfgEntry
    ACCESS not-accessible
    STATUS mandatory
    DESCRIPTION
        "The Analog Voice Standard Configuration Table. It contains 
         the standard configuration information of the analog          
         telephony interface."
    ::= { cvaIfGeneralObjects 1 }

cvaIfCfgEntry OBJECT-TYPE
    SYNTAX CvaIfCfgEntry
    ACCESS not-accessible
    STATUS mandatory
    DESCRIPTION
        "An entry in the configuration table for each voice analog
         interface. The entry is created when the voice analog
         hardware is detected."
    INDEX { ifIndex }
    ::= { cvaIfCfgTable 1 }

CvaIfCfgEntry ::= SEQUENCE {
    cvaIfCfgImpedance INTEGER,
    cvaIfCfgIntegratedDSP TruthValue
    }

cvaIfCfgImpedance OBJECT-TYPE
    SYNTAX INTEGER {
        other(1),
        ohms600Real(2),
        ohms600Complex(3),
        ohms900Complex(4),
        ohmsComplex1(5),
        ohmsComplex2(6)
        }
    ACCESS read-write
    STATUS mandatory
    DESCRIPTION
        "Specifies the terminating impedance of voice analog
         interfaces.
         other          - none of the following; arbitrary,
                          within limits, for special cases.
         ohms600Real    - 600 Ohms.
         ohms600Complex - 600 Ohms + 2.16uF
         ohms900Complex - 900 Ohms + 2.16uF.
         ohmsComplex1   - complex 1; 
                          220 Ohms + 820 Ohms || 115nF.
                          This impedance is primarily used in
                          Germany.
         ohmsComplex2   - complex 2;
                          270 Ohms + 750 Ohms || 150nF.
                          This impedance is primarily used in 
                          United Kingdom and Sweden."
    ::= { cvaIfCfgEntry 1 }

cvaIfCfgIntegratedDSP OBJECT-TYPE
    SYNTAX TruthValue
--    Rsyntax INTEGER {
--        true(1),
--        false(2)
--        }
    ACCESS read-only
    STATUS mandatory
    DESCRIPTION
        "Indicates whether the interface has an integrated
         Digital Signal processing (DSP) unit."
    ::= { cvaIfCfgEntry 2 }

cvaIfStatusTable OBJECT-TYPE
    SYNTAX SEQUENCE OF CvaIfStatusEntry
    ACCESS not-accessible
    STATUS mandatory
    DESCRIPTION
        "The Analog Voice Status Table.  It contains general 
         information about the status of Analog Telephony interface
         including the error statistics."
    ::= { cvaIfGeneralObjects 2 }

cvaIfStatusEntry OBJECT-TYPE
    SYNTAX CvaIfStatusEntry
    ACCESS not-accessible
    STATUS mandatory
    DESCRIPTION
        "An entry in the status table for each Analog voice interface."
    INDEX { ifIndex }
-- Augments cvaIfCfgEntry
    ::= { cvaIfStatusTable 1 }

CvaIfStatusEntry ::= SEQUENCE {
    cvaIfStatusInfoType INTEGER,
    cvaIfMaintenanceMode INTEGER,
    cvaIfStatusSignalErrors Counter32
    }

cvaIfStatusInfoType OBJECT-TYPE
    SYNTAX INTEGER {
        none(1),
        voice(2),
        g3Fax(3)
        }
    ACCESS read-only
    STATUS mandatory
    DESCRIPTION
        "The information transfer services for the current
         or last call.
         none     - no information transfer service
         voice    - analog voice.
         g3Fax    - Group 3 FAX. "
    ::= { cvaIfStatusEntry 1 }

cvaIfMaintenanceMode OBJECT-TYPE
    SYNTAX INTEGER {
        none(1),
        hostCompressedLoopback(2),
        hostUncompressedLoopback(3),
        ifCompressedLoopback(4),
        ifUncompressedLoopback(5)
        }
    ACCESS read-only
    STATUS mandatory
    DESCRIPTION
        "Indicates the maintenance modes of the Analog voice interface.
        
                       Managed system
              +=============+=============================+
              |   Voice     |   +===========+   telephony |
        <=====+ application +===+   CODEC   +===end point +=== test
        IP    |   (Host)    | . +===========+ .(Interface)|   equipment
        backbone +=============+=============================+
                              .               .
          Host      ======>===+               .
          Compressed   <======+               .
                              .               .
          Host      ===================>======+
          Uncompressed <======================+
                              .               .
          Interface           +========<==========================    
          Compressed          +==================================>
                              .               . 
          Interface           .               +===<===============    
          Uncompressed        .               +==================>
                            Compress      Uncompress 
                            Loopback      Loopback
                            point         point
        
         none(1)  - the interface is not in maintenance mode.
         hostCompressedLoopback(2) - Host Compressed Loopback.
            This mode is set by the managed system to perform the 
            compressed voice loopback test. The voice packet is passed
            by voice application to the interface associated CODEC.
            Instead of feeding these into the CODEC for decompression,
            they are immediately sent back to the voice application as
            if they had originated locally and been compressed.
        
         hostUncompressedLoopback(3) - Host Uncompressed Loopback.
            This mode is set by the managed system to perform the 
            uncompressed voice loopback test. The voice packet is 
            sent by voice application all the way through the
            interface associated CODEC and then turned around instead
            of being sent to the telephony endpoint.
        
         ifCompressedLoopback(4) - Interface Compressed Loopback.
            This mode is set by the managed system to perform the 
            interface uncompressed voice loopback test for the 
            external test equipment that is connected to the voice
            interface.
            The voice samples are sent from the test equipment all the
            way through the interface associated CODEC and then turned
            around instead of being sent to voice application.
        
         ifUncompressedLoopback(5) - Interface Uncompressed Loopback.
            This mode is set by the managed system to perform the 
            interface uncompressed voice loopback test for the
            external test equipment that is connected to the voice
            interface.
            The voice samples are sent from the test equipment to the
            interface associated CODEC. Instead of feeding the voice
            samples into the CODEC for compression, they are 
            immediately sent back to the telephony interface."
    ::= { cvaIfStatusEntry 2 }

cvaIfStatusSignalErrors OBJECT-TYPE
    SYNTAX Counter32
    ACCESS read-only
    STATUS mandatory
    DESCRIPTION
        "Accumulated number of signaling protocol errors that are
         detected in the interface since system startup."
    ::= { cvaIfStatusEntry 3 }

cvaIfEMCfgTable OBJECT-TYPE
    SYNTAX SEQUENCE OF CvaIfEMCfgEntry
    ACCESS not-accessible
    STATUS mandatory
    DESCRIPTION
        "The E&M standard configuration table. It contains 
         the current setting of E&M configurable parameters."
    ::= { cvaIfEMObjects 1 }

cvaIfEMCfgEntry OBJECT-TYPE
    SYNTAX CvaIfEMCfgEntry
    ACCESS not-accessible
    STATUS mandatory
    DESCRIPTION
        "An entry in the standard configuration table for
         each E&M tie trunk interface."
    INDEX { ifIndex }
    ::= { cvaIfEMCfgTable 1 }

CvaIfEMCfgEntry ::= SEQUENCE {
    cvaIfEMCfgSignalType INTEGER,
    cvaIfEMCfgOperation INTEGER,
    cvaIfEMCfgType INTEGER,
    cvaIfEMCfgDialType INTEGER
    }

cvaIfEMCfgSignalType OBJECT-TYPE
    SYNTAX INTEGER {
        winkStart(1),
        immediateDial(2),
        delayDial(3)
        }
    ACCESS read-write
    STATUS mandatory
    DESCRIPTION
        "The signaling type of E&M tie trunk interface.
         winkStart - the calling side seizes the line by going
                     off-hook on its E lead but waits for a short
                     off-hook 'wink' indication on its M lead from
                     the called side before sending address
                     information as DTMF digits.
         immediateDial - the calling side seizes the line by going
                     off-hook on its E lead and sends sends address
                     information as DTMF digits.
         delayDial - the calling side seizes the line by going
                     off-hook on its E lead. After a timing interval,
                     the calling side looks at the supervision 
                     from the called side. If the supervision is
                     on-hook, the calling side starts sending
                     information as DTMF digits; otherwise, the calling
                     side waits until the called side goes
                     on-hook and then starts sending address
                     information.
         The default value of this object is winkStart(1)."
    REFERENCE
        "EIA/TIA-464B: Sections 4.1.3.4.1 Signaling Protocols."
    ::= { cvaIfEMCfgEntry 1 }

cvaIfEMCfgOperation OBJECT-TYPE
    SYNTAX INTEGER {
        twoWires(1),
        fourWires(2)
        }
    ACCESS read-write
    STATUS mandatory
    DESCRIPTION
        "Specify the operation of the E&M signal.
         twoWires  - 2-wire operation.
         fourWires - 4-wire operation.
         The default value of this object is twoWires(1)."
    ::= { cvaIfEMCfgEntry 2 }

cvaIfEMCfgType OBJECT-TYPE
    SYNTAX INTEGER {
        typeI(1),
        typeII(2),
        typeIII(3),
        typeIV(4),
        typeV(5)
        }
    ACCESS read-write
    STATUS mandatory
    DESCRIPTION
        "Specifies the E&M Lead Signaling type.
         LEGEND: V     = -48V
         /\/\/ = detector/resister
         X     = normally open relay contact
         +     = normally closed relay contact
         G     = ground
         SB    = Signal Battery
         SG    = Signal Ground
        
         typeI -
              Leads:  E (output, relay to ground)
                      M (input, referenced to ground)
        
              The tie line equipment (switch/router/etc) generates the
              E-signal to the PBX type grounding the E-lead.  
              The tie line equipment detects the M-signal by detecting
              current flow to ground.  A common ground must exist 
              between the line equipment and the PBX.
        
                       PBX    |  TIE LINE
                              |
              E:   V--/\/\/---|-----X----G
                              |
              M:   V----X-----|---/\/\/--G
        
         typeII -
              Leads: E (output, relay to SG)
              M (input, referenced to ground)
              SB (feed for M, connected to -48V)
              SG (return for E, galvanically isolated from ground)
        
              This interface requires no common ground between the
              equipment, thus avoiding ground loop noise problems.
              E-signal is generated toward the PBX by connecting it
              to SG.  M-signal is indicated by the PBX connecting
              it to SB.  While this interface does NOT require a
              common ground, it does have the tendency to inject
              noise into the audio paths since it is asymmetrical
              with respect to current flow between devices.
        
                       PBX    |  TIE LINE
                              |
              E:   V--/\/\/---|-----X----
                              |          |
              SG:  G----------|----------
                              |
              M:    ----X-----|---/\/\/--G
                              |          |
              SB:   ----------|----------V
        
         typeIII -
              Leads: E (output, relay to ground)
              M (input, referenced to ground)
              SB (connected to -48V)
              SG (connected to ground) 
        
              This interface operates similar to type I with respect
              to the E-signal. The M-signal, however, is indicated by
              the PBX connecting it to SB on assertion, and alternately
              connecting it to SG during inactivity. Unfortunately, a 
              common ground must be shared between the equipment.
        
                       PBX    |  TIE LINE
                              |
              E:   V--/\/\/---|-----X----G
                              |          
              SG:   ----------|----------G
                       +      |
              M:    ----------|---/\/\/--G
                   X          |
              SB:   ----------|----------V
        
         typeIV -
              Leads: E (output, relay to SG)
              M (input, referenced to -48V)
              SB (feed for M, connected to ground)
              SG (return for E, galvanically isolated from ground)
        
              This interface is fully symmetrical; it does not require
              a common ground, does not inject noise into audio paths,
              and can be connected back to back by swapping E/SG for 
              M/SB.  E-signal is indicated to the PBX by connecting it
              to SG.  M-signal is provided by the PBX connecting it to
              SB.
        
                       PBX    |  TIE LINE
                              |
              E:   V--/\/\/---|-----X----
                              |          |
              SG:  G----------|----------
                              |
              M:    ----------|---/\/\/--V
                   X          |
              SB:   ----------|----------G
        
         typeV -
              Leads: E (output, relay to ground)
                     M (input, referenced to -48V)
        
              Type V line equipment indicates E-signal to the PBX by
              grounding the E-lead. The PBX indicates M-signal by 
              grounding the M-lead.  This interface does require a
              common ground, but does allow back to back connections
              by swapping E for M.  This interface is quasi-symmetric
              in that while the line is up, current flow is more or
              less equal between the PBX and line equipment. But noise
              injection is still a problem.
        
                       PBX    |  TIE LINE
                              |
              E:   V--/\/\/---|-----X----G
                              |          
              M:   G-----X----|---/\/\/--V
                              |
         The default value of this object is typeI(1)."
    REFERENCE
        "EIA/TIA-464B: Sections 4.2.3 E&M Lead Signaling. "
    ::= { cvaIfEMCfgEntry 3 }

cvaIfEMCfgDialType OBJECT-TYPE
    SYNTAX INTEGER {
        dtmf(1),
        pulse(2)
        }
    ACCESS read-write
    STATUS mandatory
    DESCRIPTION
        "Specifies the out dialing type of E&M interface.
         dtmf  - DTMF digit.
         pulse - pulse.
         The default value of this object is dtmf(1)."
    ::= { cvaIfEMCfgEntry 4 }

cvaIfEMStatusTable OBJECT-TYPE
    SYNTAX SEQUENCE OF CvaIfEMStatusEntry
    ACCESS not-accessible
    STATUS mandatory
    DESCRIPTION
        "The E&M interface Table.  The table contains 
         the status of the E&M tie trunk interface."
    ::= { cvaIfEMObjects 2 }

cvaIfEMStatusEntry OBJECT-TYPE
    SYNTAX CvaIfEMStatusEntry
    ACCESS not-accessible
    STATUS mandatory
    DESCRIPTION
        "An entry in the status table for each E&M interface."
    INDEX { ifIndex }
-- Augments cvaIfEMCfgEntry
    ::= { cvaIfEMStatusTable 1 }

CvaIfEMStatusEntry ::= SEQUENCE {
    cvaIfEMInSeizureActive TruthValue,
    cvaIfEMOutSeizureActive TruthValue
    }

cvaIfEMInSeizureActive OBJECT-TYPE
    SYNTAX TruthValue
--    Rsyntax INTEGER {
--        true(1),
--        false(2)
--        }
    ACCESS read-only
    STATUS mandatory
    DESCRIPTION
        "This object contains the incoming seizure state of the E&M 
         interface. If the value is true, then the interface has an 
         incoming trunk seizure active; otherwise, it doesn't."
    ::= { cvaIfEMStatusEntry 1 }

cvaIfEMOutSeizureActive OBJECT-TYPE
    SYNTAX TruthValue
--    Rsyntax INTEGER {
--        true(1),
--        false(2)
--        }
    ACCESS read-only
    STATUS mandatory
    DESCRIPTION
        "This object contains the outgoing seizure state of the E&M 
         interface. If the value is true, then the interface has an 
         outgoing trunk seizure active; otherwise, it doesn't."
    ::= { cvaIfEMStatusEntry 2 }

cvaIfEMTimingTable OBJECT-TYPE
    SYNTAX SEQUENCE OF CvaIfEMTimingEntry
    ACCESS not-accessible
    STATUS mandatory
    DESCRIPTION
        "The E&M tie trunk Timing Parameters table. It 
         contains the configuration of the various E&M signaling
         protocol timing parameters."
    ::= { cvaIfEMObjects 3 }

cvaIfEMTimingEntry OBJECT-TYPE
    SYNTAX CvaIfEMTimingEntry
    ACCESS not-accessible
    STATUS mandatory
    DESCRIPTION
        "An entry in the E&M Timing Parameters Table for
         each E&M interface."
    INDEX { ifIndex }
-- Augments cvaIfEMCfgEntry
    ::= { cvaIfEMTimingTable 1 }

CvaIfEMTimingEntry ::= SEQUENCE {
    cvaIfEMTimingDigitDuration Integer32,
    cvaIfEMTimingInterDigitDuration Integer32,
    cvaIfEMTimingPulseRate Integer32,
    cvaIfEMTimingPulseInterDigitDuration Integer32,
    cvaIfEMTimingClearWaitDuration Integer32,
    cvaIfEMTimingMaxWinkWaitDuration Integer32,
    cvaIfEMTimingMaxWinkDuration Integer32,
    cvaIfEMTimingDelayStart Integer32,
    cvaIfEMTimingMaxDelayDuration Integer32,
    cvaIfEMTimingMinDelayPulseWidth Integer32
    }

cvaIfEMTimingDigitDuration OBJECT-TYPE
    SYNTAX Integer32(50..500)
--  Units
--    milliseconds
    ACCESS read-write
    STATUS mandatory
    DESCRIPTION
        "Outgoing DTMF digit duration in milliseconds.
         The default value of this object is 100 milliseconds."
    ::= { cvaIfEMTimingEntry 1 }

cvaIfEMTimingInterDigitDuration OBJECT-TYPE
    SYNTAX Integer32(50..500)
--  Units
--    milliseconds
    ACCESS read-write
    STATUS mandatory
    DESCRIPTION
        "Outgoing DTMF inter-digit duration in milliseconds.
         The default value of this object is 100 milliseconds."
    ::= { cvaIfEMTimingEntry 2 }

cvaIfEMTimingPulseRate OBJECT-TYPE
    SYNTAX Integer32(10..20)
--  Units
--    pulses per second
    ACCESS read-write
    STATUS mandatory
    DESCRIPTION
        "Outgoing pulse dialing rate in pulses per second (pps).
         The default value of this object is 10 pps."
    ::= { cvaIfEMTimingEntry 3 }

cvaIfEMTimingPulseInterDigitDuration OBJECT-TYPE
    SYNTAX Integer32(100..1000)
--  Units
--    milliseconds
    ACCESS read-write
    STATUS mandatory
    DESCRIPTION
        "Outgoing Pulse dialing inter-digit timing in milliseconds.
         The default value of this object is 500 milliseconds."
    ::= { cvaIfEMTimingEntry 4 }

cvaIfEMTimingClearWaitDuration OBJECT-TYPE
    SYNTAX Integer32(200..2000)
--  Units
--    milliseconds
    ACCESS read-write
    STATUS mandatory
    DESCRIPTION
        "Time of Inactive seizure signal to declare call cleared.
         The default value of this object is 400 milliseconds."
    ::= { cvaIfEMTimingEntry 5 }

cvaIfEMTimingMaxWinkWaitDuration OBJECT-TYPE
    SYNTAX Integer32(100..5000)
--  Units
--    milliseconds
    ACCESS read-write
    STATUS mandatory
    DESCRIPTION
        "Maximum time to wait from the outgoing seizure of the line
         to the time of sending out a wink-pulse. 
         The default value of this object is 200 milliseconds."
    ::= { cvaIfEMTimingEntry 6 }

cvaIfEMTimingMaxWinkDuration OBJECT-TYPE
    SYNTAX Integer32(100..3000)
--  Units
--    milliseconds
    ACCESS read-write
    STATUS mandatory
    DESCRIPTION
        "Maximum outgoing wink duration (between the wink-pulse leading
         edge and trailing edge) for wink start signaling.
         The default value of this object is 200 milliseconds."
    ::= { cvaIfEMTimingEntry 7 }

cvaIfEMTimingDelayStart OBJECT-TYPE
    SYNTAX Integer32(20..2000)
--  Units
--    milliseconds
    ACCESS read-write
    STATUS mandatory
    DESCRIPTION
        "Minimum time to wait from outgoing seizure to
         out-dialing digits for delay start signaling.
         The default value of this object is 300 milliseconds."
    ::= { cvaIfEMTimingEntry 8 }

cvaIfEMTimingMaxDelayDuration OBJECT-TYPE
    SYNTAX Integer32(100..5000)
--  Units
--    milliseconds
    ACCESS read-write
    STATUS mandatory
    DESCRIPTION
        "Maximum time to wait from outgoing seizure to
         out-dialing digits. If the far end does not allow to
         send digits after the duration specified in the object,
         a reorder tone will be sent to the calling party.
         The default value of this object is 2000 milliseconds."
    ::= { cvaIfEMTimingEntry 9 }

cvaIfEMTimingMinDelayPulseWidth OBJECT-TYPE
    SYNTAX Integer32(0 | 140..5000)
--  Units
--    milliseconds
    ACCESS read-write
    STATUS mandatory
    DESCRIPTION
        "Minimum delay-dial pulse duration for incoming call.
         If the value of this object is 0, then no delay-dial
         is sent to the far end for the incoming call.
         The default value of this object is 140 milliseconds."
    ::= { cvaIfEMTimingEntry 10 }

cvaIfFXOCfgTable OBJECT-TYPE
    SYNTAX SEQUENCE OF CvaIfFXOCfgEntry
    ACCESS not-accessible
    STATUS mandatory
    DESCRIPTION
        "The FXO standard configuration table. It contains 
         FXO configuration parameters, one entry per FXO interface.
         The configuration information of this table is set by 
         hardware with its default setting or CLI during the hardware 
         installation time."
    ::= { cvaIfFXOObjects 1 }

cvaIfFXOCfgEntry OBJECT-TYPE
    SYNTAX CvaIfFXOCfgEntry
    ACCESS not-accessible
    STATUS mandatory
    DESCRIPTION
        "An entry in the standard configuration table for
         each FXO interface."
    INDEX { ifIndex }
    ::= { cvaIfFXOCfgTable 1 }

CvaIfFXOCfgEntry ::= SEQUENCE {
    cvaIfFXOCfgSignalType INTEGER,
    cvaIfFXOCfgNumberRings Integer32,
    cvaIfFXOCfgSupDisconnect TruthValue,
    cvaIfFXOCfgDialType INTEGER
    }

cvaIfFXOCfgSignalType OBJECT-TYPE
    SYNTAX INTEGER {
        fxoLoopStart(1),
        fxoGroundStart(2)
        }
    ACCESS read-write
    STATUS mandatory
    DESCRIPTION
        "the signaling type of FXO interface.
         fxoLoopStart   - loop start.
         fxoGroundStart - ground start.
         The default value of this object is fxoLoopStart(1)."
    ::= { cvaIfFXOCfgEntry 1 }

cvaIfFXOCfgNumberRings OBJECT-TYPE
    SYNTAX Integer32(1..10)
--  Units
--    rings
    ACCESS read-write
    STATUS mandatory
    DESCRIPTION
        "The number of rings detected before closing loop.
         The default value of this object is 1 ring."
    ::= { cvaIfFXOCfgEntry 2 }

cvaIfFXOCfgSupDisconnect OBJECT-TYPE
    SYNTAX TruthValue
--    Rsyntax INTEGER {
--        true(1),
--        false(2)
--        }
    ACCESS read-write
    STATUS mandatory
    DESCRIPTION
        " Specifies whether a supervisory disconnect signal (CPC) will 
          be presented to the interface when the connected party at 
          the interface hangs up.
          The default value of this object is 'true'."
    ::= { cvaIfFXOCfgEntry 3 }

cvaIfFXOCfgDialType OBJECT-TYPE
    SYNTAX INTEGER {
        dtmf(1),
        pulse(2)
        }
    ACCESS read-write
    STATUS mandatory
    DESCRIPTION
        "Specifies the out dialing type of FXO interface.
         dtmf  - DTMF digit.
         pulse - pulse.
         The default value of this object is dtmf(1)."
    ::= { cvaIfFXOCfgEntry 4 }

cvaIfFXOStatusTable OBJECT-TYPE
    SYNTAX SEQUENCE OF CvaIfFXOStatusEntry
    ACCESS not-accessible
    STATUS mandatory
    DESCRIPTION
        "The Foreign Exchange Office (FXO) interface Status Table.
         It contains hook status, ring detection and other states of
         the interface."
    ::= { cvaIfFXOObjects 2 }

cvaIfFXOStatusEntry OBJECT-TYPE
    SYNTAX CvaIfFXOStatusEntry
    ACCESS not-accessible
    STATUS mandatory
    DESCRIPTION
        "An entry in the status table for each FXO interface."
    INDEX { ifIndex }
-- Augments cvaIfFXOCfgEntry
    ::= { cvaIfFXOStatusTable 1 }

CvaIfFXOStatusEntry ::= SEQUENCE {
    cvaIfFXOHookStatus INTEGER,
    cvaIfFXORingDetect TruthValue,
    cvaIfFXORingGround TruthValue,
    cvaIfFXOTipGround TruthValue
    }

cvaIfFXOHookStatus OBJECT-TYPE
    SYNTAX INTEGER {
        onHook(1),
        offHook(2)
        }
    ACCESS read-only
    STATUS mandatory
    DESCRIPTION
        "This object contains the hook status of FXO interface.
         onHook  - Present the onHook to the connected equipment.
         offHook - Present the offHook to the connected equipment."
    ::= { cvaIfFXOStatusEntry 1 }

cvaIfFXORingDetect OBJECT-TYPE
    SYNTAX TruthValue
--    Rsyntax INTEGER {
--        true(1),
--        false(2)
--        }
    ACCESS read-only
    STATUS mandatory
    DESCRIPTION
        "This object contains the ring detect indication. If the
         value is true, then the interface detects ring from PBX or
         CO; otherwise, it doesn't."
    ::= { cvaIfFXOStatusEntry 2 }

cvaIfFXORingGround OBJECT-TYPE
    SYNTAX TruthValue
--    Rsyntax INTEGER {
--        true(1),
--        false(2)
--        }
    ACCESS read-only
    STATUS mandatory
    DESCRIPTION
        "This object contains the incoming ring ground indication.
         It is only valid when the cvaIfFXOCfgSignalType is
         fxoGroundStart. If the object is true, then the interface 
         is presenting a ring ground to the connected equipment; 
         otherwise, it doesn't."
    ::= { cvaIfFXOStatusEntry 3 }

cvaIfFXOTipGround OBJECT-TYPE
    SYNTAX TruthValue
--    Rsyntax INTEGER {
--        true(1),
--        false(2)
--        }
    ACCESS read-only
    STATUS mandatory
    DESCRIPTION
        "This object contains the incoming tip ground indication. 
         It is only valid when the cvaIfFXOCfgSignalType is
         fxoGroundStart. If the object is true, then the interface
         is detecting a tip ground at the interface; otherwise, 
         it doesn't."
    ::= { cvaIfFXOStatusEntry 4 }

cvaIfFXOTimingTable OBJECT-TYPE
    SYNTAX SEQUENCE OF CvaIfFXOTimingEntry
    ACCESS not-accessible
    STATUS mandatory
    DESCRIPTION
        "The FXO interface Timing Parameters table. It 
         contains the configuration of the various FXO signaling
         protocol timing parameters."
    ::= { cvaIfFXOObjects 3 }

cvaIfFXOTimingEntry OBJECT-TYPE
    SYNTAX CvaIfFXOTimingEntry
    ACCESS not-accessible
    STATUS mandatory
    DESCRIPTION
        "An entry in the FXO Timing Parameters Table for
         each FXO interface."
    INDEX { ifIndex }
-- Augments cvaIfFXOCfgEntry
    ::= { cvaIfFXOTimingTable 1 }

CvaIfFXOTimingEntry ::= SEQUENCE {
    cvaIfFXOTimingDigitDuration Integer32,
    cvaIfFXOTimingInterDigitDuration Integer32,
    cvaIfFXOTimingPulseRate Integer32,
    cvaIfFXOTimingPulseInterDigitDuration Integer32
    }

cvaIfFXOTimingDigitDuration OBJECT-TYPE
    SYNTAX Integer32(50..500)
--  Units
--    milliseconds
    ACCESS read-write
    STATUS mandatory
    DESCRIPTION
        "Outgoing DTMF digit duration in milliseconds.
         The default value of this object is 100 msec."
    ::= { cvaIfFXOTimingEntry 1 }

cvaIfFXOTimingInterDigitDuration OBJECT-TYPE
    SYNTAX Integer32(50..500)
--  Units
--    milliseconds
    ACCESS read-write
    STATUS mandatory
    DESCRIPTION
        "Outgoing DTMF inter-digit duration in milliseconds.
         The default value of this object is 100 msec."
    ::= { cvaIfFXOTimingEntry 2 }

cvaIfFXOTimingPulseRate OBJECT-TYPE
    SYNTAX Integer32(10..20)
--  Units
--    pulses per second
    ACCESS read-write
    STATUS mandatory
    DESCRIPTION
        "Outgoing pulse dialing rate in pulses per second (pps).
         The default value of this object is 10 pps.   "
    ::= { cvaIfFXOTimingEntry 3 }

cvaIfFXOTimingPulseInterDigitDuration OBJECT-TYPE
    SYNTAX Integer32(100..1000)
--  Units
--    milliseconds
    ACCESS read-write
    STATUS mandatory
    DESCRIPTION
        "Outgoing pulse dialing inter-digit timing in milliseconds.
         The default value of this object is 500 milliseconds.   "
    ::= { cvaIfFXOTimingEntry 4 }

cvaIfFXSCfgTable OBJECT-TYPE
    SYNTAX SEQUENCE OF CvaIfFXSCfgEntry
    ACCESS not-accessible
    STATUS mandatory
    DESCRIPTION
        "The FXS standard configuration table. It contains
         FXS configuration parameters, one entry per FXS interface.
         The configuration information of this table is set by 
         hardware with its default setting or CLI during the hardware 
         installation time."
    ::= { cvaIfFXSObjects 1 }

cvaIfFXSCfgEntry OBJECT-TYPE
    SYNTAX CvaIfFXSCfgEntry
    ACCESS not-accessible
    STATUS mandatory
    DESCRIPTION
        "An entry in the standard configuration table for
         each FXS interface."
    INDEX { ifIndex }
    ::= { cvaIfFXSCfgTable 1 }

CvaIfFXSCfgEntry ::= SEQUENCE {
    cvaIfFXSCfgSignalType INTEGER,
    cvaIfFXSRingFrequency INTEGER
    }

cvaIfFXSCfgSignalType OBJECT-TYPE
    SYNTAX INTEGER {
        fxsLoopStart(1),
        fxsGroundStart(2)
        }
    ACCESS read-write
    STATUS mandatory
    DESCRIPTION
        "the signaling type of FXS interface.
         fxsLoopStart   - loop start.
         fxsGroundStart - ground start.
         The default value of this object is fxsLoopStart(1)."
    ::= { cvaIfFXSCfgEntry 1 }

cvaIfFXSRingFrequency OBJECT-TYPE
    SYNTAX INTEGER {
        ringFrequency25(1),
        ringFrequency50(2),
        ringFrequency20(3),
        ringFrequency30(4)
        }
    ACCESS read-write
    STATUS mandatory
    DESCRIPTION
        "the ring  frequency to be used in the FXS interface.
         ringFrequency25  - ring frequency 25 Hertz.
         ringFrequency50  - ring frequency 50 Hertz.
         ringFrequency20  - ring frequency 20 Hertz.
         ringFrequency30  - ring frequency 30 Hertz."
    ::= { cvaIfFXSCfgEntry 2 }

cvaIfFXSStatusTable OBJECT-TYPE
    SYNTAX SEQUENCE OF CvaIfFXSStatusEntry
    ACCESS not-accessible
    STATUS mandatory
    DESCRIPTION
        "The Foreign Exchange Station (FXS) interface Status Table.
         It contains hook status, ring active and other states of
         the interface."
    ::= { cvaIfFXSObjects 2 }

cvaIfFXSStatusEntry OBJECT-TYPE
    SYNTAX CvaIfFXSStatusEntry
    ACCESS not-accessible
    STATUS mandatory
    DESCRIPTION
        "An entry in the status table for each FXS interface."
    INDEX { ifIndex }
-- Augments cvaIfFXSCfgEntry
    ::= { cvaIfFXSStatusTable 1 }

CvaIfFXSStatusEntry ::= SEQUENCE {
    cvaIfFXSHookStatus INTEGER,
    cvaIfFXSRingActive TruthValue,
    cvaIfFXSRingGround TruthValue,
    cvaIfFXSTipGround TruthValue
    }

cvaIfFXSHookStatus OBJECT-TYPE
    SYNTAX INTEGER {
        onHook(1),
        offHook(2)
        }
    ACCESS read-only
    STATUS mandatory
    DESCRIPTION
        "This object contains the hook status of FXS interface.
         onHook - the connected equipment(e.g., phone) is onHook.
         offHook - the connected equipment is offHook."
    ::= { cvaIfFXSStatusEntry 1 }

cvaIfFXSRingActive OBJECT-TYPE
    SYNTAX TruthValue
--    Rsyntax INTEGER {
--        true(1),
--        false(2)
--        }
    ACCESS read-only
    STATUS mandatory
    DESCRIPTION
        "This object contains the outgoing ring active indication. If
         the object value is true, then the interface is currently 
         generating ring out to the Key Telephone System (KTS) or
         Plain Old Telephone (POT); otherwise, it doesn't."
    ::= { cvaIfFXSStatusEntry 2 }

cvaIfFXSRingGround OBJECT-TYPE
    SYNTAX TruthValue
--    Rsyntax INTEGER {
--        true(1),
--        false(2)
--        }
    ACCESS read-only
    STATUS mandatory
    DESCRIPTION
        "This object contains the incoming ring ground indication.
         It is only valid when the cvaIfFXSCfgSignalType is
         fxsGroundStart. If the object is true, then the interface 
         is presenting a ring ground to the connected equipment; 
         otherwise, it doesn't."
    ::= { cvaIfFXSStatusEntry 3 }

cvaIfFXSTipGround OBJECT-TYPE
    SYNTAX TruthValue
--    Rsyntax INTEGER {
--        true(1),
--        false(2)
--        }
    ACCESS read-only
    STATUS mandatory
    DESCRIPTION
        "This object contains the incoming tip ground indication. 
         It is only valid when the cvaIfFXSCfgSignalType is
         fxsGroundStart. If the object is true, then the interface
         is detecting a tip ground at the interface; otherwise, 
         it doesn't."
    ::= { cvaIfFXSStatusEntry 4 }

cvaIfFXSTimingTable OBJECT-TYPE
    SYNTAX SEQUENCE OF CvaIfFXSTimingEntry
    ACCESS not-accessible
    STATUS mandatory
    DESCRIPTION
        "The FXS interface Timing Parameters table. It 
         contains the configuration of the various FXS signaling
         protocol timing parameters."
    ::= { cvaIfFXSObjects 3 }

cvaIfFXSTimingEntry OBJECT-TYPE
    SYNTAX CvaIfFXSTimingEntry
    ACCESS not-accessible
    STATUS mandatory
    DESCRIPTION
        "An entry in the FXS Timing Parameters Table for
         each FXS interface."
    INDEX { ifIndex }
-- Augments cvaIfFXSCfgEntry
    ::= { cvaIfFXSTimingTable 1 }

CvaIfFXSTimingEntry ::= SEQUENCE {
    cvaIfFXSTimingDigitDuration Integer32,
    cvaIfFXSTimingInterDigitDuration Integer32
    }

cvaIfFXSTimingDigitDuration OBJECT-TYPE
    SYNTAX Integer32(50..500)
--  Units
--    milliseconds
    ACCESS read-write
    STATUS mandatory
    DESCRIPTION
        "Outgoing DTMF digit duration in milliseconds.
         The default value of this object is 100 milliseconds.   "
    ::= { cvaIfFXSTimingEntry 1 }

cvaIfFXSTimingInterDigitDuration OBJECT-TYPE
    SYNTAX Integer32(50..500)
--  Units
--    milliseconds
    ACCESS read-write
    STATUS mandatory
    DESCRIPTION
        "Outgoing DTMF inter-digit duration in milliseconds.
         The default value of this object is 100 milliseconds.   "
    ::= { cvaIfFXSTimingEntry 2 }

cvaIfGeneralGroup OBJECT IDENTIFIER ::= { cvaIfMIBGroups 1 }
-- OBJECT-GROUP
--  Status
--    mandatory
--  Descr
--    The collection of objects providing general information
--     about the Cisco Analog Voice interfaces.
--  objects
--    cvaIfCfgIntegratedDSP, cvaIfCfgImpedance, cvaIfStatusInfoType, 
--    cvaIfMaintenanceMode, cvaIfStatusSignalErrors

cvaIfEMGroup OBJECT IDENTIFIER ::= { cvaIfMIBGroups 2 }
-- OBJECT-GROUP
--  Status
--    mandatory
--  Descr
--    The collection of objects providing information
--     about the Cisco E&M trunk interface.
--  objects
--    cvaIfEMInSeizureActive, cvaIfEMOutSeizureActive, 
--    cvaIfEMCfgSignalType, cvaIfEMCfgOperation, cvaIfEMCfgType, 
--    cvaIfEMCfgDialType, cvaIfEMTimingDigitDuration, 
--    cvaIfEMTimingInterDigitDuration, cvaIfEMTimingPulseRate, 
--    cvaIfEMTimingPulseInterDigitDuration, 
--    cvaIfEMTimingClearWaitDuration, 
--    cvaIfEMTimingMaxWinkWaitDuration, 
--    cvaIfEMTimingMaxWinkDuration, cvaIfEMTimingDelayStart, 
--    cvaIfEMTimingMaxDelayDuration, 
--    cvaIfEMTimingMinDelayPulseWidth

cvaIfFXOGroup OBJECT IDENTIFIER ::= { cvaIfMIBGroups 3 }
-- OBJECT-GROUP
--  Status
--    mandatory
--  Descr
--    The collection of objects providing information
--     about the Cisco FXO interface.
--  objects
--    cvaIfFXOHookStatus, cvaIfFXORingDetect, cvaIfFXORingGround, 
--    cvaIfFXOTipGround, cvaIfFXOCfgSignalType, 
--    cvaIfFXOCfgNumberRings, cvaIfFXOCfgSupDisconnect, 
--    cvaIfFXOCfgDialType, cvaIfFXOTimingDigitDuration, 
--    cvaIfFXOTimingInterDigitDuration, cvaIfFXOTimingPulseRate, 
--    cvaIfFXOTimingPulseInterDigitDuration

cvaIfFXSGroup OBJECT IDENTIFIER ::= { cvaIfMIBGroups 4 }
-- OBJECT-GROUP
--  Status
--    mandatory
--  Descr
--    The collection of objects providing information
--     about the Cisco FXS interface.
--  objects
--    cvaIfFXSHookStatus, cvaIfFXSRingActive, cvaIfFXSRingGround, 
--    cvaIfFXSTipGround, cvaIfFXSCfgSignalType, 
--    cvaIfFXSRingFrequency, cvaIfFXSTimingDigitDuration, 
--    cvaIfFXSTimingInterDigitDuration

cvaIfMIBCompliance OBJECT IDENTIFIER ::= { cvaIfMIBCompliances 1 }
-- MODULE-COMPLIANCE
--  Status
--    mandatory
--  Descr
--    The compliance statement for entities which implement
--     the Cisco Analog Voice interface MIB
--  Module
--    >>current<<
--   MandGroup
--    cvaIfGeneralGroup
--   OptGroup
--    cvaIfEMGroup
--   OptGroup
--    cvaIfFXOGroup
--   OptGroup
--    cvaIfFXSGroup
--   ObjVar
--    cvaIfCfgImpedance
--   ObjVar
--    cvaIfEMCfgSignalType
--   ObjVar
--    cvaIfEMCfgOperation
--   ObjVar
--    cvaIfEMCfgType
--   ObjVar
--    cvaIfEMCfgDialType
--   ObjVar
--    cvaIfEMTimingDigitDuration
--   ObjVar
--    cvaIfEMTimingInterDigitDuration
--   ObjVar
--    cvaIfEMTimingPulseRate
--   ObjVar
--    cvaIfEMTimingPulseInterDigitDuration
--   ObjVar
--    cvaIfEMTimingClearWaitDuration
--   ObjVar
--    cvaIfEMTimingMaxWinkWaitDuration
--   ObjVar
--    cvaIfEMTimingMaxWinkDuration
--   ObjVar
--    cvaIfEMTimingDelayStart
--   ObjVar
--    cvaIfEMTimingMaxDelayDuration
--   ObjVar
--    cvaIfEMTimingMinDelayPulseWidth
--   ObjVar
--    cvaIfFXOCfgSignalType
--   ObjVar
--    cvaIfFXOCfgNumberRings
--   ObjVar
--    cvaIfFXOCfgSupDisconnect
--   ObjVar
--    cvaIfFXOCfgDialType
--   ObjVar
--    cvaIfFXOTimingDigitDuration
--   ObjVar
--    cvaIfFXOTimingInterDigitDuration
--   ObjVar
--    cvaIfFXOTimingPulseRate
--   ObjVar
--    cvaIfFXOTimingPulseInterDigitDuration
--   ObjVar
--    cvaIfFXSCfgSignalType
--   ObjVar
--    cvaIfFXSRingFrequency
--   ObjVar
--    cvaIfFXSTimingDigitDuration
--   ObjVar
--    cvaIfFXSTimingInterDigitDuration


END
