CISCOTRAP-MIB DEFINITIONS ::= BEGIN

          IMPORTS
-- FIX: added additional import (snmp)
              sysUpTime, ifIndex, ifDescr, ifType, egpNeighAddr, 
              tcpConnState, snmp
                   FROM RFC1213-MIB
              cisco
                   FROM CISCO-SMI
              whyReload, authAddr
                   FROM OLD-CISCO-SYSTEM-MIB
              locIfReason
                   FROM OLD-CISCO-INTERFACES-MIB
              tslineSesType, tsLineUser
                   FROM OLD-CISCO-TS-MIB
              loctcpConnElapsed, loctcpConnInBytes, loctcpConnOutBytes
                   FROM OLD-CISCO-TCP-MIB
              TRAP-TYPE
                   FROM RFC-1215;

          -- The standard traps 

          coldStart TRAP-TYPE
              ENTERPRISE  snmp
              VARIABLES   { sysUpTime, whyReload }
              DESCRIPTION
                          "A coldStart trap signifies that the sending
                          protocol entity is reinitializing itself such
                          that the agent's configuration or the protocol
                          entity implementation may be altered."
              ::= 0

          linkDown TRAP-TYPE
              ENTERPRISE  snmp
              VARIABLES   { ifIndex, ifDescr, ifType, locIfReason }
              DESCRIPTION
                          "A linkDown trap signifies that the sending
                          protocol entity recognizes a failure in one of
                          the communication links represented in the
                          agent's configuration."
              ::= 2

          linkUp TRAP-TYPE
              ENTERPRISE  snmp
              VARIABLES   { ifIndex, ifDescr, ifType, locIfReason }
              DESCRIPTION
                          "A linkUp trap signifies that the sending
                          protocol entity recognizes that one of the
                          communication links represented in the agent's
                          configuration has come up."
              ::= 3

          authenticationFailure TRAP-TYPE
              ENTERPRISE  snmp
              VARIABLES   { authAddr }
              DESCRIPTION
                          "An authenticationFailure trap signifies that
                          the sending protocol entity is the addressee
                          of a protocol message that is not properly
                          authenticated.  While implementations of the
                          SNMP must be capable of generating this trap,
                          they must also be capable of suppressing the
                          emission of such traps via an implementation-
                          specific mechanism."
              ::= 4

          egpNeighborLoss TRAP-TYPE
              ENTERPRISE  snmp
              VARIABLES   { egpNeighAddr }
              DESCRIPTION
                          "An egpNeighborLoss trap signifies that an EGP
                          neighbor for whom the sending protocol entity
                          was an EGP peer has been marked down and the
                          peer relationship no longer obtains."
              ::= 5

    -- Cisco Private Enterprise Traps

          reload TRAP-TYPE
              ENTERPRISE  cisco
              VARIABLES   { sysUpTime, whyReload }
              DESCRIPTION
                          "A reload trap signifies that the sending
                          protocol entity is reinitializing itself such
                          that the agent's configuration or the protocol
                          entity implementation may be altered."
              ::= 0

          tcpConnectionClose TRAP-TYPE
              ENTERPRISE  cisco
              VARIABLES   { tslineSesType, tcpConnState, 
                            loctcpConnElapsed, loctcpConnInBytes,
                            loctcpConnOutBytes, tsLineUser }
              DESCRIPTION
                          "A tty trap signifies that a TCP connection,
                          previously established with the sending
                          protocol entity for the purposes of a tty
                          session, has been terminated."
              ::= 1

     END
