-- MIB file created 10-May-2004 20:10:33, by
--   SMICng version 2.2.11-beta(PRO)(Solaris), January 20, 2001. Enterprise key cisco.com

CISCO-DHCP-SNOOPING-MIB DEFINITIONS ::= BEGIN

-- From file: "CISCO-DHCP-SNOOPING-MIB.my"
-- Compile options "4 7 F H N W 03 06 0B 0G 0N 0T"

IMPORTS
    TruthValue, MacAddress, RowStatus
            FROM SNMPv2-TC-v1
    SnmpAdminString
            FROM SNMP-FRAMEWORK-MIB
    ifIndex, InterfaceIndex
            FROM IF-MIB
    InetAddressType, InetAddress
            FROM INET-ADDRESS-MIB
    VlanIndex
            FROM Q-BRIDGE-MIB
    ciscoMgmt
            FROM CISCO-SMI
    Gauge
            FROM RFC1155-SMI
    OBJECT-TYPE
            FROM RFC-1212;

ciscoDhcpSnoopingMIB OBJECT IDENTIFIER ::= { ciscoMgmt 380 }
-- MODULE-IDENTITY
--  LastUpdated
--    200403040000Z
--  OrgName
--    Cisco Systems, Inc.
--  ContactInfo
--            Cisco Systems
--             Customer Service
--    
--     Postal: 170 W Tasman Drive
--             San Jose, CA 95134
--             USA
--    
--        Tel: +1 800 553-NETS
--    
--     E-mail: cs-lan-switch-snmp@cisco.com
--  Descr
--    The MIB module is for configuration of DHCP Snooping 
--     feature. DHCP Snooping is a security mechanism which
--     uses information gleaned from DHCP packets to provide
--     per-interface security capabilities.
--  RevDate
--    200403040000Z
--  RevDescr
--    Initial revision of this MIB module.

ciscoDhcpSnoopingMIBNotifs OBJECT IDENTIFIER ::= { ciscoDhcpSnoopingMIB 0 }
ciscoDhcpSnoopingMIBObjects OBJECT IDENTIFIER ::= { ciscoDhcpSnoopingMIB 1 }
ciscoDhcpSnoopingMIBConformance OBJECT IDENTIFIER ::= { ciscoDhcpSnoopingMIB 2 }
cdsGlobal       OBJECT IDENTIFIER ::= { ciscoDhcpSnoopingMIBObjects 1 }
cdsVlan         OBJECT IDENTIFIER ::= { ciscoDhcpSnoopingMIBObjects 2 }
cdsInterface    OBJECT IDENTIFIER ::= { ciscoDhcpSnoopingMIBObjects 3 }
cdsBindings     OBJECT IDENTIFIER ::= { ciscoDhcpSnoopingMIBObjects 4 }
cdsStatistics   OBJECT IDENTIFIER ::= { ciscoDhcpSnoopingMIBObjects 5 }
cdsSrcGuard     OBJECT IDENTIFIER ::= { ciscoDhcpSnoopingMIBObjects 6 }
cdsMIBCompliances OBJECT IDENTIFIER ::= { ciscoDhcpSnoopingMIBConformance 1 }
cdsMIBGroups    OBJECT IDENTIFIER ::= { ciscoDhcpSnoopingMIBConformance 2 }

cdsFeatureEnable OBJECT-TYPE
    SYNTAX TruthValue
--    Rsyntax INTEGER {
--        true(1),
--        false(2)
--        }
    ACCESS read-write
    STATUS mandatory
    DESCRIPTION
        "This object indicates whether the DHCP Snooping feature is
        enabled at the device level.
        
        Setting this object to 'false' disables the DHCP Snooping 
        feature globally thus disabling the feature at each VLAN.
        
        Setting this object to 'true' will start the DHCP Snooping 
        feature running in the device. Once the DHCP Snooping is 
        enabled, whether the feature is running at each VLAN is 
        controlled by the cdsVlanConfigTable."
    ::= { cdsGlobal 1 }

cdsDatabaseFile OBJECT-TYPE
    SYNTAX SnmpAdminString
--    Rsyntax OCTET STRING(SIZE(0..255))
    ACCESS read-write
    STATUS mandatory
    DESCRIPTION
        "This object indicates the name of the database file used
         to store DHCP bindings information."
    ::= { cdsGlobal 2 }

cdsDatabaseUpdateInterval OBJECT-TYPE
    SYNTAX Gauge
--  Units
--    seconds
    ACCESS read-write
    STATUS mandatory
    DESCRIPTION
        "This object indicates the time interval at which DHCP
         bindings information will be written to the database file
         denoted by cdsDatabaseFile object. Setting this object
         to zero will disable the storage of DHCP bindings."
    ::= { cdsGlobal 3 }

cdsRelayAgentInfoOptEnable OBJECT-TYPE
    SYNTAX TruthValue
--    Rsyntax INTEGER {
--        true(1),
--        false(2)
--        }
    ACCESS read-write
    STATUS mandatory
    DESCRIPTION
        "This object indicates if the DHCP relay agent information
        option (option 82) will be inserted to DHCP packets by
        DHCP Snooping feature.
        
        If this object is set to 'true', DHCP option 82 data will
        be inserted to DHCP packets.
        
        If this object is set to 'false', DHCP option 82 data
        will not be inserted."
    REFERENCE
        "RFC 3046, DHCP Relay Agent Information Option."
    ::= { cdsGlobal 4 }

cdsRelayAgentInfoOptRemoteId OBJECT-TYPE
    SYNTAX MacAddress
--    Rsyntax OCTET STRING(SIZE(6))
    ACCESS read-only
    STATUS mandatory
    DESCRIPTION
        "This object indicates the Remote ID used as part of the
        DHCP relay information option (option 82) data inserted
        to DHCP packets by DHCP Snooping feature. 
        
        The value of this object is ignored whenever the value
        of cdsRelayAgentInfoOptEnable object is 'false'."
    REFERENCE
        "RFC 3046, DHCP Relay Agent Information Option."
    ::= { cdsGlobal 5 }

cdsMatchMacAddressEnable OBJECT-TYPE
    SYNTAX TruthValue
--    Rsyntax INTEGER {
--        true(1),
--        false(2)
--        }
    ACCESS read-write
    STATUS mandatory
    DESCRIPTION
        "This object indicates if DHCP Snooping Mac address
        matching is enabled. 
        
        If this object is set to 'true', DHCP Snooping Mac
        address matching is enabled.
        
        If this object is set to 'false', DHCP Snooping Mac
        address matching is disabled."
    ::= { cdsGlobal 6 }

cdsVlanConfigTable OBJECT-TYPE
    SYNTAX SEQUENCE OF CdsVlanConfigEntry
    ACCESS not-accessible
    STATUS mandatory
    DESCRIPTION
        "A table provides the mechanism to control DHCP Snooping 
        per VLAN. When a VLAN is created in a device supporting this
        table, a corresponding entry of this table will be added."
    ::= { cdsVlan 1 }

cdsVlanConfigEntry OBJECT-TYPE
    SYNTAX CdsVlanConfigEntry
    ACCESS not-accessible
    STATUS mandatory
    DESCRIPTION
        "A row instance contains the configuration to enable
         or disable DHCP Snooping at each existing VLAN."
    INDEX { cdsVlanIndex }
    ::= { cdsVlanConfigTable 1 }

CdsVlanConfigEntry ::= SEQUENCE {
    cdsVlanIndex VlanIndex,
    cdsVlanDhcpSnoopingEnable TruthValue
    }

cdsVlanIndex OBJECT-TYPE
    SYNTAX VlanIndex
--    Rsyntax Gauge
    ACCESS not-accessible
    STATUS mandatory
    DESCRIPTION
        "This object indicates the VLAN number on which DHCP Snooping 
         feature is configured."
    ::= { cdsVlanConfigEntry 1 }

cdsVlanDhcpSnoopingEnable OBJECT-TYPE
    SYNTAX TruthValue
--    Rsyntax INTEGER {
--        true(1),
--        false(2)
--        }
    ACCESS read-write
    STATUS mandatory
    DESCRIPTION
        "This object indicates whether DHCP Snooping is enabled in
         this VLAN. 
        
         If this object is set to 'true', DHCP Snooping is enabled. 
        
         If this object is set to 'false', DHCP Snooping is disabled."
    ::= { cdsVlanConfigEntry 2 }

cdsIfConfigTable OBJECT-TYPE
    SYNTAX SEQUENCE OF CdsIfConfigEntry
    ACCESS not-accessible
    STATUS mandatory
    DESCRIPTION
        "A table provides the mechanism to configure the trust
        state for DHCP Snooping purpose at each physical interface
        capable of this feature. Some of the interfaces
        (but not limited to) for which this feature might be
        applicable are: ifType = ethernetCsmacd(6)."
    ::= { cdsInterface 1 }

cdsIfConfigEntry OBJECT-TYPE
    SYNTAX CdsIfConfigEntry
    ACCESS not-accessible
    STATUS mandatory
    DESCRIPTION
        "A row instance contains the configuration to enable
        or disable trust state for DHCP Snooping at each physical
        interface capable of this feature."
    INDEX { ifIndex }
    ::= { cdsIfConfigTable 1 }

CdsIfConfigEntry ::= SEQUENCE {
    cdsIfTrustEnable TruthValue
    }

cdsIfTrustEnable OBJECT-TYPE
    SYNTAX TruthValue
--    Rsyntax INTEGER {
--        true(1),
--        false(2)
--        }
    ACCESS read-write
    STATUS mandatory
    DESCRIPTION
        "This object indicates whether the interface is trusted for
        DHCP Snooping purpose. 
        
        If this object is set to 'true', the interface is trusted.
        DHCP packets coming to this interface will be forwarded
        without checking.
        
        If this object is set to 'false', the interface is not
        trusted. DHCP packets coming to this interface will be
        subjected to DHCP checks."
    ::= { cdsIfConfigEntry 1 }

cdsIfRateLimitTable OBJECT-TYPE
    SYNTAX SEQUENCE OF CdsIfRateLimitEntry
    ACCESS not-accessible
    STATUS mandatory
    DESCRIPTION
        "A table provides the mechanism to configure the rate limit
        for DHCP Snooping purpose at each physical interface capable
        of this feature. Some of the interfaces (but not limited to)
        for which this feature might be applicable are:
        ifType = ethernetCsmacd(6)."
    ::= { cdsInterface 2 }

cdsIfRateLimitEntry OBJECT-TYPE
    SYNTAX CdsIfRateLimitEntry
    ACCESS not-accessible
    STATUS mandatory
    DESCRIPTION
        "A row instance contains the configuration of rate limit 
        DHCP Snooping at each physical interface capable of this
        feature."
    INDEX { ifIndex }
    ::= { cdsIfRateLimitTable 1 }

CdsIfRateLimitEntry ::= SEQUENCE {
    cdsIfRateLimit Gauge
    }

cdsIfRateLimit OBJECT-TYPE
    SYNTAX Gauge
--  Units
--    packets per second
    ACCESS read-write
    STATUS mandatory
    DESCRIPTION
        "This object indicates rate limit value for DHCP Snooping
        purpose. If the value of this object is 0, no rate limit is
        applied for DHCP traffic at this interface."
    ::= { cdsIfRateLimitEntry 1 }

cdsBindingsTable OBJECT-TYPE
    SYNTAX SEQUENCE OF CdsBindingsEntry
    ACCESS not-accessible
    STATUS mandatory
    DESCRIPTION
        "A table provides the DHCP bindings information learnt by
        the device."
    ::= { cdsBindings 1 }

cdsBindingsEntry OBJECT-TYPE
    SYNTAX CdsBindingsEntry
    ACCESS not-accessible
    STATUS mandatory
    DESCRIPTION
        "A row instance contains the Mac address, IP address type,
        IP address, VLAN number, interface number, leased time and
        status of this instance."
    INDEX { cdsBindingsVlan, cdsBindingsMacAddress }
    ::= { cdsBindingsTable 1 }

CdsBindingsEntry ::= SEQUENCE {
    cdsBindingsVlan VlanIndex,
    cdsBindingsMacAddress MacAddress,
    cdsBindingsAddrType InetAddressType,
    cdsBindingsIpAddress InetAddress,
    cdsBindingsInterface InterfaceIndex,
    cdsBindingsLeasedTime Gauge,
    cdsBindingsStatus RowStatus
    }

cdsBindingsVlan OBJECT-TYPE
    SYNTAX VlanIndex
--    Rsyntax Gauge
    ACCESS not-accessible
    STATUS mandatory
    DESCRIPTION
        "This object indicates the VLAN to which a DHCP client host
         belongs."
    ::= { cdsBindingsEntry 1 }

cdsBindingsMacAddress OBJECT-TYPE
    SYNTAX MacAddress
--    Rsyntax OCTET STRING(SIZE(6))
    ACCESS not-accessible
    STATUS mandatory
    DESCRIPTION
        "This object indicates the MAC address of a DHCP client
         host."
    ::= { cdsBindingsEntry 2 }

cdsBindingsAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object indicates the type of IP address denoted
        in cdsBindingsIpAddress object."
    ::= { cdsBindingsEntry 3 }

cdsBindingsIpAddress OBJECT-TYPE
    SYNTAX InetAddress
--    Rsyntax OCTET STRING(SIZE(0..255))
    ACCESS read-only
    STATUS mandatory
    DESCRIPTION
        "This object indicates the allocated IP address of
        a DHCP client host."
    ::= { cdsBindingsEntry 4 }

cdsBindingsInterface OBJECT-TYPE
    SYNTAX InterfaceIndex
--    Rsyntax INTEGER(1..2147483647)
    ACCESS read-only
    STATUS mandatory
    DESCRIPTION
        "This object indicates the interface where a DHCP client
        host connects to."
    ::= { cdsBindingsEntry 5 }

cdsBindingsLeasedTime OBJECT-TYPE
    SYNTAX Gauge
--  Units
--    seconds
    ACCESS read-only
    STATUS mandatory
    DESCRIPTION
        "This object indicates the leased time of this DHCP
        bindings."
    ::= { cdsBindingsEntry 6 }

cdsBindingsStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to to manage the deletion of rows
        in this table. This object only supports active(1) and
        destroy(6) value. 
        
        Whenever a DHCP binding is learnt by the device, an
        entry will be created by the device in this table with
        its RowStatus object set to active(1). Setting this
        object value to destroy(6) will clear the DHCP bindings
        information represented by this row instance."
    ::= { cdsBindingsEntry 7 }

-- cdsTotalForwardedPkts OBJECT-TYPE
--    SYNTAX Counter64
--  Units
--    packets
--    ACCESS read-only
--    STATUS mandatory
--    DESCRIPTION
--        "Indicates the total number of packets subjected to
--        DHCP Snooping is forwarded."
--    ::= { cdsStatistics 1 }

-- cdsTotalDroppedPkts OBJECT-TYPE
--    SYNTAX Counter64
--  Units
--    packets
--    ACCESS read-only
--    STATUS mandatory
--    DESCRIPTION
--        "Indicates the total number of packets subjected to
--        DHCP Snooping is dropped."
--    ::= { cdsStatistics 2 }

-- cdsUntrustedPortDroppedPkts OBJECT-TYPE
--    SYNTAX Counter64
--  Units
--    packets
--    ACCESS read-only
--    STATUS mandatory
--    DESCRIPTION
--        "Indicates the number of packets subjected to DHCP Snooping
--        is dropped because they come from untrusted interface."
--    ::= { cdsStatistics 3 }

cdsIfSrcGuardConfigTable OBJECT-TYPE
    SYNTAX SEQUENCE OF CdsIfSrcGuardConfigEntry
    ACCESS not-accessible
    STATUS mandatory
    DESCRIPTION
        "A table provides the mechanism to enable or disable  
        IP Source Guard at each physical interface capable of
        this feature. Some of the interfaces (but not limited to)
        for which this feature might be applicable are:
        ifType = ethernetCsmacd(6).
        
        When DHCP Snooping is enabled at an interface, a list of
        IP addresses is obtained through DHCP Snooping for this
        particular interface. If IP Source Guard is enabled, only
        traffic from these IP addresses is allowed to pass through
        the interface."
    ::= { cdsSrcGuard 1 }

cdsIfSrcGuardConfigEntry OBJECT-TYPE
    SYNTAX CdsIfSrcGuardConfigEntry
    ACCESS not-accessible
    STATUS mandatory
    DESCRIPTION
        "A row instance contains the configuration to enable
        or disable IP Source Guard at each physical interface
        capable of this feature."
    INDEX { ifIndex }
    ::= { cdsIfSrcGuardConfigTable 1 }

CdsIfSrcGuardConfigEntry ::= SEQUENCE {
    cdsIfSrcGuardEnable TruthValue
    }

cdsIfSrcGuardEnable OBJECT-TYPE
    SYNTAX TruthValue
--    Rsyntax INTEGER {
--        true(1),
--        false(2)
--        }
    ACCESS read-write
    STATUS mandatory
    DESCRIPTION
        "This object indicates whether IP Source Guard is enabled
        at this interface. 
        
        If this object is set to 'true', IP Source Guard is
        enabled. Traffic coming to this interface will be forwarded
        if it is from the list of IP addresses obtained through
        DHCP Snooping. Otherwise, it is denied.
        
        If this object is set to 'false', IP Source Guard is
        disabled."
    ::= { cdsIfSrcGuardConfigEntry 1 }

cdsIfSrcGuardAddrTable OBJECT-TYPE
    SYNTAX SEQUENCE OF CdsIfSrcGuardAddrEntry
    ACCESS not-accessible
    STATUS mandatory
    DESCRIPTION
        "A table provides the information on IP addresses used
        for IP Source Guard purpose at each physical interface
        capable of this feature. Some of the interfaces
        (but not limited to) for which this feature might be
        applicable are: ifType = ethernetCsmacd(6)."
    ::= { cdsSrcGuard 2 }

cdsIfSrcGuardAddrEntry OBJECT-TYPE
    SYNTAX CdsIfSrcGuardAddrEntry
    ACCESS not-accessible
    STATUS mandatory
    DESCRIPTION
        "A row instance contains the IP address type and IP
        address used for IP Source Guard purpose at each
        physical interface capable of this feature."
    INDEX { ifIndex, cdsIfSrcGuardIndex }
    ::= { cdsIfSrcGuardAddrTable 1 }

CdsIfSrcGuardAddrEntry ::= SEQUENCE {
    cdsIfSrcGuardIndex Gauge,
    cdsIfSrcGuardAddrType InetAddressType,
    cdsIfSrcGuardAddress InetAddress
    }

cdsIfSrcGuardIndex OBJECT-TYPE
    SYNTAX Gauge
    ACCESS not-accessible
    STATUS mandatory
    DESCRIPTION
        "This object indicates the index of this entry."
    ::= { cdsIfSrcGuardAddrEntry 1 }

cdsIfSrcGuardAddrType OBJECT-TYPE
    SYNTAX InetAddressType
--    Rsyntax INTEGER {
--        ?? enum value of zero may cause problems
--        unknown(0),
--        ipv4(1),
--        ipv6(2),
--        ipv4z(3),
--        ipv6z(4),
--        dns(16)
--        }
    ACCESS read-only
    STATUS mandatory
    DESCRIPTION
        "This object indicates the type of IP address denoted
        in cdsIfSrcGuardAddress object."
    ::= { cdsIfSrcGuardAddrEntry 2 }

cdsIfSrcGuardAddress OBJECT-TYPE
    SYNTAX InetAddress
--    Rsyntax OCTET STRING(SIZE(0..255))
    ACCESS read-only
    STATUS mandatory
    DESCRIPTION
        "This object indicates the IP address obtained at
        this interface through DHCP Snooping."
    ::= { cdsIfSrcGuardAddrEntry 3 }

cdsGlobalEnableGroup OBJECT IDENTIFIER ::= { cdsMIBGroups 1 }
-- OBJECT-GROUP
--  Status
--    mandatory
--  Descr
--    A collection of object which are used to configure as
--     well as show information regarding the feature enabling.
--  objects
--    cdsFeatureEnable

cdsDatabaseGroup OBJECT IDENTIFIER ::= { cdsMIBGroups 2 }
-- OBJECT-GROUP
--  Status
--    mandatory
--  Descr
--    A collection of objects which are used to configure as
--     well as show information regarding the DHCP Snooping 
--     database filename and update interval.
--  objects
--    cdsDatabaseFile, cdsDatabaseUpdateInterval

cdsVlanConfigGroup OBJECT IDENTIFIER ::= { cdsMIBGroups 3 }
-- OBJECT-GROUP
--  Status
--    mandatory
--  Descr
--    A collection of object which are used to configure as
--     well as show information regarding the DHCP Snooping 
--     feature per VLAN.
--  objects
--    cdsVlanDhcpSnoopingEnable

cdsIfConfigGroup OBJECT IDENTIFIER ::= { cdsMIBGroups 4 }
-- OBJECT-GROUP
--  Status
--    mandatory
--  Descr
--    A collection of object which are used to configure as
--     well as show information regarding the interface trust
--     state for DHCP Snooping purpose.
--  objects
--    cdsIfTrustEnable

cdsIfRateLimitGroup OBJECT IDENTIFIER ::= { cdsMIBGroups 5 }
-- OBJECT-GROUP
--  Status
--    mandatory
--  Descr
--    A collection of object which are used to configure as
--     well as show information regarding the rate limit per 
--     interface for DHCP Snooping purpose.
--  objects
--    cdsIfRateLimit

cdsBindingsGroup OBJECT IDENTIFIER ::= { cdsMIBGroups 6 }
-- OBJECT-GROUP
--  Status
--    mandatory
--  Descr
--    A collection of object which are used to configure as
--     well as show information regarding the DHCP bindings
--     data.
--  objects
--    cdsBindingsAddrType, cdsBindingsIpAddress, 
--    cdsBindingsInterface, cdsBindingsLeasedTime, 
--    cdsBindingsStatus

cdsStatisticsGroup OBJECT IDENTIFIER ::= { cdsMIBGroups 7 }
-- OBJECT-GROUP
--  Status
--    mandatory
--  Descr
--    A collection of object which are used to show statistics
--     information regarding DHCP Snooping feature.
--  objects
--    cdsTotalForwardedPkts, cdsTotalDroppedPkts, 
--    cdsUntrustedPortDroppedPkts

cdsRelayAgentInfoOptGroup OBJECT IDENTIFIER ::= { cdsMIBGroups 8 }
-- OBJECT-GROUP
--  Status
--    mandatory
--  Descr
--    A collection of objects which are used to configure as
--     well as show information regarding DHCP Option 82
--     insertion.
--  objects
--    cdsRelayAgentInfoOptEnable

cdsIfSrcGuardGroup OBJECT IDENTIFIER ::= { cdsMIBGroups 9 }
-- OBJECT-GROUP
--  Status
--    mandatory
--  Descr
--    A collection of objects which are used to configure as
--     well as show information regarding IP Source Guard 
--     purpose.
--  objects
--    cdsIfSrcGuardEnable, cdsIfSrcGuardAddrType, 
--    cdsIfSrcGuardAddress

cdsRelayAgentRemoteIdGroup OBJECT IDENTIFIER ::= { cdsMIBGroups 10 }
-- OBJECT-GROUP
--  Status
--    mandatory
--  Descr
--    A collection of objects which are used to indicate information
--     regarding DHCP Option 82 remote ID relay agent.
--  objects
--    cdsRelayAgentInfoOptRemoteId

cdsMatchMacAddressGroup OBJECT IDENTIFIER ::= { cdsMIBGroups 11 }
-- OBJECT-GROUP
--  Status
--    mandatory
--  Descr
--    A collection of objects which are used to configure as
--     well as show information regarding DHCP Snooping Mac
--     address matching.
--  objects
--    cdsMatchMacAddressEnable

cdsMIBCompliance OBJECT IDENTIFIER ::= { cdsMIBCompliances 1 }
-- MODULE-COMPLIANCE
--  Status
--    mandatory
--  Descr
--    The compliance statement for the CISCO-DHCP-SNOOPING-MIB
--  Module
--    >>current<<
--   MandGroup
--    cdsIfConfigGroup
--   MandGroup
--    cdsBindingsGroup
--   OptGroup
--    cdsGlobalEnableGroup
--   OptGroup
--    cdsDatabaseGroup
--   OptGroup
--    cdsVlanConfigGroup
--   OptGroup
--    cdsIfRateLimitGroup
--   OptGroup
--    cdsStatisticsGroup
--   OptGroup
--    cdsRelayAgentInfoOptGroup
--   OptGroup
--    cdsIfSrcGuardGroup
--   OptGroup
--    cdsMatchMacAddressGroup


END
