-- MIB created 6/25/99 12:57:41, by
--   SMIC (the next generation) version 1.6.29, November 22, 1994.

CISCO-SYSLOG-MIB DEFINITIONS ::= BEGIN

-- From file: "CISCO-SYSLOG-MIB.my"

IMPORTS
    Integer32, Counter32
            FROM SNMPv2-SMI-v1
    OBJECT-TYPE
            FROM RFC-1212
    TRAP-TYPE
            FROM RFC-1215
    DisplayString, TimeStamp, TruthValue
            FROM SNMPv2-TC-v1
    ciscoMgmt
            FROM CISCO-SMI;

ciscoSyslogMIB OBJECT IDENTIFIER ::= { ciscoMgmt 41 }
-- MODULE-IDENTITY
--  LastUpdated
--    9508070000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    The MIB module to describe and store the system messages
--     generated by the IOS.

ciscoSyslogMIBObjects OBJECT IDENTIFIER ::= { ciscoSyslogMIB 1 }
clogBasic       OBJECT IDENTIFIER ::= { ciscoSyslogMIBObjects 1 }
clogHistory     OBJECT IDENTIFIER ::= { ciscoSyslogMIBObjects 2 }
ciscoSyslogMIBNotificationPrefix OBJECT IDENTIFIER ::= { ciscoSyslogMIB 2 }
ciscoSyslogMIBNotifications OBJECT IDENTIFIER ::= { ciscoSyslogMIBNotificationPrefix 0 }
ciscoSyslogMIBConformance OBJECT IDENTIFIER ::= { ciscoSyslogMIB 3 }
ciscoSyslogMIBCompliances OBJECT IDENTIFIER ::= { ciscoSyslogMIBConformance 1 }
ciscoSyslogMIBGroups OBJECT IDENTIFIER ::= { ciscoSyslogMIBConformance 2 }

SyslogSeverity ::= INTEGER {
        emergency(1),
        alert(2),
        critical(3),
        error(4),
        warning(5),
        notice(6),
        info(7),
        debug(8)
        }
-- TEXTUAL-CONVENTION
--  Status
--    mandatory
--  Descr
--    The severity of a syslog message.  The enumeration
--    values are equal to the values that syslog uses + 1.
--    For example, with syslog, emergency=0.

clogNotificationsSent OBJECT-TYPE
    SYNTAX Counter32
--  Units
--    notifications
    ACCESS read-only
    STATUS mandatory
    DESCRIPTION
        "The number of clogMessageGenerated notifications that
        have been sent. This number may include notifications 
        that were prevented from being transmitted due to 
        reasons such as resource limitations and/or 
        non-connectivity.  If one is receiving notifications,
        one can periodically poll this object to determine if
        any notifications were missed.  If so, a poll of the
        clogHistoryTable might be appropriate."
    ::= { clogBasic 1 }

clogNotificationsEnabled OBJECT-TYPE
    SYNTAX TruthValue
--    Rsyntax INTEGER {
--        true(1),
--        false(2)
--        }
    ACCESS read-write
    STATUS mandatory
    DESCRIPTION
        "Indicates whether clogMessageGenerated notifications
        will or will not be sent when a syslog message is
        generated by the device.  Disabling notifications
        does not prevent syslog messages from being added
        to the clogHistoryTable."
    DEFVAL { false }
    ::= { clogBasic 2 }

clogMaxSeverity OBJECT-TYPE
    SYNTAX SyslogSeverity
--    Rsyntax INTEGER {
--        emergency(1),
--        alert(2),
--        critical(3),
--        error(4),
--        warning(5),
--        notice(6),
--        info(7),
--        debug(8)
--        }
    ACCESS read-write
    STATUS mandatory
    DESCRIPTION
        "Indicates which syslog severity levels will be
        processed.  Any syslog message with a severity value
        greater than this value will be ignored by the agent.
        note: severity numeric values increase as their
        severity decreases, e.g. error(4) is more severe than
        debug(8)."
    DEFVAL { warning }
    ::= { clogBasic 3 }

clogMsgIgnores OBJECT-TYPE
    SYNTAX Counter32
--  Units
--    messages
    ACCESS read-only
    STATUS mandatory
    DESCRIPTION
        "The number of syslog messages which were ignored.  A
        message will be ignored if it has a severity value
        greater than clogMaxSeverity."
    ::= { clogBasic 4 }

clogMsgDrops OBJECT-TYPE
    SYNTAX Counter32
--  Units
--    messages
    ACCESS read-only
    STATUS mandatory
    DESCRIPTION
        "The number of syslog messages which could not be
        processed due to lack of system resources.  Most
        likely this will occur at the same time that syslog
        messages are generated to indicate this lack of
        resources.  Increases in this object's value may serve
        as an indication that system resource levels should be
        examined via other mib objects.  A message that is
        dropped will not appear in the history table and
        no notification will be sent for this message."
    ::= { clogBasic 5 }

clogHistTableMaxLength OBJECT-TYPE
    SYNTAX Integer32(0..500)
--  Units
--    entries
    ACCESS read-write
    STATUS mandatory
    DESCRIPTION
        "The upper limit on the number of entries that the
        clogHistoryTable may contain.  A value of 0 will
        prevent any history from being retained. When this
        table is full, the oldest entry will be deleted and
        a new one will be created."
    DEFVAL { 1 }
    ::= { clogHistory 1 }

clogHistMsgsFlushed OBJECT-TYPE
    SYNTAX Counter32
--  Units
--    messages
    ACCESS read-only
    STATUS mandatory
    DESCRIPTION
        "The number of entries that have been removed from
        the clogHistoryTable in order to make room for new
        entries.  This object can be utilized to determine
        whether your polling frequency on the history table
        is fast enough and/or the size of your history table
        is large enough such that you are not missing
        messages."
    ::= { clogHistory 2 }

clogHistoryTable OBJECT-TYPE
    SYNTAX SEQUENCE OF ClogHistoryEntry
    ACCESS not-accessible
    STATUS mandatory
    DESCRIPTION
        "A table of syslog messages generated by this device.
        All 'interesting' syslog messages (i.e. severity <=
        clogMaxSeverity) are entered into this table."
    ::= { clogHistory 3 }

clogHistoryEntry OBJECT-TYPE
    SYNTAX ClogHistoryEntry
    ACCESS not-accessible
    STATUS mandatory
    DESCRIPTION
        "A syslog message that was previously generated by this
        device.  Each entry is indexed by a message index."
    INDEX { clogHistIndex }
    ::= { clogHistoryTable 1 }

ClogHistoryEntry ::= SEQUENCE {
    clogHistIndex Integer32,
    clogHistFacility DisplayString,
    clogHistSeverity SyslogSeverity,
    clogHistMsgName DisplayString,
    clogHistMsgText DisplayString,
    clogHistTimestamp TimeStamp
    }

clogHistIndex OBJECT-TYPE
    SYNTAX Integer32(1..2147483647)
    ACCESS not-accessible
    STATUS mandatory
    DESCRIPTION
        "A monotonically increasing integer for the sole
        purpose of indexing messages.  When it reaches the
        maximum value the agent flushes the table and wraps 
        the value back to 1."
    ::= { clogHistoryEntry 1 }

clogHistFacility OBJECT-TYPE
    SYNTAX DisplayString(SIZE(1..20))
--    Rsyntax OCTET STRING(SIZE(1..20))
    ACCESS read-only
    STATUS mandatory
    DESCRIPTION
        "Name of the facility that generated this message.
        For example: 'SYS'."
    ::= { clogHistoryEntry 2 }

clogHistSeverity OBJECT-TYPE
    SYNTAX SyslogSeverity
--    Rsyntax INTEGER {
--        emergency(1),
--        alert(2),
--        critical(3),
--        error(4),
--        warning(5),
--        notice(6),
--        info(7),
--        debug(8)
--        }
    ACCESS read-only
    STATUS mandatory
    DESCRIPTION
        "The severity of the message."
    ::= { clogHistoryEntry 3 }

clogHistMsgName OBJECT-TYPE
    SYNTAX DisplayString(SIZE(1..30))
--    Rsyntax OCTET STRING(SIZE(1..30))
    ACCESS read-only
    STATUS mandatory
    DESCRIPTION
        "A textual identification for the message type.  A 
        facility name in conjunction with a message name 
        uniquely identifies a message type."
    ::= { clogHistoryEntry 4 }

clogHistMsgText OBJECT-TYPE
    SYNTAX DisplayString(SIZE(1..255))
--    Rsyntax OCTET STRING(SIZE(1..255))
    ACCESS read-only
    STATUS mandatory
    DESCRIPTION
        "The text of the message.  If the text of the message
        exceeds 255 bytes, the message will be truncated to
        254 bytes and a '*' character will be appended -
        indicating that the message has been truncated."
    ::= { clogHistoryEntry 5 }

clogHistTimestamp OBJECT-TYPE
    SYNTAX TimeStamp
--    Rsyntax TimeTicks
    ACCESS read-only
    STATUS mandatory
    DESCRIPTION
        "The value of sysUpTime when this message was generated."
    ::= { clogHistoryEntry 6 }

clogMessageGenerated TRAP-TYPE
-- Reverse mappable trap
    ENTERPRISE ciscoSyslogMIBNotificationPrefix
    VARIABLES {
        clogHistFacility, clogHistSeverity, clogHistMsgName, 
        clogHistMsgText, clogHistTimestamp }
--  Status
--    mandatory
    DESCRIPTION
        "When a syslog message is generated by the device a
        clogMessageGenerated notification is sent.  The
        sending of these notifications can be enabled/disabled
        via the clogNotificationsEnabled object."
    ::= 1

ciscoSyslogMIBGroup OBJECT IDENTIFIER ::= { ciscoSyslogMIBGroups 1 }
-- OBJECT-GROUP
--  Status
--    mandatory
--  Descr
--    A collection of objects providing the syslog MIB capability.
--  objects
--    clogNotificationsSent, clogNotificationsEnabled, 
--    clogMaxSeverity, clogMsgIgnores, clogMsgDrops, 
--    clogHistTableMaxLength, clogHistMsgsFlushed, clogHistFacility, 
--    clogHistSeverity, clogHistMsgName, clogHistMsgText, 
--    clogHistTimestamp

ciscoSyslogMIBCompliance OBJECT IDENTIFIER ::= { ciscoSyslogMIBCompliances 1 }
-- MODULE-COMPLIANCE
--  Status
--    mandatory
--  Descr
--    The compliance statement for entities which implement
--    the Cisco syslog MIB.
--  Module
--    >>current<<
--   MandGroup
--    ciscoSyslogMIBGroup


END
