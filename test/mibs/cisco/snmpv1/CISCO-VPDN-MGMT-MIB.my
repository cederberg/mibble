-- MIB file created 19-Aug-2003 11:43:04, by
--   SMICng version 2.2.11-beta(PRO)(Solaris), January 20, 2001. Enterprise key cisco.com

CISCO-VPDN-MGMT-MIB DEFINITIONS ::= BEGIN

-- From file: "CISCO-VPDN-MGMT-MIB.my"
-- Compile options "4 7 F H N W 03 06 0B 0G 0N 0T"

IMPORTS
    TimeStamp, DisplayString, TruthValue
            FROM SNMPv2-TC-v1
    SnmpAdminString
            FROM SNMP-FRAMEWORK-MIB
    InterfaceIndexOrZero
            FROM IF-MIB
    ciscoExperiment
            FROM CISCO-SMI
    Counter, Gauge, IpAddress, TimeTicks
            FROM RFC1155-SMI
    OBJECT-TYPE
            FROM RFC-1212
    TRAP-TYPE
            FROM RFC-1215;

ciscoVpdnMgmtMIB OBJECT IDENTIFIER ::= { ciscoExperiment 24 }
-- MODULE-IDENTITY
--  LastUpdated
--    200207080000Z
--  OrgName
--    Cisco Systems, Inc.
--  ContactInfo
--           Cisco Systems
--     Customer Service
--    
--    Postal: 170 W Tasman Drive
--     San Jose, CA  95134
--     USA
--    
--       Tel: +1 800 553-NETS
--    
--    E-mail: cs-vpdn@cisco.com
--  Descr
--    The MIB module for VPDN.
--    
--      Overview of VPDN MIB
--    
--      MIB description
--    
--          This MIB is to support the VPDN (Virtual Private Dialup Network)
--          feature of Cisco IOS. VPDN handles the forwarding of PPP links 
--    from an Internet Provider (ISP) to a Home Gateway.
--    
--      The VPDN MIB provides the operational information on Cisco's 
--    VPDN tunnelling implementation.  The following entities
--      are managed:
--       1) Global VPDN information
--       2) VPDN tunnel information
--       3) VPDN tunnel's user information
--    4) Failure history per user
--    
--      The following example configuration shows how the VPDN MIB returns
--      VPDN information, from either CISCO A - Network Access Server (NAS)
--    or CISCO B - Tunnel Server (TS).  The User call is projected by either 
--    domain name or Dialed Number Identification Service (DNIS).
--    
--    The terms NAS and TS are generic terms refering to the VPDN systems.
--    The following table shows the corresponding technology-specific terms.
--    
--           Network Access Server            Tunnel Server
--           ==============================   =========================
--       L2F   Network Access Server    (NAS)   Home Gateway (HGW) 
--     L2TP  L2TP Access Concentrator (LAC)   L2TP Network Server (LNS)
--     PPTP  PPTP Access Concentrator (PAC)   PPTP Network Server (PNS)
--    
--       (NAS)     (TS)
--       User ===== Cisco A ===== IP Network ===== Cisco B ===== Server 
--                   |                          |
--            +========== VPDN ==========+
--    
--      1) The VPDN global entry identifies the system wide VPDN information.
--      2) The VPDN tunnel table identifies the active VPDN tunnels on Cisco A 
--      and Cisco B. The table contains an entry for each active tunnel 
--            on the system.
--      3) The VPDN tunnel user table identifies the active users for each
--      active tunnel on each system and provides relevant information
--      for each user.
--    4) The VPDN failure history table identifies the last failure
--      recorded per user and provides relevant information.
--       
--  RevDate
--    200207080000Z
--  RevDescr
--    Added support for VPDN Template information.  The template
--     table reports the number of active sessions for each template.
--     This number is the sum of active sessions for all VPDN groups
--     associated with each template.
--  RevDate
--    200205170000Z
--  RevDescr
--    Changed cvpdnSessionAttrVirtualCircuitID to an Unsigned32
--     object.  Also, moved Unsigned32 import to SNMPv2-SMI.
--           
--  RevDate
--    200204020000Z
--  RevDescr
--    Added virtual circuit ID, packets dropped, and notification
--     objects for WAN/IP support.
--           
--  RevDate
--    200001120000Z
--  RevDescr
--    Added support for Point-to-Point Tunneling Protocol (PPTP).
--     Changed object descriptions to use generic terms.
--  RevDate
--    9903240000Z
--  RevDescr
--    Added support for multiple tunnel protocols with these tables
--      1) cvpdnSystemTable
--      2) cvpdnTunnelAttrTable 
--      3) cvpdnTunnelSessionAttrTable 
--    
--     Deprecated objects and tables duplicated by the three new tables
--      1) cvpdnTunnelTotal, cvpdnSessionTotal, cvpdnDeniedUsersTotal 
--      2) cvpdnTunnelTable 
--      3) cvpdnTunnelSessionTable 
--  RevDate
--    9707150000Z
--  RevDescr
--    Initial version of this MIB module.

ciscoVpdnMgmtMIBObjects OBJECT IDENTIFIER ::= { ciscoVpdnMgmtMIB 1 }
cvpdnSystemInfo OBJECT IDENTIFIER ::= { ciscoVpdnMgmtMIBObjects 1 }
cvpdnTunnelInfo OBJECT IDENTIFIER ::= { ciscoVpdnMgmtMIBObjects 2 }
cvpdnTunnelSessionInfo OBJECT IDENTIFIER ::= { ciscoVpdnMgmtMIBObjects 3 }
cvpdnUserToFailHistInfo OBJECT IDENTIFIER ::= { ciscoVpdnMgmtMIBObjects 4 }
cvpdnTemplateInfo OBJECT IDENTIFIER ::= { ciscoVpdnMgmtMIBObjects 5 }
ciscoVpdnMgmtMIBNotifs OBJECT IDENTIFIER ::= { ciscoVpdnMgmtMIB 0 }
ciscoVpdnMgmtMIBConformance OBJECT IDENTIFIER ::= { ciscoVpdnMgmtMIB 3 }
ciscoVpdnMgmtMIBCompliances OBJECT IDENTIFIER ::= { ciscoVpdnMgmtMIBConformance 1 }
ciscoVpdnMgmtMIBGroups OBJECT IDENTIFIER ::= { ciscoVpdnMgmtMIBConformance 2 }

cvpdnTunnelTotal OBJECT-TYPE
    SYNTAX Gauge
--  Units
--    tunnels
    ACCESS read-only
    STATUS deprecated
    DESCRIPTION
        "The total number of VPDN tunnels that are currently 
        active within this system."
    ::= { cvpdnSystemInfo 1 }

cvpdnSessionTotal OBJECT-TYPE
    SYNTAX Gauge
--  Units
--    users
    ACCESS read-only
    STATUS deprecated
    DESCRIPTION
        "The total number of active users in all the active VPDN 
        tunnels within this system."
    ::= { cvpdnSystemInfo 2 }

cvpdnDeniedUsersTotal OBJECT-TYPE
    SYNTAX Counter
--  Units
--    attempts
    ACCESS read-only
    STATUS deprecated
    DESCRIPTION
        "The total number of denied user attempts to all the active 
        VPDN tunnels within this system."
    ::= { cvpdnSystemInfo 3 }

cvpdnSystemTable OBJECT-TYPE
    SYNTAX SEQUENCE OF CvpdnSystemEntry
    ACCESS not-accessible
    STATUS mandatory
    DESCRIPTION
        "Table of information about the VPDN system for all tunnel
         types."
    ::= { cvpdnSystemInfo 4 }

cvpdnSystemEntry OBJECT-TYPE
    SYNTAX CvpdnSystemEntry
    ACCESS not-accessible
    STATUS mandatory
    DESCRIPTION
        "An entry in the table, containing information about a single
         type of VPDN tunnel."
    INDEX { cvpdnSystemTunnelType }
    ::= { cvpdnSystemTable 1 }

CvpdnSystemEntry ::= SEQUENCE {
    cvpdnSystemTunnelType INTEGER,
    cvpdnSystemTunnelTotal Gauge,
    cvpdnSystemSessionTotal Gauge,
    cvpdnSystemDeniedUsersTotal Counter
    }

cvpdnSystemTunnelType OBJECT-TYPE
    SYNTAX INTEGER {
        l2f(1),
        l2tp(2),
        pptp(3)
        }
    ACCESS not-accessible
    STATUS mandatory
    DESCRIPTION
        "The tunnel type.  This is the tunnel protocol."
    ::= { cvpdnSystemEntry 1 }

cvpdnSystemTunnelTotal OBJECT-TYPE
    SYNTAX Gauge
--  Units
--    tunnels
    ACCESS read-only
    STATUS mandatory
    DESCRIPTION
        "The total number of VPDN tunnels that are currently 
         active of this tunnel type."
    ::= { cvpdnSystemEntry 2 }

cvpdnSystemSessionTotal OBJECT-TYPE
    SYNTAX Gauge
--  Units
--    sessions
    ACCESS read-only
    STATUS mandatory
    DESCRIPTION
        "The total number of active sessions in all the active VPDN 
         tunnels of this tunnel type."
    ::= { cvpdnSystemEntry 3 }

cvpdnSystemDeniedUsersTotal OBJECT-TYPE
    SYNTAX Counter
--  Units
--    attempts
    ACCESS read-only
    STATUS mandatory
    DESCRIPTION
        "The total number of denied user attempts to all the 
         VPDN tunnels of this tunnel type since last system
         re-initialization."
    ::= { cvpdnSystemEntry 4 }

cvpdnSystemNotifSessionEnabled OBJECT-TYPE
    SYNTAX TruthValue
--    Rsyntax INTEGER {
--        true(1),
--        false(2)
--        }
    ACCESS read-only
    STATUS mandatory
    DESCRIPTION
        "Indicates whether Layer 2 VPN session notifications are
         enabled."
    DEFVAL { false }
    ::= { cvpdnSystemInfo 5 }

cvpdnTunnelTable OBJECT-TYPE
    SYNTAX SEQUENCE OF CvpdnTunnelEntry
    ACCESS not-accessible
    STATUS deprecated
    DESCRIPTION
        "Table of information about the active VPDN tunnels."
    ::= { cvpdnTunnelInfo 1 }

cvpdnTunnelEntry OBJECT-TYPE
    SYNTAX CvpdnTunnelEntry
    ACCESS not-accessible
    STATUS deprecated
    DESCRIPTION
        "An entry in the table, containing information about a single
         active VPDN tunnel."
    INDEX { cvpdnTunnelTunnelId }
    ::= { cvpdnTunnelTable 1 }

CvpdnTunnelEntry ::= SEQUENCE {
    cvpdnTunnelTunnelId Gauge,
    cvpdnTunnelRemoteTunnelId Gauge,
    cvpdnTunnelLocalName DisplayString,
    cvpdnTunnelRemoteName DisplayString,
    cvpdnTunnelRemoteEndpointName DisplayString,
    cvpdnTunnelLocalInitConnection TruthValue,
    cvpdnTunnelOrigCause INTEGER,
    cvpdnTunnelState INTEGER,
    cvpdnTunnelActiveSessions Gauge,
    cvpdnTunnelDeniedUsers Counter,
    cvpdnTunnelSoftshut TruthValue,
    cvpdnTunnelNetworkServiceType INTEGER,
    cvpdnTunnelLocalIpAddress IpAddress,
    cvpdnTunnelSourceIpAddress IpAddress,
    cvpdnTunnelRemoteIpAddress IpAddress
    }

cvpdnTunnelTunnelId OBJECT-TYPE
    SYNTAX Gauge
    ACCESS not-accessible
    STATUS deprecated
    DESCRIPTION
        "The Tunnel ID of an active VPDN tunnel. If it is the
        instigator of the tunnel, the ID is the HGW/LNS tunnel ID,
        otherwise it is the NAS/LAC tunnel ID."
    ::= { cvpdnTunnelEntry 1 }

cvpdnTunnelRemoteTunnelId OBJECT-TYPE
    SYNTAX Gauge
    ACCESS read-only
    STATUS deprecated
    DESCRIPTION
        "The remote Tunnel ID of an active VPDN tunnel. If it is 
        the instigator of the tunnel, the ID is the NAS/LAC tunnel 
        ID, otherwise it is the HGW/LNS tunnel ID."
    ::= { cvpdnTunnelEntry 2 }

cvpdnTunnelLocalName OBJECT-TYPE
    SYNTAX DisplayString(SIZE(1..255))
--    Rsyntax OCTET STRING(SIZE(1..255))
    ACCESS read-only
    STATUS deprecated
    DESCRIPTION
        "The local name of an active VPDN tunnel. It will be the
        NAS/LAC name of the tunnel if the router serves as the
        NAS/LAC, or the HGW/LNS name of the tunnel if the  
        system serves as the home gateway. Typically, the local 
        name is the configured host name of the router."
    ::= { cvpdnTunnelEntry 3 }

cvpdnTunnelRemoteName OBJECT-TYPE
    SYNTAX DisplayString(SIZE(1..255))
--    Rsyntax OCTET STRING(SIZE(1..255))
    ACCESS read-only
    STATUS deprecated
    DESCRIPTION
        "The remote name of an active VPDN tunnel. It will be the
        home gateway name of the tunnel if the system is a NAS/LAC, 
        or the NAS/LAC name of the tunnel if the system serves as 
        the home gateway."
    ::= { cvpdnTunnelEntry 4 }

cvpdnTunnelRemoteEndpointName OBJECT-TYPE
    SYNTAX DisplayString(SIZE(1..255))
--    Rsyntax OCTET STRING(SIZE(1..255))
    ACCESS read-only
    STATUS deprecated
    DESCRIPTION
        "The remote end point name of an active VPDN tunnel. This name
        is either the domain name or the DNIS that this tunnel is
        projected with."
    ::= { cvpdnTunnelEntry 5 }

cvpdnTunnelLocalInitConnection OBJECT-TYPE
    SYNTAX TruthValue
--    Rsyntax INTEGER {
--        true(1),
--        false(2)
--        }
    ACCESS read-only
    STATUS deprecated
    DESCRIPTION
        "This object indicates whether the tunnel was generated 
        locally or not."
    ::= { cvpdnTunnelEntry 6 }

cvpdnTunnelOrigCause OBJECT-TYPE
    SYNTAX INTEGER {
        domain(1),
        dnis(2),
        stack(3)
        }
    ACCESS read-only
    STATUS deprecated
    DESCRIPTION
        "The cause which originated an active VPDN tunnel. The tunnel 
        can be projected via domain name, DNIS or a stack group (SGBP)."
    ::= { cvpdnTunnelEntry 7 }

cvpdnTunnelState OBJECT-TYPE
    SYNTAX INTEGER {
        unknown(1),
        opening(2),
        open(3),
        closing(4)
        }
    ACCESS read-only
    STATUS deprecated
    DESCRIPTION
        "The current state of an active VPDN tunnel. Each state code 
        is explained below:
        
        unknown: The current state of the tunnel is unknown.
        
        opening: The tunnel has just been instigated and 
        is pending for a remote end reply to 
        complete the process.
        
        open: The tunnel is active.
        
        closing: The tunnel has just been shut down and is 
        pending for the remote end to reply to 
        complete the process. "
    ::= { cvpdnTunnelEntry 8 }

cvpdnTunnelActiveSessions OBJECT-TYPE
    SYNTAX Gauge
--  Units
--    sessions
    ACCESS read-only
    STATUS deprecated
    DESCRIPTION
        "The total number of active session currently in the tunnel."
    ::= { cvpdnTunnelEntry 9 }

cvpdnTunnelDeniedUsers OBJECT-TYPE
    SYNTAX Counter
--  Units
--    calls
    ACCESS read-only
    STATUS deprecated
    DESCRIPTION
        "A count of the accumulated total of denied users for 
        the tunnel."
    ::= { cvpdnTunnelEntry 10 }

cvpdnTunnelSoftshut OBJECT-TYPE
    SYNTAX TruthValue
--    Rsyntax INTEGER {
--        true(1),
--        false(2)
--        }
    ACCESS read-only
    STATUS deprecated
    DESCRIPTION
        "A VPDN tunnel can be put into a soft shut state to prevent 
        any new user session to be added. This object specifies 
        whether this tunnel has been soft shut."
    ::= { cvpdnTunnelEntry 12 }

cvpdnTunnelNetworkServiceType OBJECT-TYPE
    SYNTAX INTEGER {
        ip(1)
        }
    ACCESS read-only
    STATUS deprecated
    DESCRIPTION
        "The type of network service used in the active tunnel. For
        now it is IP only."
    ::= { cvpdnTunnelEntry 13 }

cvpdnTunnelLocalIpAddress OBJECT-TYPE
    SYNTAX IpAddress
    ACCESS read-only
    STATUS deprecated
    DESCRIPTION
        "The local IP address of the tunnel. This IP address is that
        of the interface at the local end of the tunnel. "
    ::= { cvpdnTunnelEntry 14 }

cvpdnTunnelSourceIpAddress OBJECT-TYPE
    SYNTAX IpAddress
    ACCESS read-only
    STATUS deprecated
    DESCRIPTION
        "The Source IP address of the tunnel. This IP address is the 
        user configurable IP address for Stack Group Bundling Protocol
        (SGBP) via the CLI command:
        vpdn source-ip"
    ::= { cvpdnTunnelEntry 15 }

cvpdnTunnelRemoteIpAddress OBJECT-TYPE
    SYNTAX IpAddress
    ACCESS read-only
    STATUS deprecated
    DESCRIPTION
        "The remote IP address of the tunnel. This IP address is 
        that of the interface at the remote end of the tunnel. "
    ::= { cvpdnTunnelEntry 16 }

cvpdnTunnelAttrTable OBJECT-TYPE
    SYNTAX SEQUENCE OF CvpdnTunnelAttrEntry
    ACCESS not-accessible
    STATUS mandatory
    DESCRIPTION
        "Table of information about the active VPDN tunnels.
         An entry is added to the table when a new tunnel is 
         initiated and removed from the table when the tunnel
         is terminated."
    ::= { cvpdnTunnelInfo 2 }

cvpdnTunnelAttrEntry OBJECT-TYPE
    SYNTAX CvpdnTunnelAttrEntry
    ACCESS not-accessible
    STATUS mandatory
    DESCRIPTION
        "An entry in the table, containing information about a single
         active VPDN tunnel."
    INDEX { cvpdnSystemTunnelType, cvpdnTunnelAttrTunnelId }
    ::= { cvpdnTunnelAttrTable 1 }

CvpdnTunnelAttrEntry ::= SEQUENCE {
    cvpdnTunnelAttrTunnelId INTEGER,
    cvpdnTunnelAttrRemoteTunnelId INTEGER,
    cvpdnTunnelAttrLocalName DisplayString,
    cvpdnTunnelAttrRemoteName DisplayString,
    cvpdnTunnelAttrRemoteEndpointName DisplayString,
    cvpdnTunnelAttrLocalInitConnection TruthValue,
    cvpdnTunnelAttrOrigCause INTEGER,
    cvpdnTunnelAttrState INTEGER,
    cvpdnTunnelAttrActiveSessions Gauge,
    cvpdnTunnelAttrDeniedUsers Counter,
    cvpdnTunnelAttrSoftshut TruthValue,
    cvpdnTunnelAttrNetworkServiceType INTEGER,
    cvpdnTunnelAttrLocalIpAddress IpAddress,
    cvpdnTunnelAttrSourceIpAddress IpAddress,
    cvpdnTunnelAttrRemoteIpAddress IpAddress
    }

cvpdnTunnelAttrTunnelId OBJECT-TYPE
    SYNTAX INTEGER(0..65535)
    ACCESS not-accessible
    STATUS mandatory
    DESCRIPTION
        "The Tunnel ID of an active VPDN tunnel. If this end is the
         instigator of the tunnel, the ID is the TS tunnel ID,
         otherwise it is the NAS tunnel ID.
        
         Two distinct tunnels with the same tunnel ID may exist, but
         with different tunnel types."
    ::= { cvpdnTunnelAttrEntry 1 }

cvpdnTunnelAttrRemoteTunnelId OBJECT-TYPE
    SYNTAX INTEGER(0..65535)
    ACCESS read-only
    STATUS mandatory
    DESCRIPTION
        "The remote Tunnel ID of an active VPDN tunnel. If this end is 
         the instigator of the tunnel, the ID is the NAS tunnel 
         ID, otherwise it is the TS tunnel ID."
    ::= { cvpdnTunnelAttrEntry 2 }

cvpdnTunnelAttrLocalName OBJECT-TYPE
    SYNTAX DisplayString(SIZE(1..255))
--    Rsyntax OCTET STRING(SIZE(1..255))
    ACCESS read-only
    STATUS mandatory
    DESCRIPTION
        "The local name of an active VPDN tunnel. It will be the
         NAS name of the tunnel if the system serves as the
         NAS, or the TS name of the tunnel if the  
         system serves as the tunnel server. Typically, the local 
         name is the configured host name of the system."
    ::= { cvpdnTunnelAttrEntry 3 }

cvpdnTunnelAttrRemoteName OBJECT-TYPE
    SYNTAX DisplayString(SIZE(1..255))
--    Rsyntax OCTET STRING(SIZE(1..255))
    ACCESS read-only
    STATUS mandatory
    DESCRIPTION
        "The remote name of an active VPDN tunnel. It will be the
         tunnel server name of the tunnel if the system is a NAS, 
         or the NAS name of the tunnel if the system serves as 
         the tunnel server."
    ::= { cvpdnTunnelAttrEntry 4 }

cvpdnTunnelAttrRemoteEndpointName OBJECT-TYPE
    SYNTAX DisplayString(SIZE(1..255))
--    Rsyntax OCTET STRING(SIZE(1..255))
    ACCESS read-only
    STATUS mandatory
    DESCRIPTION
        "The remote end point name of an active VPDN tunnel. This name
         is either the domain name or the DNIS that this tunnel is
         projected with."
    ::= { cvpdnTunnelAttrEntry 5 }

cvpdnTunnelAttrLocalInitConnection OBJECT-TYPE
    SYNTAX TruthValue
--    Rsyntax INTEGER {
--        true(1),
--        false(2)
--        }
    ACCESS read-only
    STATUS mandatory
    DESCRIPTION
        "This object indicates whether the tunnel was originated 
         locally or not.  If it's true, the tunnel was originated
         locally."
    ::= { cvpdnTunnelAttrEntry 6 }

cvpdnTunnelAttrOrigCause OBJECT-TYPE
    SYNTAX INTEGER {
        domain(1),
        dnis(2),
        stack(3),
        xconnect(4)
        }
    ACCESS read-only
    STATUS mandatory
    DESCRIPTION
        "The cause which originated an active VPDN tunnel. The tunnel 
         can be projected via domain name, DNIS, stack group, or
        L2 Xconnect."
    ::= { cvpdnTunnelAttrEntry 7 }

cvpdnTunnelAttrState OBJECT-TYPE
    SYNTAX INTEGER {
        unknown(1),
        l2fOpening(2),
        l2fOpenWait(3),
        l2fOpen(4),
        l2fClosing(5),
        l2fCloseWait(6),
        l2tpIdle(7),
        l2tpWaitCtlReply(8),
        l2tpEstablished(9),
        l2tpShuttingDown(10),
        l2tpNoSessionLeft(11),
        pptpIdle(12),
        pptpWaitConnect(13),
        pptpWaitCtlRequest(14),
        pptpWaitCtlReply(15),
        pptpEstablished(16),
        pptpWaitStopReply(17),
        pptpTerminal(18)
        }
    ACCESS read-only
    STATUS mandatory
    DESCRIPTION
        "The current state of an active VPDN tunnel.
         Tunnels of type l2f will have states with the 'l2f' prefix.
         Tunnels of type l2tp will have states with the 'l2tp' prefix.
        Tunnels of type pptp will have states with the 'pptp' prefix.
        
         Each state code is explained below:
        
                    unknown: The current state of the tunnel is unknown.
        
                    l2fOpening: The tunnel has just been initiated and 
                             is pending for a remote end reply to 
                             complete the process.
        
                    l2fOpenWait: This end received a tunnel open
                            request from the remote end and is waiting
                            for the tunnel to be established.
        
                    l2fOpen: The tunnel is active.
        
                    l2fClosing: This end received a tunnel close request.
        
                    l2fCloseWait: The tunnel has just been shut down and is 
                            pending for the remote end to reply to 
                            complete the process.
        
                    l2tpIdle: No tunnel is initiated yet.
        
                    l2tpWaitCtlReply: The tunnel has been initiated and
                            is pending for a remote end reply to complete
                            the process.
        
                    l2tpEstablished: The tunnel is active.
        
                    l2tpShuttingDown: The tunnel is in progress of
                            shutting down.
        
                    l2tpNoSessionLeft: There is no session left in
                            the tunnel.
        
        pptpIdle: No tunnel is initiated yet.
        
        pptpWaitConnect: The tunnel is waiting for a TCP connection.
        
        pptpWaitCtlRequest:  The tunnel has been initiated and
        is pending for a remote end request. 
        
        pptpWaitCtlReply: The tunnel has been initated and is
        pending for a remote end reply.
        
        pptpEstablished: The tunnel is active.
        
        pptpWaitStopReply: The tunnel is being shut down and is 
        pending for a remote end reply.
        
        pptpTerminal: The tunnel has been shut down."
    ::= { cvpdnTunnelAttrEntry 8 }

cvpdnTunnelAttrActiveSessions OBJECT-TYPE
    SYNTAX Gauge
--  Units
--    sessions
    ACCESS read-only
    STATUS mandatory
    DESCRIPTION
        "The total number of active session currently in the tunnel."
    ::= { cvpdnTunnelAttrEntry 9 }

cvpdnTunnelAttrDeniedUsers OBJECT-TYPE
    SYNTAX Counter
--  Units
--    calls
    ACCESS read-only
    STATUS mandatory
    DESCRIPTION
        "A count of the accumulated total of denied users for 
         the tunnel."
    ::= { cvpdnTunnelAttrEntry 10 }

cvpdnTunnelAttrSoftshut OBJECT-TYPE
    SYNTAX TruthValue
--    Rsyntax INTEGER {
--        true(1),
--        false(2)
--        }
    ACCESS read-only
    STATUS mandatory
    DESCRIPTION
        "A VPDN tunnel can be put into a soft shut state to prevent 
         any new session to be added. This object specifies 
         whether this tunnel has been soft shut.  If its true,
         it has been soft shut."
    ::= { cvpdnTunnelAttrEntry 11 }

cvpdnTunnelAttrNetworkServiceType OBJECT-TYPE
    SYNTAX INTEGER {
        ip(1)
        }
    ACCESS read-only
    STATUS mandatory
    DESCRIPTION
        "The type of network service used in the active tunnel."
    ::= { cvpdnTunnelAttrEntry 12 }

cvpdnTunnelAttrLocalIpAddress OBJECT-TYPE
    SYNTAX IpAddress
    ACCESS read-only
    STATUS mandatory
    DESCRIPTION
        "The local IP address of the tunnel. This IP address is that
         of the interface at the local end of the tunnel. "
    ::= { cvpdnTunnelAttrEntry 13 }

cvpdnTunnelAttrSourceIpAddress OBJECT-TYPE
    SYNTAX IpAddress
    ACCESS read-only
    STATUS mandatory
    DESCRIPTION
        "The Source IP address of the tunnel. This IP address is the 
         user configurable IP address for Stack Group Biding Protocol"
    ::= { cvpdnTunnelAttrEntry 14 }

cvpdnTunnelAttrRemoteIpAddress OBJECT-TYPE
    SYNTAX IpAddress
    ACCESS read-only
    STATUS mandatory
    DESCRIPTION
        "The remote IP address of the tunnel. This IP address is 
         that of the interface at the remote end of the tunnel. "
    ::= { cvpdnTunnelAttrEntry 15 }

cvpdnTunnelSessionTable OBJECT-TYPE
    SYNTAX SEQUENCE OF CvpdnTunnelSessionEntry
    ACCESS not-accessible
    STATUS deprecated
    DESCRIPTION
        "Table of information about individual user sessions within
        the active tunnels. Entry is added to the table when
        new user session is initiated and be removed from the
        table when the user session is terminated."
    ::= { cvpdnTunnelSessionInfo 1 }

cvpdnTunnelSessionEntry OBJECT-TYPE
    SYNTAX CvpdnTunnelSessionEntry
    ACCESS not-accessible
    STATUS deprecated
    DESCRIPTION
        "An entry in the table, containing information about a single
         user session within the tunnel."
    INDEX { cvpdnTunnelTunnelId, cvpdnTunnelSessionId }
    ::= { cvpdnTunnelSessionTable 1 }

CvpdnTunnelSessionEntry ::= SEQUENCE {
    cvpdnTunnelSessionId Gauge,
    cvpdnTunnelSessionUserName DisplayString,
    cvpdnTunnelSessionState INTEGER,
    cvpdnTunnelSessionCallDuration TimeTicks,
    cvpdnTunnelSessionPacketsOut Counter,
    cvpdnTunnelSessionBytesOut Counter,
    cvpdnTunnelSessionPacketsIn Counter,
    cvpdnTunnelSessionBytesIn Counter,
    cvpdnTunnelSessionDeviceType INTEGER,
    cvpdnTunnelSessionDeviceCallerId DisplayString,
    cvpdnTunnelSessionDevicePhyId InterfaceIndexOrZero,
    cvpdnTunnelSessionMultilink TruthValue,
    cvpdnTunnelSessionModemSlotIndex Gauge,
    cvpdnTunnelSessionModemPortIndex Gauge,
    cvpdnTunnelSessionDS1SlotIndex Gauge,
    cvpdnTunnelSessionDS1PortIndex Gauge,
    cvpdnTunnelSessionDS1ChannelIndex Gauge,
    cvpdnTunnelSessionModemCallStartTime TimeStamp,
    cvpdnTunnelSessionModemCallStartIndex Gauge
    }

cvpdnTunnelSessionId OBJECT-TYPE
    SYNTAX Gauge
    ACCESS not-accessible
    STATUS deprecated
    DESCRIPTION
        "The ID of an active VPDN tunnel user session."
    ::= { cvpdnTunnelSessionEntry 1 }

cvpdnTunnelSessionUserName OBJECT-TYPE
    SYNTAX DisplayString(SIZE(1..255))
--    Rsyntax OCTET STRING(SIZE(1..255))
    ACCESS read-only
    STATUS deprecated
    DESCRIPTION
        "The name of the user of the user session."
    ::= { cvpdnTunnelSessionEntry 2 }

cvpdnTunnelSessionState OBJECT-TYPE
    SYNTAX INTEGER {
        unknown(1),
        opening(2),
        open(3),
        closing(4),
        waitingForTunnel(5)
        }
    ACCESS read-only
    STATUS deprecated
    DESCRIPTION
        "The current state of an active user session. Each state 
        code is explained below:
        
                unknown: The current state of the tunnel's session 
        is unknown.
        
                opening: The user session has just been initiated 
        through a tunnel and is pending for the remote 
        end reply to complete the process.
        
                open: The user session is active.
        
                closing: The user session has just been closed and 
        is pending for the remote end reply to complete 
        the process.
        
        waitingForTunnel: The user session is in this state 
        when the tunnel which this session is going 
        through is still in CLOSED state. It waits for 
        the tunnel to become OPEN before the session 
        is allow to be fully established."
    ::= { cvpdnTunnelSessionEntry 3 }

cvpdnTunnelSessionCallDuration OBJECT-TYPE
    SYNTAX TimeTicks
    ACCESS read-only
    STATUS deprecated
    DESCRIPTION
        "This object specifies the call duration of the current
         active user session in value of system uptime."
    ::= { cvpdnTunnelSessionEntry 4 }

cvpdnTunnelSessionPacketsOut OBJECT-TYPE
    SYNTAX Counter
--  Units
--    packets
    ACCESS read-only
    STATUS deprecated
    DESCRIPTION
        "The total number of output packets through this active 
        user session."
    ::= { cvpdnTunnelSessionEntry 5 }

cvpdnTunnelSessionBytesOut OBJECT-TYPE
    SYNTAX Counter
--  Units
--    bytes
    ACCESS read-only
    STATUS deprecated
    DESCRIPTION
        "The total number of output bytes through this active 
        user session."
    ::= { cvpdnTunnelSessionEntry 6 }

cvpdnTunnelSessionPacketsIn OBJECT-TYPE
    SYNTAX Counter
--  Units
--    packets
    ACCESS read-only
    STATUS deprecated
    DESCRIPTION
        "The total number of input packets through this active 
        user session."
    ::= { cvpdnTunnelSessionEntry 7 }

cvpdnTunnelSessionBytesIn OBJECT-TYPE
    SYNTAX Counter
--  Units
--    bytes
    ACCESS read-only
    STATUS deprecated
    DESCRIPTION
        "The total number of input bytes through this active 
        user session."
    ::= { cvpdnTunnelSessionEntry 8 }

cvpdnTunnelSessionDeviceType OBJECT-TYPE
    SYNTAX INTEGER {
        other(1),
        asyncInternalModem(2),
        async(3),
        bchan(4),
        sync(5),
        virtualAccess(6),
        xdsl(7),
        cable(8)
        }
    ACCESS read-only
    STATUS deprecated
    DESCRIPTION
        "The type of physical devices that this user session
         is attached to for the local end of the tunnel. The meaning
         of each device type is explained below:
        
                other: Any device that has not been defined.
        
                asyncInternalModem: Modem Pool device of an access
                        server.
        
                async: A regular asynchronous serial interface.
        
                sync: A regular synchronous serial interface.
        
                bchan: An ISDN call.
        
                xdsl: Future application with xDSL devices.
        
                cable: Future application with Cable modem devices."
    ::= { cvpdnTunnelSessionEntry 9 }

cvpdnTunnelSessionDeviceCallerId OBJECT-TYPE
    SYNTAX DisplayString
--    Rsyntax OCTET STRING(SIZE(0..255))
    ACCESS read-only
    STATUS deprecated
    DESCRIPTION
        "The incoming caller identification of the user. It is
        the originating number that called into the device that
        initiates the user session. This object can be empty
        since not all dial device can provide caller ID 
        information."
    ::= { cvpdnTunnelSessionEntry 10 }

cvpdnTunnelSessionDevicePhyId OBJECT-TYPE
    SYNTAX InterfaceIndexOrZero
--    Rsyntax INTEGER(0..2147483647)
    ACCESS read-only
    STATUS deprecated
    DESCRIPTION
        "The device ID of the physical interface for the user
         session. The object is the the interface index which
        points to the iftable. For virtual interface that is
        not in the iftable, it will have zero value."
    ::= { cvpdnTunnelSessionEntry 11 }

cvpdnTunnelSessionMultilink OBJECT-TYPE
    SYNTAX TruthValue
--    Rsyntax INTEGER {
--        true(1),
--        false(2)
--        }
    ACCESS read-only
    STATUS deprecated
    DESCRIPTION
        "This object indicates whether the sesssion is part of
         a multilink or not."
    ::= { cvpdnTunnelSessionEntry 12 }

cvpdnTunnelSessionModemSlotIndex OBJECT-TYPE
    SYNTAX Gauge
    ACCESS read-only
    STATUS deprecated
    DESCRIPTION
        "The Modem Pool database slot index if it is associated 
        with this user session. Only a session with device
        of type asyncInternalModem will have a valid value for this
        object."
    ::= { cvpdnTunnelSessionEntry 13 }

cvpdnTunnelSessionModemPortIndex OBJECT-TYPE
    SYNTAX Gauge
    ACCESS read-only
    STATUS deprecated
    DESCRIPTION
        "The Modem Pool database port index if it is associated 
        with this user session. Only a session with a device
         of type asyncInternalModem will have a valid value for this
         object."
    ::= { cvpdnTunnelSessionEntry 14 }

cvpdnTunnelSessionDS1SlotIndex OBJECT-TYPE
    SYNTAX Gauge
    ACCESS read-only
    STATUS deprecated
    DESCRIPTION
        "The DS1 database slot index if it is associated 
        with this user session. Only a session with a device
         of type asyncInternalModem will have a valid value for 
        this object."
    ::= { cvpdnTunnelSessionEntry 15 }

cvpdnTunnelSessionDS1PortIndex OBJECT-TYPE
    SYNTAX Gauge
    ACCESS read-only
    STATUS deprecated
    DESCRIPTION
        "The DS1 database port index if it is associated 
        with this user session. Only a session with a device
         of type asyncInternalModem will have a a valid value for 
        this object."
    ::= { cvpdnTunnelSessionEntry 16 }

cvpdnTunnelSessionDS1ChannelIndex OBJECT-TYPE
    SYNTAX Gauge
    ACCESS read-only
    STATUS deprecated
    DESCRIPTION
        "The DS1 database channel index if it is associated 
        with this user session. Only a session over a device
         of type asyncInternalModem will have a valid value for 
        this object."
    ::= { cvpdnTunnelSessionEntry 17 }

cvpdnTunnelSessionModemCallStartTime OBJECT-TYPE
    SYNTAX TimeStamp
--    Rsyntax TimeTicks
    ACCESS read-only
    STATUS deprecated
    DESCRIPTION
        "The start time of the current modem call. Only a session 
                with a  device of type asyncInternalModem will have a valid 
        value for this object."
    ::= { cvpdnTunnelSessionEntry 18 }

cvpdnTunnelSessionModemCallStartIndex OBJECT-TYPE
    SYNTAX Gauge
    ACCESS read-only
    STATUS deprecated
    DESCRIPTION
        "Arbitrary small integer to distinguish modem calls that 
          occured at the same time tick. Only session over device
                asyncInternalModem will have a valid value for this
                object."
    ::= { cvpdnTunnelSessionEntry 19 }

cvpdnSessionAttrTable OBJECT-TYPE
    SYNTAX SEQUENCE OF CvpdnSessionAttrEntry
    ACCESS not-accessible
    STATUS mandatory
    DESCRIPTION
        "Table of information about individual sessions within
         the active tunnels. An entry is added to the table when
         a new session is initiated and removed from the
         table when the session is terminated."
    ::= { cvpdnTunnelSessionInfo 2 }

cvpdnSessionAttrEntry OBJECT-TYPE
    SYNTAX CvpdnSessionAttrEntry
    ACCESS not-accessible
    STATUS mandatory
    DESCRIPTION
        "An entry in the table, containing information about a single
         session within the tunnel."
    INDEX { cvpdnSystemTunnelType, cvpdnTunnelAttrTunnelId, cvpdnSessionAttrSessionId }
    ::= { cvpdnSessionAttrTable 1 }

CvpdnSessionAttrEntry ::= SEQUENCE {
    cvpdnSessionAttrSessionId INTEGER,
    cvpdnSessionAttrUserName DisplayString,
    cvpdnSessionAttrState INTEGER,
    cvpdnSessionAttrCallDuration TimeTicks,
    cvpdnSessionAttrPacketsOut Counter,
    cvpdnSessionAttrBytesOut Counter,
    cvpdnSessionAttrPacketsIn Counter,
    cvpdnSessionAttrBytesIn Counter,
    cvpdnSessionAttrDeviceType INTEGER,
    cvpdnSessionAttrDeviceCallerId DisplayString,
    cvpdnSessionAttrDevicePhyId InterfaceIndexOrZero,
    cvpdnSessionAttrMultilink TruthValue,
    cvpdnSessionAttrModemSlotIndex Gauge,
    cvpdnSessionAttrModemPortIndex Gauge,
    cvpdnSessionAttrDS1SlotIndex Gauge,
    cvpdnSessionAttrDS1PortIndex Gauge,
    cvpdnSessionAttrDS1ChannelIndex Gauge,
    cvpdnSessionAttrModemCallStartTime TimeStamp,
    cvpdnSessionAttrModemCallStartIndex Gauge,
    cvpdnSessionAttrVirtualCircuitID Gauge,
    cvpdnSessionAttrSentPktsDropped Counter,
    cvpdnSessionAttrRecvPktsDropped Counter
    }

cvpdnSessionAttrSessionId OBJECT-TYPE
    SYNTAX INTEGER(0..65535)
    ACCESS not-accessible
    STATUS mandatory
    DESCRIPTION
        "The ID of an active VPDN session."
    ::= { cvpdnSessionAttrEntry 1 }

cvpdnSessionAttrUserName OBJECT-TYPE
    SYNTAX DisplayString(SIZE(1..255))
--    Rsyntax OCTET STRING(SIZE(1..255))
    ACCESS read-only
    STATUS mandatory
    DESCRIPTION
        "The name of the user of the session."
    ::= { cvpdnSessionAttrEntry 2 }

cvpdnSessionAttrState OBJECT-TYPE
    SYNTAX INTEGER {
        unknown(1),
        l2fOpening(2),
        l2fOpen(3),
        l2fCloseWait(4),
        l2fWaitingForTunnel(5),
        l2tpIdle(6),
        l2tpWaitingTunnel(7),
        l2tpWaitReply(8),
        l2tpWaitConnect(9),
        l2tpEstablished(10),
        l2tpShuttingDown(11),
        pptpWaitVAccess(12),
        pptpPacEstablished(13),
        pptpWaitTunnel(14),
        pptpWaitOCRP(15),
        pptpPnsEstablished(16),
        pptpWaitCallDisc(17),
        pptpTerminal(18)
        }
    ACCESS read-only
    STATUS mandatory
    DESCRIPTION
        "The current state of a tunnel session.
         L2F tunnel sessions will have states with the 'l2f' prefix.
         L2TP tunnel sessions will have states with the 'l2tp' prefix.
        
         Each state code is explained below:
        
                    unknown: The current state of the tunnel's session 
                            is unknown.
        
                    l2fOpening: The session has just been initiated 
                            through a tunnel and is pending for the remote 
                            end reply to complete the process.
        
                    l2fOpen: The session is active.
        
                    l2fCloseWait: The session has just been closed and 
                            is pending for the remote end reply to complete 
                            the process.
        
                    l2fWaitingForTunnel: The session is in this state 
                            when the tunnel which this session is going 
                            through is still in CLOSED state. It waits for 
                            the tunnel to become OPEN before the session 
                            is allow to be fully established.
        
                    l2tpIdle: No session is initiated yet.
        
                    l2tpWaitingTunnel: The session is waiting for the
                            tunnel to be established.
        
                    l2tpWaitReply: The session has been initiated and is 
                            pending for the remote end reply to complete
                            the process.
        
                    l2tpWaitConnect: This end has acknowledged a connection
                            request and is waiting for the remote end
                            to connect.
        
                    l2tpEstablished: The session is active.
        
                    l2tpShuttingDown: The session is in progress of 
                            shutting down.
        
        pptpWaitVAccess: The seession is waiting for the
        creation of a virtual access interface. 
        
        pptpPacEstablished:  The session is active.
        
        pptpWaitTunnel: The session is waiting for the tunnel
        to be established.  
        
        pptpWaitOCRP:  The session has been initiated and is 
        pending for the remote end reply to complete
        the process. 
        
        pptpPnsEstablished: The session is active.
        
        pptpWaitCallDisc: Session shutdown is in progress."
    ::= { cvpdnSessionAttrEntry 3 }

cvpdnSessionAttrCallDuration OBJECT-TYPE
    SYNTAX TimeTicks
    ACCESS read-only
    STATUS mandatory
    DESCRIPTION
        "This object specifies the call duration of the current
         active session."
    ::= { cvpdnSessionAttrEntry 4 }

cvpdnSessionAttrPacketsOut OBJECT-TYPE
    SYNTAX Counter
--  Units
--    packets
    ACCESS read-only
    STATUS mandatory
    DESCRIPTION
        "The total number of output packets through this active 
         session."
    ::= { cvpdnSessionAttrEntry 5 }

cvpdnSessionAttrBytesOut OBJECT-TYPE
    SYNTAX Counter
--  Units
--    bytes
    ACCESS read-only
    STATUS mandatory
    DESCRIPTION
        "The total number of output bytes through this active 
         session."
    ::= { cvpdnSessionAttrEntry 6 }

cvpdnSessionAttrPacketsIn OBJECT-TYPE
    SYNTAX Counter
--  Units
--    packets
    ACCESS read-only
    STATUS mandatory
    DESCRIPTION
        "The total number of input packets through this active 
         session."
    ::= { cvpdnSessionAttrEntry 7 }

cvpdnSessionAttrBytesIn OBJECT-TYPE
    SYNTAX Counter
--  Units
--    bytes
    ACCESS read-only
    STATUS mandatory
    DESCRIPTION
        "The total number of input bytes through this active 
         session."
    ::= { cvpdnSessionAttrEntry 8 }

cvpdnSessionAttrDeviceType OBJECT-TYPE
    SYNTAX INTEGER {
        other(1),
        asyncInternalModem(2),
        async(3),
        bchan(4),
        sync(5),
        virtualAccess(6),
        xdsl(7),
        cable(8)
        }
    ACCESS read-only
    STATUS mandatory
    DESCRIPTION
        "The type of physical devices that this session is attached
         to for the local end of the tunnel. The meaning of each 
         device type is explained below:
        
                    other: Any device that has not been defined.
        
                    asyncInternalModem: Modem Pool device of an access
                            server.
        
                    async: A regular asynchronous serial interface.
        
                    sync: A regular synchronous serial interface.
        
                    bchan: An ISDN call.
        
                    xdsl: xDSL interface.
        
                    cable: cable modem interface."
    ::= { cvpdnSessionAttrEntry 9 }

cvpdnSessionAttrDeviceCallerId OBJECT-TYPE
    SYNTAX DisplayString
--    Rsyntax OCTET STRING(SIZE(0..255))
    ACCESS read-only
    STATUS mandatory
    DESCRIPTION
        "The incoming caller identification of the user. It is
         the originating number that called into the device that
         initiates the session. This object can be empty
         since not all dial devices can provide caller ID 
         information."
    ::= { cvpdnSessionAttrEntry 10 }

cvpdnSessionAttrDevicePhyId OBJECT-TYPE
    SYNTAX InterfaceIndexOrZero
--    Rsyntax INTEGER(0..2147483647)
    ACCESS read-only
    STATUS mandatory
    DESCRIPTION
        "The device ID of the physical interface for the
         session. The object is the the interface index which
         points to the iftable. For virtual interfaces that are
         not in the ifTable, the value will be zero."
    ::= { cvpdnSessionAttrEntry 11 }

cvpdnSessionAttrMultilink OBJECT-TYPE
    SYNTAX TruthValue
--    Rsyntax INTEGER {
--        true(1),
--        false(2)
--        }
    ACCESS read-only
    STATUS mandatory
    DESCRIPTION
        "This object indicates whether the session is part of
         a multilink PPP bundle, even if there is only one link
         or session in the bundle.  If it is multilink PPP, the
         value is true."
    ::= { cvpdnSessionAttrEntry 12 }

cvpdnSessionAttrModemSlotIndex OBJECT-TYPE
    SYNTAX Gauge
    ACCESS read-only
    STATUS mandatory
    DESCRIPTION
        "The Modem Pool database slot index if it is associated 
         with this session. Only a session with device
         of type 'asyncInternalModem' will have a valid value for
         this object; otherwise, it is not instantiated."
    ::= { cvpdnSessionAttrEntry 13 }

cvpdnSessionAttrModemPortIndex OBJECT-TYPE
    SYNTAX Gauge
    ACCESS read-only
    STATUS mandatory
    DESCRIPTION
        "The Modem Pool database port index if it is associated 
         with this session. Only a session with a device
         of type 'asyncInternalModem' will have a valid value for
         this object; otherwise, it is not instantiated."
    ::= { cvpdnSessionAttrEntry 14 }

cvpdnSessionAttrDS1SlotIndex OBJECT-TYPE
    SYNTAX Gauge
    ACCESS read-only
    STATUS mandatory
    DESCRIPTION
        "The DS1 database slot index if it is associated 
         with this session. Only a session with a device
         of type 'asyncInternalModem' will have a valid value for
         this object; otherwise it is not instantiated."
    ::= { cvpdnSessionAttrEntry 15 }

cvpdnSessionAttrDS1PortIndex OBJECT-TYPE
    SYNTAX Gauge
    ACCESS read-only
    STATUS mandatory
    DESCRIPTION
        "The DS1 database port index if it is associated 
         with this session. Only a session with a device
         of type 'asyncInternalModem' will have a valid value for
         this object; otherwise it is not instantiated."
    ::= { cvpdnSessionAttrEntry 16 }

cvpdnSessionAttrDS1ChannelIndex OBJECT-TYPE
    SYNTAX Gauge
    ACCESS read-only
    STATUS mandatory
    DESCRIPTION
        "The DS1 database channel index if it is associated 
         with this session. Only a session over a device
         of type 'asyncInternalModem' will have a valid value for
         this object; otherwise it is not instantiated."
    ::= { cvpdnSessionAttrEntry 17 }

cvpdnSessionAttrModemCallStartTime OBJECT-TYPE
    SYNTAX TimeStamp
--    Rsyntax TimeTicks
    ACCESS read-only
    STATUS mandatory
    DESCRIPTION
        "The start time of the current modem call. Only a session 
         with a device of type 'asyncInternalModem' will have
         a valid value for this object; otherwise, it is not
         instantiated."
    ::= { cvpdnSessionAttrEntry 18 }

cvpdnSessionAttrModemCallStartIndex OBJECT-TYPE
    SYNTAX Gauge
    ACCESS read-only
    STATUS mandatory
    DESCRIPTION
        "Arbitrary small integer to distinguish modem calls that 
         occured at the same time tick. Only session over device
         'asyncInternalModem' will have a valid value for this
         object; otherwise, it is not instantiated."
    ::= { cvpdnSessionAttrEntry 19 }

cvpdnSessionAttrVirtualCircuitID OBJECT-TYPE
    SYNTAX Gauge
    ACCESS read-only
    STATUS mandatory
    DESCRIPTION
        "The virtual circuit ID of an active Layer 2 VPN session."
    ::= { cvpdnSessionAttrEntry 20 }

cvpdnSessionAttrSentPktsDropped OBJECT-TYPE
    SYNTAX Counter
--  Units
--    packets
    ACCESS read-only
    STATUS mandatory
    DESCRIPTION
        "The total number of dropped packets that could not be
        sent into this active session."
    ::= { cvpdnSessionAttrEntry 21 }

cvpdnSessionAttrRecvPktsDropped OBJECT-TYPE
    SYNTAX Counter
--  Units
--    packets
    ACCESS read-only
    STATUS mandatory
    DESCRIPTION
        "The total number of dropped packets that were received
         from this active session."
    ::= { cvpdnSessionAttrEntry 22 }

cvpdnUserToFailHistInfoTable OBJECT-TYPE
    SYNTAX SEQUENCE OF CvpdnUserToFailHistInfoEntry
    ACCESS not-accessible
    STATUS mandatory
    DESCRIPTION
        "Table of the record of failure objects which are
         referencable by an user name. Only a name that has
         a valid item in the cisco IOS VPDN failure history 
        table will yield a valid entry in this table. The
        table has a maximum size of 50 entries. Only the
        newest 50 entries will be kept in the table."
    ::= { cvpdnUserToFailHistInfo 1 }

cvpdnUserToFailHistInfoEntry OBJECT-TYPE
    SYNTAX CvpdnUserToFailHistInfoEntry
    ACCESS not-accessible
    STATUS mandatory
    DESCRIPTION
        "An entry in the table, containing failure history
         relevant to an user name."
    INDEX { cvpdnUnameToFailHistUname, cvpdnUnameToFailHistTunnelId }
    ::= { cvpdnUserToFailHistInfoTable 1 }

CvpdnUserToFailHistInfoEntry ::= SEQUENCE {
    cvpdnUnameToFailHistUname DisplayString,
    cvpdnUnameToFailHistTunnelId Gauge,
    cvpdnUnameToFailHistUserId Gauge,
    cvpdnUnameToFailHistLocalInitConn TruthValue,
    cvpdnUnameToFailHistLocalName DisplayString,
    cvpdnUnameToFailHistRemoteName DisplayString,
    cvpdnUnameToFailHistSourceIp IpAddress,
    cvpdnUnameToFailHistDestIp IpAddress,
    cvpdnUnameToFailHistCount Counter,
    cvpdnUnameToFailHistFailTime TimeStamp,
    cvpdnUnameToFailHistFailType DisplayString,
    cvpdnUnameToFailHistFailReason DisplayString
    }

cvpdnUnameToFailHistUname OBJECT-TYPE
    SYNTAX DisplayString(SIZE(1..255))
--    Rsyntax OCTET STRING(SIZE(1..255))
    ACCESS not-accessible
    STATUS mandatory
    DESCRIPTION
        "The user name for this failure entry."
    ::= { cvpdnUserToFailHistInfoEntry 1 }

cvpdnUnameToFailHistTunnelId OBJECT-TYPE
    SYNTAX Gauge
    ACCESS not-accessible
    STATUS mandatory
    DESCRIPTION
        "The Tunnel ID for this failure entry. If it is the 
        instigator of the tunnel, the ID is the TS tunnel ID, 
        otherwise it is the NAS tunnel ID."
    ::= { cvpdnUserToFailHistInfoEntry 2 }

cvpdnUnameToFailHistUserId OBJECT-TYPE
    SYNTAX Gauge
    ACCESS read-only
    STATUS mandatory
    DESCRIPTION
        "The user ID of this failure entry."
    ::= { cvpdnUserToFailHistInfoEntry 3 }

cvpdnUnameToFailHistLocalInitConn OBJECT-TYPE
    SYNTAX TruthValue
--    Rsyntax INTEGER {
--        true(1),
--        false(2)
--        }
    ACCESS read-only
    STATUS mandatory
    DESCRIPTION
        "This object indicates whether the tunnel in which the 
        failure occurred was generated locally or not."
    ::= { cvpdnUserToFailHistInfoEntry 4 }

cvpdnUnameToFailHistLocalName OBJECT-TYPE
    SYNTAX DisplayString
--    Rsyntax OCTET STRING(SIZE(0..255))
    ACCESS read-only
    STATUS mandatory
    DESCRIPTION
        "The local name of the VPDN tunnel in which the failure 
        occurred. It will be the NAS name of the tunnel if the 
        system serves as the NAS, or the TS name of the tunnel 
        if the system serves as the tunnel server. The local name is
         the configured host name of the system. This object can
        be empty if the failure occurred prior to successful tunnel
        projection, thus no source name will be available."
    ::= { cvpdnUserToFailHistInfoEntry 5 }

cvpdnUnameToFailHistRemoteName OBJECT-TYPE
    SYNTAX DisplayString
--    Rsyntax OCTET STRING(SIZE(0..255))
    ACCESS read-only
    STATUS mandatory
    DESCRIPTION
        "The remote name of the VPDN tunnel in which the failure 
        occurred. It will be the tunnel server name of the tunnel if 
        the system is a NAS, or the NAS name of the tunnel 
        if the system serves as the tunnel server. This object can
         be empty if the failure occurred prior to successful tunnel
         projection, thus no source name will be available."
    ::= { cvpdnUserToFailHistInfoEntry 6 }

cvpdnUnameToFailHistSourceIp OBJECT-TYPE
    SYNTAX IpAddress
    ACCESS read-only
    STATUS mandatory
    DESCRIPTION
        "The source IP address of the tunnel in which the failure 
        occurred. This IP address is that of the interface at the 
        instigator end of the tunnel. "
    ::= { cvpdnUserToFailHistInfoEntry 7 }

cvpdnUnameToFailHistDestIp OBJECT-TYPE
    SYNTAX IpAddress
    ACCESS read-only
    STATUS mandatory
    DESCRIPTION
        "The destination IP address of the tunnel in which the failure 
        occurred. This IP address is that of the interface at the 
        receiver end of the tunnel. "
    ::= { cvpdnUserToFailHistInfoEntry 8 }

cvpdnUnameToFailHistCount OBJECT-TYPE
    SYNTAX Counter
--  Units
--    failures
    ACCESS read-only
    STATUS mandatory
    DESCRIPTION
        "This object is incremented when multiple failures has been 
        experienced by this user on this tunnel. Seeing a delta of >1 
        is an indication that the current failure record is the latest 
        of a series of failures that has been recorded."
    ::= { cvpdnUserToFailHistInfoEntry 9 }

cvpdnUnameToFailHistFailTime OBJECT-TYPE
    SYNTAX TimeStamp
--    Rsyntax TimeTicks
    ACCESS read-only
    STATUS mandatory
    DESCRIPTION
        "This object specifies the time when the failure is occured."
    ::= { cvpdnUserToFailHistInfoEntry 10 }

cvpdnUnameToFailHistFailType OBJECT-TYPE
    SYNTAX DisplayString(SIZE(1..255))
--    Rsyntax OCTET STRING(SIZE(1..255))
    ACCESS read-only
    STATUS mandatory
    DESCRIPTION
        "The type of failure for the current failure record. It
        comes in a form of a an ascii string which describes
        the type of failure."
    ::= { cvpdnUserToFailHistInfoEntry 11 }

cvpdnUnameToFailHistFailReason OBJECT-TYPE
    SYNTAX DisplayString(SIZE(1..255))
--    Rsyntax OCTET STRING(SIZE(1..255))
    ACCESS read-only
    STATUS mandatory
    DESCRIPTION
        "The reason of failure for the current failure record."
    ::= { cvpdnUserToFailHistInfoEntry 12 }

cvpdnNotifSessionID OBJECT-TYPE
    SYNTAX INTEGER(0..65535)
    ACCESS read-only
    STATUS mandatory
    DESCRIPTION
        "This object contains the local session ID of the
        L2X session for which this notification has been
        generated."
    ::= { ciscoVpdnMgmtMIBNotifs 1 }

cvpdnNotifSessionEvent OBJECT-TYPE
    SYNTAX INTEGER {
        up(1),
        down(2)
        }
    ACCESS read-only
    STATUS mandatory
    DESCRIPTION
        "Indicates the event that generated the L2X session
         notification."
    ::= { ciscoVpdnMgmtMIBNotifs 2 }

cvpdnTemplateTable OBJECT-TYPE
    SYNTAX SEQUENCE OF CvpdnTemplateEntry
    ACCESS not-accessible
    STATUS mandatory
    DESCRIPTION
        "Table of information about the VPDN templates.  The VPDN
        template is a grouping mechanism that allows configuration
        settings to be shared among multiple VPDN groups.  One such
        setting is a limit on the number of active sessions across
        all VPDN groups associated with the template.  The template
        table allows customers to monitor template-wide information
        such as tracking the allocation of sessions across templates."
    ::= { cvpdnTemplateInfo 1 }

cvpdnTemplateEntry OBJECT-TYPE
    SYNTAX CvpdnTemplateEntry
    ACCESS not-accessible
    STATUS mandatory
    DESCRIPTION
        "An entry in the table, containing information about a single
        VPDN template."
    INDEX { --?? IMPLIED may cause problems
            IMPLIED cvpdnTemplateName }
    ::= { cvpdnTemplateTable 1 }

CvpdnTemplateEntry ::= SEQUENCE {
    cvpdnTemplateName SnmpAdminString,
    cvpdnTemplateActiveSessions Gauge
    }

cvpdnTemplateName OBJECT-TYPE
    SYNTAX SnmpAdminString(SIZE(1..255))
--    Rsyntax OCTET STRING(SIZE(1..255))
    ACCESS not-accessible
    STATUS mandatory
    DESCRIPTION
        "The name of the VPDN template."
    ::= { cvpdnTemplateEntry 1 }

cvpdnTemplateActiveSessions OBJECT-TYPE
    SYNTAX Gauge
--  Units
--    sessions
    ACCESS read-only
    STATUS mandatory
    DESCRIPTION
        "The total number of active session in all groups associated
        with the template."
    ::= { cvpdnTemplateEntry 2 }

cvpdnNotifSession TRAP-TYPE
-- Reverse mappable trap
    ENTERPRISE ciscoVpdnMgmtMIB
    VARIABLES {
        cvpdnNotifSessionID, cvpdnNotifSessionEvent, 
        cvpdnSessionAttrDevicePhyId, 
        cvpdnSessionAttrVirtualCircuitID }
--  Status
--    mandatory
    DESCRIPTION
        "Conveys an event regarding the L2X session with the
         indicated session ID and Xconnect VCID."
    ::= 3

cvpdnSystemInfoGroup OBJECT IDENTIFIER ::= { ciscoVpdnMgmtMIBGroups 1 }
-- OBJECT-GROUP
--  Status
--    deprecated
--  Descr
--    A collection of objects providing VPDN system status information.
--  objects
--    cvpdnTunnelTotal, cvpdnSessionTotal, cvpdnDeniedUsersTotal

cvpdnTunnelInfoGroup OBJECT IDENTIFIER ::= { ciscoVpdnMgmtMIBGroups 2 }
-- OBJECT-GROUP
--  Status
--    deprecated
--  Descr
--    A collection of objects providing VPDN tunnel status information.
--  objects
--    cvpdnTunnelRemoteTunnelId, cvpdnTunnelLocalName, 
--    cvpdnTunnelRemoteName, cvpdnTunnelRemoteEndpointName, 
--    cvpdnTunnelLocalInitConnection, cvpdnTunnelOrigCause, 
--    cvpdnTunnelState, cvpdnTunnelActiveSessions, 
--    cvpdnTunnelDeniedUsers, cvpdnTunnelSoftshut, 
--    cvpdnTunnelNetworkServiceType, cvpdnTunnelLocalIpAddress, 
--    cvpdnTunnelSourceIpAddress, cvpdnTunnelRemoteIpAddress

cvpdnTunnelSessionInfoGroup OBJECT IDENTIFIER ::= { ciscoVpdnMgmtMIBGroups 3 }
-- OBJECT-GROUP
--  Status
--    deprecated
--  Descr
--    A collection of objects providing session information of VPDN tunnel.
--  objects
--    cvpdnTunnelSessionUserName, cvpdnTunnelSessionState, 
--    cvpdnTunnelSessionCallDuration, cvpdnTunnelSessionPacketsOut, 
--    cvpdnTunnelSessionBytesOut, cvpdnTunnelSessionPacketsIn, 
--    cvpdnTunnelSessionBytesIn, cvpdnTunnelSessionDeviceType, 
--    cvpdnTunnelSessionDeviceCallerId, 
--    cvpdnTunnelSessionDevicePhyId, cvpdnTunnelSessionMultilink, 
--    cvpdnTunnelSessionModemSlotIndex, 
--    cvpdnTunnelSessionModemPortIndex, 
--    cvpdnTunnelSessionDS1SlotIndex, 
--    cvpdnTunnelSessionDS1PortIndex, 
--    cvpdnTunnelSessionDS1ChannelIndex, 
--    cvpdnTunnelSessionModemCallStartTime, 
--    cvpdnTunnelSessionModemCallStartIndex

cvpdnUserToFailHistInfoGroup OBJECT IDENTIFIER ::= { ciscoVpdnMgmtMIBGroups 4 }
-- OBJECT-GROUP
--  Status
--    mandatory
--  Descr
--    A collection of objects providing user failure information of VPDN 
--     system.
--  objects
--    cvpdnUnameToFailHistUserId, cvpdnUnameToFailHistLocalInitConn, 
--    cvpdnUnameToFailHistLocalName, cvpdnUnameToFailHistRemoteName, 
--    cvpdnUnameToFailHistSourceIp, cvpdnUnameToFailHistDestIp, 
--    cvpdnUnameToFailHistCount, cvpdnUnameToFailHistFailTime, 
--    cvpdnUnameToFailHistFailType, cvpdnUnameToFailHistFailReason

cvpdnSystemGroup OBJECT IDENTIFIER ::= { ciscoVpdnMgmtMIBGroups 5 }
-- OBJECT-GROUP
--  Status
--    mandatory
--  Descr
--    A collection of objects providing VPDN system status information
--     for multiple tunnel types.
--  objects
--    cvpdnSystemTunnelTotal, cvpdnSystemSessionTotal, 
--    cvpdnSystemDeniedUsersTotal

cvpdnTunnelAttrGroup OBJECT IDENTIFIER ::= { ciscoVpdnMgmtMIBGroups 6 }
-- OBJECT-GROUP
--  Status
--    mandatory
--  Descr
--    A collection of objects providing VPDN tunnel attribute
--     information for multiple tunnel types.
--  objects
--    cvpdnTunnelAttrRemoteTunnelId, cvpdnTunnelAttrLocalName, 
--    cvpdnTunnelAttrRemoteName, cvpdnTunnelAttrRemoteEndpointName, 
--    cvpdnTunnelAttrLocalInitConnection, cvpdnTunnelAttrOrigCause, 
--    cvpdnTunnelAttrState, cvpdnTunnelAttrActiveSessions, 
--    cvpdnTunnelAttrDeniedUsers, cvpdnTunnelAttrSoftshut, 
--    cvpdnTunnelAttrNetworkServiceType, 
--    cvpdnTunnelAttrLocalIpAddress, cvpdnTunnelAttrSourceIpAddress, 
--    cvpdnTunnelAttrRemoteIpAddress

cvpdnSessionAttrGroup OBJECT IDENTIFIER ::= { ciscoVpdnMgmtMIBGroups 7 }
-- OBJECT-GROUP
--  Status
--    deprecated
--  Descr
--    A collection of objects providing session attributed
--     information for multiple tunnel types.
--  objects
--    cvpdnSessionAttrUserName, cvpdnSessionAttrState, 
--    cvpdnSessionAttrCallDuration, cvpdnSessionAttrPacketsOut, 
--    cvpdnSessionAttrBytesOut, cvpdnSessionAttrPacketsIn, 
--    cvpdnSessionAttrBytesIn, cvpdnSessionAttrDeviceType, 
--    cvpdnSessionAttrDeviceCallerId, cvpdnSessionAttrDevicePhyId, 
--    cvpdnSessionAttrMultilink, cvpdnSessionAttrModemSlotIndex, 
--    cvpdnSessionAttrModemPortIndex, cvpdnSessionAttrDS1SlotIndex, 
--    cvpdnSessionAttrDS1PortIndex, cvpdnSessionAttrDS1ChannelIndex, 
--    cvpdnSessionAttrModemCallStartTime, 
--    cvpdnSessionAttrModemCallStartIndex

cvpdnSessionAttrGroupRev1 OBJECT IDENTIFIER ::= { ciscoVpdnMgmtMIBGroups 8 }
-- OBJECT-GROUP
--  Status
--    mandatory
--  Descr
--    A collection of objects providing session attributed
--     information for multiple tunnel types.
--  objects
--    cvpdnSessionAttrUserName, cvpdnSessionAttrState, 
--    cvpdnSessionAttrCallDuration, cvpdnSessionAttrPacketsOut, 
--    cvpdnSessionAttrBytesOut, cvpdnSessionAttrPacketsIn, 
--    cvpdnSessionAttrBytesIn, cvpdnSessionAttrDeviceType, 
--    cvpdnSessionAttrDeviceCallerId, cvpdnSessionAttrDevicePhyId, 
--    cvpdnSessionAttrMultilink, cvpdnSessionAttrModemSlotIndex, 
--    cvpdnSessionAttrModemPortIndex, cvpdnSessionAttrDS1SlotIndex, 
--    cvpdnSessionAttrDS1PortIndex, cvpdnSessionAttrDS1ChannelIndex, 
--    cvpdnSessionAttrModemCallStartTime, 
--    cvpdnSessionAttrModemCallStartIndex, 
--    cvpdnSessionAttrVirtualCircuitID, 
--    cvpdnSessionAttrSentPktsDropped, 
--    cvpdnSessionAttrRecvPktsDropped

cvpdnNotifEnabledGroup OBJECT IDENTIFIER ::= { ciscoVpdnMgmtMIBGroups 9 }
-- OBJECT-GROUP
--  Status
--    mandatory
--  Descr
--    A collection of objects indicating whether Layer 2 VPN
--     notifications are enabled.
--  objects
--    cvpdnSystemNotifSessionEnabled, cvpdnNotifSessionID, 
--    cvpdnNotifSessionEvent

cvpdnTemplateGroup OBJECT IDENTIFIER ::= { ciscoVpdnMgmtMIBGroups 11 }
-- OBJECT-GROUP
--  Status
--    mandatory
--  Descr
--    A collection of objects providing VPDN template information.
--  objects
--    cvpdnTemplateActiveSessions

cvpdnSessionNotifGroup OBJECT IDENTIFIER ::= { ciscoVpdnMgmtMIBGroups 10 }
-- NOTIFICATION-GROUP
--  Status
--    mandatory
--  Descr
--    A collection of objects providing basic Layer 2 VPN
--     session notifications.
--  notifications
--    cvpdnNotifSession

ciscoVpdnMgmtMIBCompliance OBJECT IDENTIFIER ::= { ciscoVpdnMgmtMIBCompliances 1 }
-- MODULE-COMPLIANCE
--  Status
--    obsolete
--  Descr
--    The compliance statement for entities which implement
--    the Cisco VPDN Management MIB
--  Module
--    >>current<<
--   MandGroup
--    cvpdnSystemInfoGroup
--   MandGroup
--    cvpdnTunnelInfoGroup
--   MandGroup
--    cvpdnTunnelSessionInfoGroup
--   MandGroup
--    cvpdnUserToFailHistInfoGroup

ciscoVpdnMgmtMIBComplianceRev1 OBJECT IDENTIFIER ::= { ciscoVpdnMgmtMIBCompliances 2 }
-- MODULE-COMPLIANCE
--  Status
--    deprecated
--  Descr
--    The compliance statement for entities which implement
--    the Cisco VPDN Management MIB
--  Module
--    >>current<<
--   MandGroup
--    cvpdnSystemInfoGroup
--   MandGroup
--    cvpdnTunnelInfoGroup
--   MandGroup
--    cvpdnTunnelSessionInfoGroup
--   MandGroup
--    cvpdnUserToFailHistInfoGroup
--   MandGroup
--    cvpdnSystemGroup
--   MandGroup
--    cvpdnTunnelAttrGroup
--   MandGroup
--    cvpdnSessionAttrGroup

ciscoVpdnMgmtMIBComplianceRev2 OBJECT IDENTIFIER ::= { ciscoVpdnMgmtMIBCompliances 3 }
-- MODULE-COMPLIANCE
--  Status
--    deprecated
--  Descr
--    The compliance statement for entities which implement
--    the Cisco VPDN Management MIB
--  Module
--    >>current<<
--   MandGroup
--    cvpdnUserToFailHistInfoGroup
--   MandGroup
--    cvpdnSystemGroup
--   MandGroup
--    cvpdnTunnelAttrGroup
--   MandGroup
--    cvpdnSessionAttrGroupRev1

ciscoVpdnMgmtMIBComplianceRev3 OBJECT IDENTIFIER ::= { ciscoVpdnMgmtMIBCompliances 4 }
-- MODULE-COMPLIANCE
--  Status
--    mandatory
--  Descr
--    The compliance statement for entities which implement
--    the Cisco VPDN Management MIB
--  Module
--    >>current<<
--   MandGroup
--    cvpdnUserToFailHistInfoGroup
--   MandGroup
--    cvpdnSystemGroup
--   MandGroup
--    cvpdnTunnelAttrGroup
--   MandGroup
--    cvpdnSessionAttrGroupRev1
--   MandGroup
--    cvpdnTemplateGroup


END
