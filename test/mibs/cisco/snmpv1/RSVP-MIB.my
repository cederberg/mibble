-- MIB file created 09-Aug-2001 15:16:19, by
--   SMICng version 2.2.11-beta(PRO)(Solaris), January 20, 2001. Enterprise key cisco.com

RSVP-MIB DEFINITIONS ::= BEGIN

-- From file: "RSVP-MIB.my"
-- Compile options "4 7 F H N W 03 06 0B 0G 0N 0T"

IMPORTS
    mib-2
            FROM SNMPv2-SMI-v1
    TruthValue, RowStatus, TimeStamp, TestAndIncr, TimeInterval
            FROM SNMPv2-TC-v1
    Port, SessionNumber, SessionType, Protocol, QosService, 
    intSrvFlowStatus, MessageSize, BitRate, BurstSize
            FROM INT-SERV-MIB
    ifIndex, InterfaceIndex
            FROM IF-MIB
    Gauge
            FROM RFC1155-SMI
    OBJECT-TYPE
            FROM RFC-1212
    TRAP-TYPE
            FROM RFC-1215;

rsvp OBJECT IDENTIFIER ::= { mib-2 51 }
-- MODULE-IDENTITY
--  LastUpdated
--    9808251820Z
--  OrgName
--    IETF RSVP Working Group
--  ContactInfo
--        Fred Baker
--    Postal: Cisco Systems
--     519 Lado Drive
--     Santa Barbara, California 93111
--    Tel:    +1 805 681 0115
--    E-Mail: fred@cisco.com
--    
--     John Krawczyk
--    Postal: ArrowPoint Communications
--     235 Littleton Road
--     Westford, Massachusetts 01886
--    Tel:    +1 508 692 5875
--    E-Mail: jjk@tiac.net
--    
--     Arun Sastry
--    Postal: Cisco Systems
--     3 The Square
--     Stockley Park, Uxbridge
--     Middlesex, UB11 1BN
--     UK
--    Tel:    +44 181 756 8693
--    E-Mail: arun@cisco.com
--  Descr
--    The MIB module to describe the RSVP Protocol

rsvpObjects     OBJECT IDENTIFIER ::= { rsvp 1 }
rsvpGenObjects  OBJECT IDENTIFIER ::= { rsvp 2 }
rsvpNotificationsPrefix OBJECT IDENTIFIER ::= { rsvp 3 }
rsvpConformance OBJECT IDENTIFIER ::= { rsvp 4 }
rsvpNotifications OBJECT IDENTIFIER ::= { rsvpNotificationsPrefix 0 }
rsvpGroups      OBJECT IDENTIFIER ::= { rsvpConformance 1 }
rsvpCompliances OBJECT IDENTIFIER ::= { rsvpConformance 2 }

RsvpEncapsulation ::= INTEGER {
        ip(1),
        udp(2),
        both(3)
        }
-- TEXTUAL-CONVENTION
--  Status
--    mandatory
--  Descr
--    This indicates the encapsulation that an  RSVP
--    Neighbor is perceived to be using.

RefreshInterval ::= INTEGER(0..2147483647)
-- TEXTUAL-CONVENTION
--  DspHint
--    d
--  Status
--    mandatory
--  Descr
--    The number of milliseconds that  are  expected
--    to elapse  between   refreshes  of  path or
--    reservation  state.    Unrefreshed  Path or
--    reservation state  is  removed  after  a small
--    multiple of this period.

rsvpSessionNewIndex OBJECT-TYPE
    SYNTAX TestAndIncr
--    Rsyntax INTEGER(0..2147483647)
    ACCESS read-write
    STATUS mandatory
    DESCRIPTION
        "This  object  is  used  to assign values to
        rsvpSessionNumber   as  described  in  'Textual
        Conventions for SNMPv2'.  The  network  manager
        reads  the  object, and  then writes the value
        back in the SET that creates a new instance of
        rsvpSessionEntry.   If  the SET fails with the
        code 'inconsistentValue', then the process must
        be  repeated;  If  the  SET succeeds, then the
        object is incremented, and the new instance is
        created according to the manager's directions."
    ::= { rsvpGenObjects 5 }

rsvpSessionTable OBJECT-TYPE
    SYNTAX SEQUENCE OF RsvpSessionEntry
    ACCESS not-accessible
    STATUS mandatory
    DESCRIPTION
        "A table  of  all  sessions seen  by  a  given
        system."
    ::= { rsvpObjects 1 }

rsvpSessionEntry OBJECT-TYPE
    SYNTAX RsvpSessionEntry
    ACCESS not-accessible
    STATUS mandatory
    DESCRIPTION
        "A single session seen by a given system."
    INDEX { rsvpSessionNumber }
    ::= { rsvpSessionTable 1 }

RsvpSessionEntry ::= SEQUENCE {
    rsvpSessionNumber SessionNumber,
    rsvpSessionType SessionType,
    rsvpSessionDestAddr OCTET STRING,
    rsvpSessionDestAddrLength INTEGER,
    rsvpSessionProtocol Protocol,
    rsvpSessionPort Port,
    rsvpSessionSenders Gauge,
    rsvpSessionReceivers Gauge,
    rsvpSessionRequests Gauge
    }

rsvpSessionNumber OBJECT-TYPE
    SYNTAX SessionNumber
--    Rsyntax INTEGER(0..2147483647)
    ACCESS not-accessible
    STATUS mandatory
    DESCRIPTION
        "The number of this session.  This is for  SNMP
        Indexing  purposes  only and has no relation to
        any protocol value."
    ::= { rsvpSessionEntry 1 }

rsvpSessionType OBJECT-TYPE
    SYNTAX SessionType
--    Rsyntax INTEGER(1..255)
    ACCESS read-only
    STATUS mandatory
    DESCRIPTION
        "The type of session (IP4, IP6, IP6 with  flow
        information, etc)."
    ::= { rsvpSessionEntry 2 }

rsvpSessionDestAddr OBJECT-TYPE
    SYNTAX OCTET STRING(SIZE(4..16))
    ACCESS read-only
    STATUS mandatory
    DESCRIPTION
        "The destination address used by all senders in
        this  session.   This object may not be changed
        when the  value  of the  RowStatus object is
        'active'."
    ::= { rsvpSessionEntry 3 }

rsvpSessionDestAddrLength OBJECT-TYPE
    SYNTAX INTEGER(0..128)
    ACCESS read-only
    STATUS mandatory
    DESCRIPTION
        "The CIDR prefix length of the session address,
        which   is 32  for  IP4  host  and  multicast
        addresses, and 128  for  IP6  addresses.   This
        object may not be changed when the value of the
        RowStatus object is 'active'."
    ::= { rsvpSessionEntry 4 }

rsvpSessionProtocol OBJECT-TYPE
    SYNTAX Protocol
--    Rsyntax INTEGER(1..255)
    ACCESS read-only
    STATUS mandatory
    DESCRIPTION
        "The IP Protocol used by  this  session.   This
        object may not be changed when the value of the
        RowStatus object is 'active'."
    ::= { rsvpSessionEntry 5 }

rsvpSessionPort OBJECT-TYPE
    SYNTAX Port
--    Rsyntax OCTET STRING(SIZE(2..4))
    ACCESS read-only
    STATUS mandatory
    DESCRIPTION
        "The  UDP  or  TCP  port  number  used   as  a
        destination  port  for  all  senders  in  this
        session.  If the IP protocol in use,  specified
        by  rsvpSenderProtocol, is 50 (ESP) or 51 (AH),
        this  represents  a virtual  destination  port
        number.   A value of zero indicates that the IP
        protocol in use  does  not  have  ports.   This
        object may not be changed when the value of the
        RowStatus object is 'active'."
    ::= { rsvpSessionEntry 6 }

rsvpSessionSenders OBJECT-TYPE
    SYNTAX Gauge
    ACCESS read-only
    STATUS mandatory
    DESCRIPTION
        "The number of distinct senders currently known
        to be part of this session."
    ::= { rsvpSessionEntry 7 }

rsvpSessionReceivers OBJECT-TYPE
    SYNTAX Gauge
    ACCESS read-only
    STATUS mandatory
    DESCRIPTION
        "The number of reservations being requested of
        this system for this session."
    ::= { rsvpSessionEntry 8 }

rsvpSessionRequests OBJECT-TYPE
    SYNTAX Gauge
    ACCESS read-only
    STATUS mandatory
    DESCRIPTION
        "The number of reservation requests this system
        is sending upstream for this session."
    ::= { rsvpSessionEntry 9 }

rsvpBadPackets OBJECT-TYPE
    SYNTAX Gauge
    ACCESS read-only
    STATUS mandatory
    DESCRIPTION
        "This object keeps a count of the number of bad
        RSVP packets received."
    ::= { rsvpGenObjects 1 }

rsvpSenderNewIndex OBJECT-TYPE
    SYNTAX TestAndIncr
--    Rsyntax INTEGER(0..2147483647)
    ACCESS read-write
    STATUS mandatory
    DESCRIPTION
        "This  object  is  used  to assign values to
        rsvpSenderNumber   as   described  in  'Textual
        Conventions for SNMPv2'.  The  network  manager
        reads  the  object, and  then writes the value
        back in the SET that creates a new instance of
        rsvpSenderEntry.   If  the  SET  fails with the
        code 'inconsistentValue', then the process must
        be  repeated;  If  the  SET succeeds, then the
        object is incremented, and the new instance is
        created according to the manager's directions."
    ::= { rsvpGenObjects 2 }

rsvpSenderTable OBJECT-TYPE
    SYNTAX SEQUENCE OF RsvpSenderEntry
    ACCESS not-accessible
    STATUS mandatory
    DESCRIPTION
        "Information describing the state  information
        displayed by senders in PATH messages."
    ::= { rsvpObjects 2 }

rsvpSenderEntry OBJECT-TYPE
    SYNTAX RsvpSenderEntry
    ACCESS not-accessible
    STATUS mandatory
    DESCRIPTION
        "Information describing the state  information
        displayed by a single sender's PATH message."
    INDEX { rsvpSessionNumber, rsvpSenderNumber }
    ::= { rsvpSenderTable 1 }

RsvpSenderEntry ::= SEQUENCE {
    rsvpSenderNumber SessionNumber,
    rsvpSenderType SessionType,
    rsvpSenderDestAddr OCTET STRING,
    rsvpSenderAddr OCTET STRING,
    rsvpSenderDestAddrLength INTEGER,
    rsvpSenderAddrLength INTEGER,
    rsvpSenderProtocol Protocol,
    rsvpSenderDestPort Port,
    rsvpSenderPort Port,
    rsvpSenderFlowId INTEGER,
    rsvpSenderHopAddr OCTET STRING,
    rsvpSenderHopLih INTEGER,
    rsvpSenderInterface InterfaceIndex,
    rsvpSenderTSpecRate BitRate,
    rsvpSenderTSpecPeakRate BitRate,
    rsvpSenderTSpecBurst BurstSize,
    rsvpSenderTSpecMinTU MessageSize,
    rsvpSenderTSpecMaxTU MessageSize,
    rsvpSenderInterval RefreshInterval,
    rsvpSenderRSVPHop TruthValue,
    rsvpSenderLastChange TimeStamp,
    rsvpSenderPolicy OCTET STRING,
    rsvpSenderAdspecBreak TruthValue,
    rsvpSenderAdspecHopCount INTEGER,
    rsvpSenderAdspecPathBw BitRate,
    rsvpSenderAdspecMinLatency INTEGER,
    rsvpSenderAdspecMtu INTEGER,
    rsvpSenderAdspecGuaranteedSvc TruthValue,
    rsvpSenderAdspecGuaranteedBreak TruthValue,
    rsvpSenderAdspecGuaranteedCtot INTEGER,
    rsvpSenderAdspecGuaranteedDtot INTEGER,
    rsvpSenderAdspecGuaranteedCsum INTEGER,
    rsvpSenderAdspecGuaranteedDsum INTEGER,
    rsvpSenderAdspecGuaranteedHopCount INTEGER,
    rsvpSenderAdspecGuaranteedPathBw BitRate,
    rsvpSenderAdspecGuaranteedMinLatency INTEGER,
    rsvpSenderAdspecGuaranteedMtu INTEGER,
    rsvpSenderAdspecCtrlLoadSvc TruthValue,
    rsvpSenderAdspecCtrlLoadBreak TruthValue,
    rsvpSenderAdspecCtrlLoadHopCount INTEGER,
    rsvpSenderAdspecCtrlLoadPathBw BitRate,
    rsvpSenderAdspecCtrlLoadMinLatency INTEGER,
    rsvpSenderAdspecCtrlLoadMtu INTEGER,
    rsvpSenderStatus RowStatus,
    rsvpSenderTTL INTEGER
    }

rsvpSenderNumber OBJECT-TYPE
    SYNTAX SessionNumber
--    Rsyntax INTEGER(0..2147483647)
    ACCESS not-accessible
    STATUS mandatory
    DESCRIPTION
        "The number of this sender. This is  for  SNMP
        Indexing  purposes  only and has no relation to
        any protocol value."
    ::= { rsvpSenderEntry 1 }

rsvpSenderType OBJECT-TYPE
    SYNTAX SessionType
--    Rsyntax INTEGER(1..255)
    ACCESS read-write
    STATUS mandatory
    DESCRIPTION
        "The type of session (IP4, IP6, IP6 with  flow
        information, etc)."
    ::= { rsvpSenderEntry 2 }

rsvpSenderDestAddr OBJECT-TYPE
    SYNTAX OCTET STRING(SIZE(4..16))
    ACCESS read-write
    STATUS mandatory
    DESCRIPTION
        "The destination address used by all senders in
        this  session.   This object may not be changed
        when the  value  of the  RowStatus object is
        'active'."
    ::= { rsvpSenderEntry 3 }

rsvpSenderAddr OBJECT-TYPE
    SYNTAX OCTET STRING(SIZE(4..16))
    ACCESS read-write
    STATUS mandatory
    DESCRIPTION
        "The source address used by this sender in this
        session.   This  object may not be changed when
        the value of the RowStatus object is 'active'."
    ::= { rsvpSenderEntry 4 }

rsvpSenderDestAddrLength OBJECT-TYPE
    SYNTAX INTEGER(0..128)
    ACCESS read-write
    STATUS mandatory
    DESCRIPTION
        "The length of the destination address in bits.
        This  is  the CIDR Prefix Length, which for IP4
        hosts and multicast addresses is 32 bits.  This
        object may not be changed when the value of the
        RowStatus object is 'active'."
    ::= { rsvpSenderEntry 5 }

rsvpSenderAddrLength OBJECT-TYPE
    SYNTAX INTEGER(0..128)
    ACCESS read-write
    STATUS mandatory
    DESCRIPTION
        "The length of the sender's address  in  bits.
        This  is  the CIDR Prefix Length, which for IP4
        hosts and multicast addresses is 32 bits.  This
        object may not be changed when the value of the
        RowStatus object is 'active'."
    ::= { rsvpSenderEntry 6 }

rsvpSenderProtocol OBJECT-TYPE
    SYNTAX Protocol
--    Rsyntax INTEGER(1..255)
    ACCESS read-write
    STATUS mandatory
    DESCRIPTION
        "The IP Protocol used by  this  session.   This
        object may not be changed when the value of the
        RowStatus object is 'active'."
    ::= { rsvpSenderEntry 7 }

rsvpSenderDestPort OBJECT-TYPE
    SYNTAX Port
--    Rsyntax OCTET STRING(SIZE(2..4))
    ACCESS read-write
    STATUS mandatory
    DESCRIPTION
        "The  UDP  or  TCP  port  number  used   as  a
        destination  port  for  all  senders  in  this
        session.  If the IP protocol in use,  specified
        by  rsvpSenderProtocol, is 50 (ESP) or 51 (AH),
        this  represents  a virtual  destination  port
        number.   A value of zero indicates that the IP
        protocol in use  does  not  have  ports.   This
        object may not be changed when the value of the
        RowStatus object is 'active'."
    ::= { rsvpSenderEntry 8 }

rsvpSenderPort OBJECT-TYPE
    SYNTAX Port
--    Rsyntax OCTET STRING(SIZE(2..4))
    ACCESS read-write
    STATUS mandatory
    DESCRIPTION
        "The UDP or TCP port number used  as  a  source
        port  for  this sender in this session.  If the
        IP  protocol    in    use,    specified by
        rsvpSenderProtocol is 50 (ESP) or 51 (AH), this
        represents a generalized port identifier (GPI).
        A  value of zero indicates that the IP protocol
        in use does not have ports.  This  object  may
        not be changed when the value of the RowStatus
        object is 'active'."
    ::= { rsvpSenderEntry 9 }

rsvpSenderFlowId OBJECT-TYPE
    SYNTAX INTEGER(0..16777215)
    ACCESS read-only
    STATUS mandatory
    DESCRIPTION
        "The flow ID that  this  sender  is using, if
        this  is  an IPv6 session."
    ::= { rsvpSenderEntry 10 }

rsvpSenderHopAddr OBJECT-TYPE
    SYNTAX OCTET STRING(SIZE(4..16))
    ACCESS read-write
    STATUS mandatory
    DESCRIPTION
        "The address used  by  the  previous  RSVP  hop
        (which may be the original sender)."
    ::= { rsvpSenderEntry 11 }

rsvpSenderHopLih OBJECT-TYPE
    SYNTAX INTEGER
    ACCESS read-write
    STATUS mandatory
    DESCRIPTION
        "The  Logical  Interface  Handle  used  by  the
        previous  RSVP  hop (which may be the original
        sender)."
    ::= { rsvpSenderEntry 12 }

rsvpSenderInterface OBJECT-TYPE
    SYNTAX InterfaceIndex
--    Rsyntax INTEGER(1..2147483647)
    ACCESS read-write
    STATUS mandatory
    DESCRIPTION
        "The ifIndex value of the  interface  on  which
        this PATH message was most recently received."
    ::= { rsvpSenderEntry 13 }

rsvpSenderTSpecRate OBJECT-TYPE
    SYNTAX BitRate
--    Rsyntax INTEGER(0..2147483647)
--  Units
--    bits per second
    ACCESS read-write
    STATUS mandatory
    DESCRIPTION
        "The Average Bit  Rate  of  the  sender's  data
        stream.    Within  a  transmission  burst,  the
        arrival   rate    may    be   as fast as
        rsvpSenderTSpecPeakRate  (if  supported  by the
        service model); however, averaged across two or
        more  burst intervals,  the  rate  should  not
        exceed rsvpSenderTSpecRate.
        
        Note that this is a prediction, often based on
        the general  capability  of a type of codec or
        particular encoding; the measured average  rate
        may be significantly lower."
    ::= { rsvpSenderEntry 14 }

rsvpSenderTSpecPeakRate OBJECT-TYPE
    SYNTAX BitRate
--    Rsyntax INTEGER(0..2147483647)
--  Units
--    bits per second
    ACCESS read-write
    STATUS mandatory
    DESCRIPTION
        "The Peak Bit Rate of the sender's data stream.
        Traffic  arrival is not expected to exceed this
        rate at any time, apart  from  the  effects of
        jitter in the network.  If not specified in the
        TSpec, this returns zero or noSuchValue."
    ::= { rsvpSenderEntry 15 }

rsvpSenderTSpecBurst OBJECT-TYPE
    SYNTAX BurstSize
--    Rsyntax INTEGER(0..2147483647)
--  Units
--    bytes
    ACCESS read-write
    STATUS mandatory
    DESCRIPTION
        "The size of the largest  burst  expected  from
        the sender at a time."
    ::= { rsvpSenderEntry 16 }

rsvpSenderTSpecMinTU OBJECT-TYPE
    SYNTAX MessageSize
--    Rsyntax INTEGER(0..2147483647)
    ACCESS read-write
    STATUS mandatory
    DESCRIPTION
        "The minimum message size for  this flow.  The
        policing  algorithm will treat smaller messages
        as though they are this size."
    ::= { rsvpSenderEntry 17 }

rsvpSenderTSpecMaxTU OBJECT-TYPE
    SYNTAX MessageSize
--    Rsyntax INTEGER(0..2147483647)
    ACCESS read-write
    STATUS mandatory
    DESCRIPTION
        "The maximum message size for  this flow.  The
        admission  algorithm  will  reject TSpecs whose
        Maximum Transmission Unit, plus  the  interface
        headers, exceed the interface MTU."
    ::= { rsvpSenderEntry 18 }

rsvpSenderInterval OBJECT-TYPE
    SYNTAX RefreshInterval
--    Rsyntax INTEGER(0..2147483647)
    ACCESS read-write
    STATUS mandatory
    DESCRIPTION
        "The  interval  between  refresh  messages as
        advertised by the Previous Hop."
    ::= { rsvpSenderEntry 19 }

rsvpSenderRSVPHop OBJECT-TYPE
    SYNTAX TruthValue
--    Rsyntax INTEGER {
--        true(1),
--        false(2)
--        }
    ACCESS read-write
    STATUS mandatory
    DESCRIPTION
        "If TRUE, the node believes that  the  previous
        IP  hop  is an  RSVP  hop. If FALSE, the node
        believes that the previous IP hop may not be an
        RSVP hop."
    ::= { rsvpSenderEntry 20 }

rsvpSenderLastChange OBJECT-TYPE
    SYNTAX TimeStamp
--    Rsyntax TimeTicks
    ACCESS read-only
    STATUS mandatory
    DESCRIPTION
        "The time of  the  last  change  in this  PATH
        message;  This  is either the first time it was
        received or the time of the most recent  change
        in parameters."
    ::= { rsvpSenderEntry 21 }

rsvpSenderPolicy OBJECT-TYPE
    SYNTAX OCTET STRING(SIZE(4..65536))
    ACCESS read-write
    STATUS mandatory
    DESCRIPTION
        "The contents of the policy object,  displayed
        as an uninterpreted string of octets, including
        the object header.  In the absence of  such an
        object, this should be of zero length."
    ::= { rsvpSenderEntry 22 }

rsvpSenderAdspecBreak OBJECT-TYPE
    SYNTAX TruthValue
--    Rsyntax INTEGER {
--        true(1),
--        false(2)
--        }
    ACCESS read-write
    STATUS mandatory
    DESCRIPTION
        "The global break bit general  characterization
        parameter  from  the ADSPEC.  If TRUE, at least
        one non-IS hop was detected in  the path. If
        FALSE, no non-IS hops were detected."
    ::= { rsvpSenderEntry 23 }

rsvpSenderAdspecHopCount OBJECT-TYPE
    SYNTAX INTEGER(0..65535)
    ACCESS read-write
    STATUS mandatory
    DESCRIPTION
        "The   hop count general   characterization
        parameter from the ADSPEC.  A return of zero or
        noSuchValue indicates  one of  the  following
        conditions:
        
           the invalid bit was set
           the parameter was not present"
    ::= { rsvpSenderEntry 24 }

rsvpSenderAdspecPathBw OBJECT-TYPE
    SYNTAX BitRate
--    Rsyntax INTEGER(0..2147483647)
--  Units
--    bits per second
    ACCESS read-write
    STATUS mandatory
    DESCRIPTION
        "The   path   bandwidth    estimate    general
        characterization  parameter from the ADSPEC.  A
        return of zero or noSuchValue indicates one of
        the following conditions:
        
           the invalid bit was set
           the parameter was not present"
    ::= { rsvpSenderEntry 25 }

rsvpSenderAdspecMinLatency OBJECT-TYPE
    SYNTAX INTEGER
--  Units
--    microseconds
    ACCESS read-write
    STATUS mandatory
    DESCRIPTION
        "The    minimum    path     latency    general
        characterization  parameter from the ADSPEC.  A
        return of zero or noSuchValue indicates one of
        the following conditions:
        
           the invalid bit was set
           the parameter was not present"
    ::= { rsvpSenderEntry 26 }

rsvpSenderAdspecMtu OBJECT-TYPE
    SYNTAX INTEGER(0..65535)
--  Units
--    bytes
    ACCESS read-write
    STATUS mandatory
    DESCRIPTION
        "The composed Maximum Transmission Unit general
        characterization  parameter from the ADSPEC.  A
        return of zero or noSuchValue indicates one of
        the following conditions:
        
           the invalid bit was set
           the parameter was not present"
    ::= { rsvpSenderEntry 27 }

rsvpSenderAdspecGuaranteedSvc OBJECT-TYPE
    SYNTAX TruthValue
--    Rsyntax INTEGER {
--        true(1),
--        false(2)
--        }
    ACCESS read-write
    STATUS mandatory
    DESCRIPTION
        "If TRUE,  the  ADSPEC  contains  a Guaranteed
        Service  fragment. If  FALSE, the ADSPEC does
        not contain a Guaranteed Service fragment."
    ::= { rsvpSenderEntry 28 }

rsvpSenderAdspecGuaranteedBreak OBJECT-TYPE
    SYNTAX TruthValue
--    Rsyntax INTEGER {
--        true(1),
--        false(2)
--        }
    ACCESS read-write
    STATUS mandatory
    DESCRIPTION
        "If TRUE, the Guaranteed Service  fragment  has
        its 'break'  bit  set,  indicating that one or
        more nodes along the path do  not  support  the
        guaranteed   service.     If    FALSE,    and
        rsvpSenderAdspecGuaranteedSvc  is   TRUE,   the
        'break' bit is not set.
        
        If rsvpSenderAdspecGuaranteedSvc is FALSE, this
        returns FALSE or noSuchValue."
    ::= { rsvpSenderEntry 29 }

rsvpSenderAdspecGuaranteedCtot OBJECT-TYPE
    SYNTAX INTEGER
--  Units
--    bytes
    ACCESS read-write
    STATUS mandatory
    DESCRIPTION
        "If rsvpSenderAdspecGuaranteedSvc is TRUE, this
        is the  end-to-end  composed  value  for  the
        guaranteed service 'C' parameter.  A return of
        zero   or  noSuchValue  indicates  one  of  the
        following conditions:
        
           the invalid bit was set
           the parameter was not present
        
        If rsvpSenderAdspecGuaranteedSvc is FALSE, this
        returns zero or noSuchValue."
    ::= { rsvpSenderEntry 30 }

rsvpSenderAdspecGuaranteedDtot OBJECT-TYPE
    SYNTAX INTEGER
--  Units
--    microseconds
    ACCESS read-write
    STATUS mandatory
    DESCRIPTION
        "If rsvpSenderAdspecGuaranteedSvc is TRUE, this
        is the  end-to-end  composed  value  for  the
        guaranteed service 'D' parameter.  A return of
        zero   or  noSuchValue  indicates  one  of  the
        following conditions:
        
           the invalid bit was set
           the parameter was not present
        
        If rsvpSenderAdspecGuaranteedSvc is FALSE, this
        returns zero or noSuchValue."
    ::= { rsvpSenderEntry 31 }

rsvpSenderAdspecGuaranteedCsum OBJECT-TYPE
    SYNTAX INTEGER
--  Units
--    bytes
    ACCESS read-write
    STATUS mandatory
    DESCRIPTION
        "If rsvpSenderAdspecGuaranteedSvc is TRUE, this
        is the  composed  value  for  the guaranteed
        service 'C' parameter since the last  reshaping
        point.    A  return  of  zero  or  noSuchValue
        indicates one of the following conditions:
        
           the invalid bit was set
           the parameter was not present
        
        If rsvpSenderAdspecGuaranteedSvc is FALSE, this
        returns zero or noSuchValue."
    ::= { rsvpSenderEntry 32 }

rsvpSenderAdspecGuaranteedDsum OBJECT-TYPE
    SYNTAX INTEGER
--  Units
--    microseconds
    ACCESS read-write
    STATUS mandatory
    DESCRIPTION
        "If rsvpSenderAdspecGuaranteedSvc is TRUE, this
        is the  composed  value  for  the guaranteed
        service 'D' parameter since the last  reshaping
        point.    A  return  of  zero  or  noSuchValue
        indicates one of the following conditions:
        
           the invalid bit was set
           the parameter was not present
        
        If rsvpSenderAdspecGuaranteedSvc is FALSE, this
        returns zero or noSuchValue."
    ::= { rsvpSenderEntry 33 }

rsvpSenderAdspecGuaranteedHopCount OBJECT-TYPE
    SYNTAX INTEGER(0..65535)
    ACCESS read-write
    STATUS mandatory
    DESCRIPTION
        "If rsvpSenderAdspecGuaranteedSvc is TRUE, this
        is  the  service-specific  override of the hop
        count general characterization  parameter  from
        the ADSPEC.   A  return of zero or noSuchValue
        indicates one of the following conditions:
        
           the invalid bit was set
           the parameter was not present
        
        If rsvpSenderAdspecGuaranteedSvc is FALSE, this
        returns zero or noSuchValue."
    ::= { rsvpSenderEntry 34 }

rsvpSenderAdspecGuaranteedPathBw OBJECT-TYPE
    SYNTAX BitRate
--    Rsyntax INTEGER(0..2147483647)
--  Units
--    bits per second
    ACCESS read-write
    STATUS mandatory
    DESCRIPTION
        "If rsvpSenderAdspecGuaranteedSvc is TRUE, this
        is  the  service-specific  override of the path
        bandwidth  estimate general   characterization
        parameter from the ADSPEC.  A return of zero or
        noSuchValue indicates  one of  the  following
        conditions:
        
           the invalid bit was set
           the parameter was not present
        
        If rsvpSenderAdspecGuaranteedSvc is FALSE, this
        returns zero or noSuchValue."
    ::= { rsvpSenderEntry 35 }

rsvpSenderAdspecGuaranteedMinLatency OBJECT-TYPE
    SYNTAX INTEGER
--  Units
--    microseconds
    ACCESS read-write
    STATUS mandatory
    DESCRIPTION
        "If rsvpSenderAdspecGuaranteedSvc is TRUE, this
        is the service-specific override of the minimum
        path latency general characterization parameter
        from   the ADSPEC.    A  return  of  zero or
        noSuchValue indicates  one of  the  following
        conditions:
        
           the invalid bit was set
           the parameter was not present
        
        If rsvpSenderAdspecGuaranteedSvc is FALSE, this
        returns zero or noSuchValue."
    ::= { rsvpSenderEntry 36 }

rsvpSenderAdspecGuaranteedMtu OBJECT-TYPE
    SYNTAX INTEGER(0..65535)
--  Units
--    bytes
    ACCESS read-write
    STATUS mandatory
    DESCRIPTION
        "If rsvpSenderAdspecGuaranteedSvc is TRUE, this
        is the   service-specific  override  of  the
        composed  Maximum  Transmission  Unit   general
        characterization  parameter from the ADSPEC.  A
        return of zero or noSuchValue indicates one of
        the following conditions:
        
           the invalid bit was set
           the parameter was not present
        
        If rsvpSenderAdspecGuaranteedSvc is FALSE, this
        returns zero or noSuchValue."
    ::= { rsvpSenderEntry 37 }

rsvpSenderAdspecCtrlLoadSvc OBJECT-TYPE
    SYNTAX TruthValue
--    Rsyntax INTEGER {
--        true(1),
--        false(2)
--        }
    ACCESS read-write
    STATUS mandatory
    DESCRIPTION
        "If TRUE, the ADSPEC contains a Controlled Load
        Service  fragment. If  FALSE, the ADSPEC does
        not  contain   a   Controlled   Load   Service
        fragment."
    ::= { rsvpSenderEntry 38 }

rsvpSenderAdspecCtrlLoadBreak OBJECT-TYPE
    SYNTAX TruthValue
--    Rsyntax INTEGER {
--        true(1),
--        false(2)
--        }
    ACCESS read-write
    STATUS mandatory
    DESCRIPTION
        "If TRUE, the Controlled Load Service  fragment
        has its 'break' bit set, indicating that one or
        more nodes along the path do  not  support  the
        controlled load   service.    If  FALSE,  and
        rsvpSenderAdspecCtrlLoadSvc  is   TRUE,    the
        'break' bit is not set.
        
        If rsvpSenderAdspecCtrlLoadSvc is  FALSE,  this
        returns FALSE or noSuchValue."
    ::= { rsvpSenderEntry 39 }

rsvpSenderAdspecCtrlLoadHopCount OBJECT-TYPE
    SYNTAX INTEGER(0..65535)
    ACCESS read-write
    STATUS mandatory
    DESCRIPTION
        "If rsvpSenderAdspecCtrlLoadSvc is  TRUE,  this
        is  the  service-specific  override of the hop
        count general characterization  parameter  from
        the ADSPEC.   A  return of zero or noSuchValue
        indicates one of the following conditions:
        
           the invalid bit was set
           the parameter was not present
        
        If rsvpSenderAdspecCtrlLoadSvc is  FALSE,  this
        returns zero or noSuchValue."
    ::= { rsvpSenderEntry 40 }

rsvpSenderAdspecCtrlLoadPathBw OBJECT-TYPE
    SYNTAX BitRate
--    Rsyntax INTEGER(0..2147483647)
--  Units
--    bits per second
    ACCESS read-write
    STATUS mandatory
    DESCRIPTION
        "If rsvpSenderAdspecCtrlLoadSvc is  TRUE,  this
        is  the  service-specific  override of the path
        bandwidth  estimate general   characterization
        parameter from the ADSPEC.  A return of zero or
        noSuchValue indicates  one of  the  following
        conditions:
        
           the invalid bit was set
           the parameter was not present
        
        If rsvpSenderAdspecCtrlLoadSvc is  FALSE,  this
        returns zero or noSuchValue."
    ::= { rsvpSenderEntry 41 }

rsvpSenderAdspecCtrlLoadMinLatency OBJECT-TYPE
    SYNTAX INTEGER
--  Units
--    microseconds
    ACCESS read-write
    STATUS mandatory
    DESCRIPTION
        "If rsvpSenderAdspecCtrlLoadSvc is  TRUE,  this
        is the service-specific override of the minimum
        path latency general characterization parameter
        from   the ADSPEC.    A  return  of  zero or
        noSuchValue indicates  one of  the  following
        conditions:
        
           the invalid bit was set
           the parameter was not present
        
        If rsvpSenderAdspecCtrlLoadSvc is  FALSE,  this
        returns zero or noSuchValue."
    ::= { rsvpSenderEntry 42 }

rsvpSenderAdspecCtrlLoadMtu OBJECT-TYPE
    SYNTAX INTEGER(0..65535)
--  Units
--    bytes
    ACCESS read-write
    STATUS mandatory
    DESCRIPTION
        "If rsvpSenderAdspecCtrlLoadSvc is  TRUE,  this
        is the   service-specific  override  of  the
        composed  Maximum  Transmission  Unit   general
        characterization  parameter from the ADSPEC.  A
        return of zero or noSuchValue indicates one of
        the following conditions:
        
           the invalid bit was set
           the parameter was not present
        
        If rsvpSenderAdspecCtrlLoadSvc is  FALSE,  this
        returns zero or noSuchValue."
    ::= { rsvpSenderEntry 43 }

rsvpSenderStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' for all active PATH  messages.   This
        object  may be  used  to  install  static PATH
        information or delete PATH information."
    ::= { rsvpSenderEntry 44 }

rsvpSenderTTL OBJECT-TYPE
    SYNTAX INTEGER(0..255)
    ACCESS read-only
    STATUS mandatory
    DESCRIPTION
        "The TTL value in the RSVP header that was last
        received."
    ::= { rsvpSenderEntry 45 }

rsvpSenderOutInterfaceTable OBJECT-TYPE
    SYNTAX SEQUENCE OF RsvpSenderOutInterfaceEntry
    ACCESS not-accessible
    STATUS mandatory
    DESCRIPTION
        "List of outgoing interfaces that PATH messages
        use.  The  ifIndex  is the ifIndex value of the
        egress interface."
    ::= { rsvpObjects 3 }

rsvpSenderOutInterfaceEntry OBJECT-TYPE
    SYNTAX RsvpSenderOutInterfaceEntry
    ACCESS not-accessible
    STATUS mandatory
    DESCRIPTION
        "List of outgoing interfaces that a particular
        PATH message has."
    INDEX { rsvpSessionNumber, rsvpSenderNumber, ifIndex }
    ::= { rsvpSenderOutInterfaceTable 1 }

RsvpSenderOutInterfaceEntry ::= SEQUENCE {
    rsvpSenderOutInterfaceStatus RowStatus
    }

rsvpSenderOutInterfaceStatus OBJECT-TYPE
    SYNTAX RowStatus
--    Rsyntax INTEGER {
--        active(1),
--        notInService(2),
--        notReady(3),
--        createAndGo(4),
--        createAndWait(5),
--        destroy(6)
--        }
    ACCESS read-only
    STATUS mandatory
    DESCRIPTION
        "'active' for all active PATH messages."
    ::= { rsvpSenderOutInterfaceEntry 1 }

rsvpResvNewIndex OBJECT-TYPE
    SYNTAX TestAndIncr
--    Rsyntax INTEGER(0..2147483647)
    ACCESS read-write
    STATUS mandatory
    DESCRIPTION
        "This  object  is  used  to assign values to
        rsvpResvNumber   as  described   in   'Textual
        Conventions for SNMPv2'.  The  network  manager
        reads  the  object, and  then writes the value
        back in the SET that creates a new instance of
        rsvpResvEntry.   If the SET fails with the code
        'inconsistentValue', then the process  must be
        repeated;  If the SET succeeds, then the object
        is incremented, and the new instance is created
        according to the manager's directions."
    ::= { rsvpGenObjects 3 }

rsvpResvTable OBJECT-TYPE
    SYNTAX SEQUENCE OF RsvpResvEntry
    ACCESS not-accessible
    STATUS mandatory
    DESCRIPTION
        "Information describing the state  information
        displayed by receivers in RESV messages."
    ::= { rsvpObjects 4 }

rsvpResvEntry OBJECT-TYPE
    SYNTAX RsvpResvEntry
    ACCESS not-accessible
    STATUS mandatory
    DESCRIPTION
        "Information describing the state  information
        displayed  by  a single receiver's RESV message
        concerning a single sender."
    INDEX { rsvpSessionNumber, rsvpResvNumber }
    ::= { rsvpResvTable 1 }

RsvpResvEntry ::= SEQUENCE {
    rsvpResvNumber SessionNumber,
    rsvpResvType SessionType,
    rsvpResvDestAddr OCTET STRING,
    rsvpResvSenderAddr OCTET STRING,
    rsvpResvDestAddrLength INTEGER,
    rsvpResvSenderAddrLength INTEGER,
    rsvpResvProtocol Protocol,
    rsvpResvDestPort Port,
    rsvpResvPort Port,
    rsvpResvHopAddr OCTET STRING,
    rsvpResvHopLih INTEGER,
    rsvpResvInterface InterfaceIndex,
    rsvpResvService QosService,
    rsvpResvTSpecRate BitRate,
    rsvpResvTSpecPeakRate BitRate,
    rsvpResvTSpecBurst BurstSize,
    rsvpResvTSpecMinTU MessageSize,
    rsvpResvTSpecMaxTU MessageSize,
    rsvpResvRSpecRate BitRate,
    rsvpResvRSpecSlack INTEGER,
    rsvpResvInterval RefreshInterval,
    rsvpResvScope OCTET STRING,
    rsvpResvShared TruthValue,
    rsvpResvExplicit TruthValue,
    rsvpResvRSVPHop TruthValue,
    rsvpResvLastChange TimeStamp,
    rsvpResvPolicy OCTET STRING,
    rsvpResvStatus RowStatus,
    rsvpResvTTL INTEGER,
    rsvpResvFlowId INTEGER
    }

rsvpResvNumber OBJECT-TYPE
    SYNTAX SessionNumber
--    Rsyntax INTEGER(0..2147483647)
    ACCESS not-accessible
    STATUS mandatory
    DESCRIPTION
        "The number of this reservation request.   This
        is  for  SNMP Indexing purposes only and has no
        relation to any protocol value."
    ::= { rsvpResvEntry 1 }

rsvpResvType OBJECT-TYPE
    SYNTAX SessionType
--    Rsyntax INTEGER(1..255)
    ACCESS read-write
    STATUS mandatory
    DESCRIPTION
        "The type of session (IP4, IP6, IP6 with  flow
        information, etc)."
    ::= { rsvpResvEntry 2 }

rsvpResvDestAddr OBJECT-TYPE
    SYNTAX OCTET STRING(SIZE(4..16))
    ACCESS read-write
    STATUS mandatory
    DESCRIPTION
        "The destination address used by all senders in
        this  session.   This object may not be changed
        when the  value  of the  RowStatus object is
        'active'."
    ::= { rsvpResvEntry 3 }

rsvpResvSenderAddr OBJECT-TYPE
    SYNTAX OCTET STRING(SIZE(4..16))
    ACCESS read-write
    STATUS mandatory
    DESCRIPTION
        "The source address of the sender  selected by
        this  reservation. The  value  of all zeroes
        indicates 'all senders'.  This object  may  not
        be  changed when  the  value  of the RowStatus
        object is 'active'."
    ::= { rsvpResvEntry 4 }

rsvpResvDestAddrLength OBJECT-TYPE
    SYNTAX INTEGER(0..128)
    ACCESS read-write
    STATUS mandatory
    DESCRIPTION
        "The length of the destination address in bits.
        This  is  the CIDR Prefix Length, which for IP4
        hosts and multicast addresses is 32 bits.  This
        object may not be changed when the value of the
        RowStatus object is 'active'."
    ::= { rsvpResvEntry 5 }

rsvpResvSenderAddrLength OBJECT-TYPE
    SYNTAX INTEGER(0..128)
    ACCESS read-write
    STATUS mandatory
    DESCRIPTION
        "The length of the sender's address  in  bits.
        This  is  the CIDR Prefix Length, which for IP4
        hosts and multicast addresses is 32 bits.  This
        object may not be changed when the value of the
        RowStatus object is 'active'."
    ::= { rsvpResvEntry 6 }

rsvpResvProtocol OBJECT-TYPE
    SYNTAX Protocol
--    Rsyntax INTEGER(1..255)
    ACCESS read-write
    STATUS mandatory
    DESCRIPTION
        "The IP Protocol used by  this  session.   This
        object may not be changed when the value of the
        RowStatus object is 'active'."
    ::= { rsvpResvEntry 7 }

rsvpResvDestPort OBJECT-TYPE
    SYNTAX Port
--    Rsyntax OCTET STRING(SIZE(2..4))
    ACCESS read-write
    STATUS mandatory
    DESCRIPTION
        "The  UDP  or  TCP  port  number  used   as  a
        destination  port  for  all  senders  in  this
        session.  If the IP protocol in use,  specified
        by  rsvpResvProtocol,  is  50 (ESP) or 51 (AH),
        this  represents  a virtual  destination  port
        number.   A value of zero indicates that the IP
        protocol in use  does  not  have  ports.   This
        object may not be changed when the value of the
        RowStatus object is 'active'."
    ::= { rsvpResvEntry 8 }

rsvpResvPort OBJECT-TYPE
    SYNTAX Port
--    Rsyntax OCTET STRING(SIZE(2..4))
    ACCESS read-write
    STATUS mandatory
    DESCRIPTION
        "The UDP or TCP port number used  as  a  source
        port  for  this sender in this session.  If the
        IP  protocol    in    use,    specified by
        rsvpResvProtocol  is  50 (ESP) or 51 (AH), this
        represents a generalized port identifier (GPI).
        A  value of zero indicates that the IP protocol
        in use does not have ports.  This  object  may
        not be changed when the value of the RowStatus
        object is 'active'."
    ::= { rsvpResvEntry 9 }

rsvpResvHopAddr OBJECT-TYPE
    SYNTAX OCTET STRING(SIZE(4..16))
    ACCESS read-write
    STATUS mandatory
    DESCRIPTION
        "The address used by the next RSVP  hop  (which
        may be the ultimate receiver)."
    ::= { rsvpResvEntry 10 }

rsvpResvHopLih OBJECT-TYPE
    SYNTAX INTEGER
    ACCESS read-write
    STATUS mandatory
    DESCRIPTION
        "The Logical Interface Handle received from the
        previous  RSVP  hop (which may be the ultimate
        receiver)."
    ::= { rsvpResvEntry 11 }

rsvpResvInterface OBJECT-TYPE
    SYNTAX InterfaceIndex
--    Rsyntax INTEGER(1..2147483647)
    ACCESS read-write
    STATUS mandatory
    DESCRIPTION
        "The ifIndex value of the  interface  on  which
        this RESV message was most recently received."
    ::= { rsvpResvEntry 12 }

rsvpResvService OBJECT-TYPE
    SYNTAX QosService
--    Rsyntax INTEGER {
--        bestEffort(1),
--        guaranteedDelay(2),
--        controlledLoad(5)
--        }
    ACCESS read-write
    STATUS mandatory
    DESCRIPTION
        "The QoS Service  classification  requested by
        the receiver."
    ::= { rsvpResvEntry 13 }

rsvpResvTSpecRate OBJECT-TYPE
    SYNTAX BitRate
--    Rsyntax INTEGER(0..2147483647)
--  Units
--    bits per second
    ACCESS read-write
    STATUS mandatory
    DESCRIPTION
        "The Average Bit  Rate  of  the  sender's  data
        stream.    Within  a  transmission  burst,  the
        arrival   rate    may    be   as fast as
        rsvpResvTSpecPeakRate   (if supported  by  the
        service model); however, averaged across two or
        more  burst intervals,  the  rate  should  not
        exceed rsvpResvTSpecRate.
        
        Note that this is a prediction, often based on
        the general  capability  of a type of codec or
        particular encoding; the measured average  rate
        may be significantly lower."
    ::= { rsvpResvEntry 14 }

rsvpResvTSpecPeakRate OBJECT-TYPE
    SYNTAX BitRate
--    Rsyntax INTEGER(0..2147483647)
--  Units
--    bits per second
    ACCESS read-write
    STATUS mandatory
    DESCRIPTION
        "The Peak Bit Rate of the sender's data stream.
        Traffic  arrival is not expected to exceed this
        rate at any time, apart  from  the  effects of
        jitter in the network.  If not specified in the
        TSpec, this returns zero or noSuchValue."
    ::= { rsvpResvEntry 15 }

rsvpResvTSpecBurst OBJECT-TYPE
    SYNTAX BurstSize
--    Rsyntax INTEGER(0..2147483647)
--  Units
--    bytes
    ACCESS read-write
    STATUS mandatory
    DESCRIPTION
        "The size of the largest  burst  expected  from
        the sender at a time.
        
        If this is less than  the  sender's advertised
        burst  size, the receiver is asking the network
        to provide flow pacing  beyond  what  would be
        provided   under   normal  circumstances.  Such
        pacing is at the network's option."
    ::= { rsvpResvEntry 16 }

rsvpResvTSpecMinTU OBJECT-TYPE
    SYNTAX MessageSize
--    Rsyntax INTEGER(0..2147483647)
    ACCESS read-write
    STATUS mandatory
    DESCRIPTION
        "The minimum message size for  this flow.  The
        policing  algorithm will treat smaller messages
        as though they are this size."
    ::= { rsvpResvEntry 17 }

rsvpResvTSpecMaxTU OBJECT-TYPE
    SYNTAX MessageSize
--    Rsyntax INTEGER(0..2147483647)
    ACCESS read-write
    STATUS mandatory
    DESCRIPTION
        "The maximum message size for  this flow.  The
        admission  algorithm  will  reject TSpecs whose
        Maximum Transmission Unit, plus  the  interface
        headers, exceed the interface MTU."
    ::= { rsvpResvEntry 18 }

rsvpResvRSpecRate OBJECT-TYPE
    SYNTAX BitRate
--    Rsyntax INTEGER(0..2147483647)
--  Units
--    bits per second
    ACCESS read-write
    STATUS mandatory
    DESCRIPTION
        "If the requested  service  is  Guaranteed, as
        specified   by  rsvpResvService,  this  is  the
        clearing  rate   that   is being requested.
        Otherwise,  it is zero, or the agent may return
        noSuchValue."
    ::= { rsvpResvEntry 19 }

rsvpResvRSpecSlack OBJECT-TYPE
    SYNTAX INTEGER
--  Units
--    microseconds
    ACCESS read-write
    STATUS mandatory
    DESCRIPTION
        "If the requested  service  is  Guaranteed, as
        specified by rsvpResvService, this is the delay
        slack.  Otherwise, it is zero, or the agent may
        return noSuchValue."
    ::= { rsvpResvEntry 20 }

rsvpResvInterval OBJECT-TYPE
    SYNTAX RefreshInterval
--    Rsyntax INTEGER(0..2147483647)
    ACCESS read-write
    STATUS mandatory
    DESCRIPTION
        "The  interval  between  refresh  messages as
        advertised by the Next Hop."
    ::= { rsvpResvEntry 21 }

rsvpResvScope OBJECT-TYPE
    SYNTAX OCTET STRING(SIZE(0..65536))
    ACCESS read-write
    STATUS mandatory
    DESCRIPTION
        "The contents of the scope object, displayed as
        an  uninterpreted  string  of octets, including
        the object header.  In the absence of  such an
        object, this should be of zero length.
        
        If the length  is  non-zero,  this  contains  a
        series of IP4 or IP6 addresses."
    ::= { rsvpResvEntry 22 }

rsvpResvShared OBJECT-TYPE
    SYNTAX TruthValue
--    Rsyntax INTEGER {
--        true(1),
--        false(2)
--        }
    ACCESS read-write
    STATUS mandatory
    DESCRIPTION
        "If TRUE, a reservation shared among senders is
        requested.  If FALSE, a reservation specific to
        this sender is requested."
    ::= { rsvpResvEntry 23 }

rsvpResvExplicit OBJECT-TYPE
    SYNTAX TruthValue
--    Rsyntax INTEGER {
--        true(1),
--        false(2)
--        }
    ACCESS read-write
    STATUS mandatory
    DESCRIPTION
        "If TRUE, individual senders are  listed  using
        Filter  Specifications.   If FALSE, all senders
        are implicitly selected.  The Scope Object will
        contain  a list of senders that need to receive
        this reservation request  for  the  purpose of
        routing the RESV message."
    ::= { rsvpResvEntry 24 }

rsvpResvRSVPHop OBJECT-TYPE
    SYNTAX TruthValue
--    Rsyntax INTEGER {
--        true(1),
--        false(2)
--        }
    ACCESS read-write
    STATUS mandatory
    DESCRIPTION
        "If TRUE, the node believes that  the  previous
        IP  hop  is an  RSVP  hop. If FALSE, the node
        believes that the previous IP hop may not be an
        RSVP hop."
    ::= { rsvpResvEntry 25 }

rsvpResvLastChange OBJECT-TYPE
    SYNTAX TimeStamp
--    Rsyntax TimeTicks
    ACCESS read-only
    STATUS mandatory
    DESCRIPTION
        "The  time  of  the  last change  in   this
        reservation request;  This is either the first
        time it was received or the time  of  the  most
        recent change in parameters."
    ::= { rsvpResvEntry 26 }

rsvpResvPolicy OBJECT-TYPE
    SYNTAX OCTET STRING(SIZE(0..65536))
    ACCESS read-write
    STATUS mandatory
    DESCRIPTION
        "The contents of the policy object,  displayed
        as an uninterpreted string of octets, including
        the object header.  In the absence of  such an
        object, this should be of zero length."
    ::= { rsvpResvEntry 27 }

rsvpResvStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' for all active RESV  messages.   This
        object  may be  used  to  install  static RESV
        information or delete RESV information."
    ::= { rsvpResvEntry 28 }

rsvpResvTTL OBJECT-TYPE
    SYNTAX INTEGER(0..255)
    ACCESS read-only
    STATUS mandatory
    DESCRIPTION
        "The TTL value in the RSVP header that was last
        received."
    ::= { rsvpResvEntry 29 }

rsvpResvFlowId OBJECT-TYPE
    SYNTAX INTEGER(0..16777215)
    ACCESS read-only
    STATUS mandatory
    DESCRIPTION
        "The flow ID that this receiver  is using, if
        this  is  an IPv6 session."
    ::= { rsvpResvEntry 30 }

rsvpResvFwdNewIndex OBJECT-TYPE
    SYNTAX TestAndIncr
--    Rsyntax INTEGER(0..2147483647)
    ACCESS read-write
    STATUS mandatory
    DESCRIPTION
        "This  object  is  used  to assign values to
        rsvpResvFwdNumber   as  described  in  'Textual
        Conventions for SNMPv2'.  The  network  manager
        reads  the  object, and  then writes the value
        back in the SET that creates a new instance of
        rsvpResvFwdEntry.   If  the SET fails with the
        code 'inconsistentValue', then the process must
        be  repeated;  If  the  SET succeeds, then the
        object is incremented, and the new instance is
        created according to the manager's directions."
    ::= { rsvpGenObjects 4 }

rsvpResvFwdTable OBJECT-TYPE
    SYNTAX SEQUENCE OF RsvpResvFwdEntry
    ACCESS not-accessible
    STATUS mandatory
    DESCRIPTION
        "Information describing the state  information
        displayed upstream in RESV messages."
    ::= { rsvpObjects 5 }

rsvpResvFwdEntry OBJECT-TYPE
    SYNTAX RsvpResvFwdEntry
    ACCESS not-accessible
    STATUS mandatory
    DESCRIPTION
        "Information describing the state  information
        displayed   upstream   in   an   RESV   message
        concerning a single sender."
    INDEX { rsvpSessionNumber, rsvpResvFwdNumber }
    ::= { rsvpResvFwdTable 1 }

RsvpResvFwdEntry ::= SEQUENCE {
    rsvpResvFwdNumber SessionNumber,
    rsvpResvFwdType SessionType,
    rsvpResvFwdDestAddr OCTET STRING,
    rsvpResvFwdSenderAddr OCTET STRING,
    rsvpResvFwdDestAddrLength INTEGER,
    rsvpResvFwdSenderAddrLength INTEGER,
    rsvpResvFwdProtocol Protocol,
    rsvpResvFwdDestPort Port,
    rsvpResvFwdPort Port,
    rsvpResvFwdHopAddr OCTET STRING,
    rsvpResvFwdHopLih INTEGER,
    rsvpResvFwdInterface InterfaceIndex,
    rsvpResvFwdService QosService,
    rsvpResvFwdTSpecRate BitRate,
    rsvpResvFwdTSpecPeakRate BitRate,
    rsvpResvFwdTSpecBurst BurstSize,
    rsvpResvFwdTSpecMinTU MessageSize,
    rsvpResvFwdTSpecMaxTU MessageSize,
    rsvpResvFwdRSpecRate BitRate,
    rsvpResvFwdRSpecSlack INTEGER,
    rsvpResvFwdInterval RefreshInterval,
    rsvpResvFwdScope OCTET STRING,
    rsvpResvFwdShared TruthValue,
    rsvpResvFwdExplicit TruthValue,
    rsvpResvFwdRSVPHop TruthValue,
    rsvpResvFwdLastChange TimeStamp,
    rsvpResvFwdPolicy OCTET STRING,
    rsvpResvFwdStatus RowStatus,
    rsvpResvFwdTTL INTEGER,
    rsvpResvFwdFlowId INTEGER
    }

rsvpResvFwdNumber OBJECT-TYPE
    SYNTAX SessionNumber
--    Rsyntax INTEGER(0..2147483647)
    ACCESS not-accessible
    STATUS mandatory
    DESCRIPTION
        "The number of this reservation request.   This
        is  for  SNMP Indexing purposes only and has no
        relation to any protocol value."
    ::= { rsvpResvFwdEntry 1 }

rsvpResvFwdType OBJECT-TYPE
    SYNTAX SessionType
--    Rsyntax INTEGER(1..255)
    ACCESS read-only
    STATUS mandatory
    DESCRIPTION
        "The type of session (IP4, IP6, IP6 with  flow
        information, etc)."
    ::= { rsvpResvFwdEntry 2 }

rsvpResvFwdDestAddr OBJECT-TYPE
    SYNTAX OCTET STRING(SIZE(4..16))
    ACCESS read-only
    STATUS mandatory
    DESCRIPTION
        "The destination address used by all senders in
        this  session.   This object may not be changed
        when the  value  of the  RowStatus object is
        'active'."
    ::= { rsvpResvFwdEntry 3 }

rsvpResvFwdSenderAddr OBJECT-TYPE
    SYNTAX OCTET STRING(SIZE(4..16))
    ACCESS read-only
    STATUS mandatory
    DESCRIPTION
        "The source address of the sender  selected by
        this  reservation. The  value  of all zeroes
        indicates 'all senders'.  This object  may  not
        be  changed when  the  value  of the RowStatus
        object is 'active'."
    ::= { rsvpResvFwdEntry 4 }

rsvpResvFwdDestAddrLength OBJECT-TYPE
    SYNTAX INTEGER(0..128)
    ACCESS read-only
    STATUS mandatory
    DESCRIPTION
        "The length of the destination address in bits.
        This  is  the CIDR Prefix Length, which for IP4
        hosts and multicast addresses is 32 bits.  This
        object may not be changed when the value of the
        RowStatus object is 'active'."
    ::= { rsvpResvFwdEntry 5 }

rsvpResvFwdSenderAddrLength OBJECT-TYPE
    SYNTAX INTEGER(0..128)
    ACCESS read-only
    STATUS mandatory
    DESCRIPTION
        "The length of the sender's address  in  bits.
        This  is  the CIDR Prefix Length, which for IP4
        hosts and multicast addresses is 32 bits.  This
        object may not be changed when the value of the
        RowStatus object is 'active'."
    ::= { rsvpResvFwdEntry 6 }

rsvpResvFwdProtocol OBJECT-TYPE
    SYNTAX Protocol
--    Rsyntax INTEGER(1..255)
    ACCESS read-only
    STATUS mandatory
    DESCRIPTION
        "The IP Protocol used by a session. for  secure
        sessions,  this  indicates  IP  Security.  This
        object may not be changed when the value of the
        RowStatus object is 'active'."
    ::= { rsvpResvFwdEntry 7 }

rsvpResvFwdDestPort OBJECT-TYPE
    SYNTAX Port
--    Rsyntax OCTET STRING(SIZE(2..4))
    ACCESS read-only
    STATUS mandatory
    DESCRIPTION
        "The  UDP  or  TCP  port  number  used   as  a
        destination  port  for  all  senders  in  this
        session.  If the IP protocol in use,  specified
        by rsvpResvFwdProtocol, is 50 (ESP) or 51 (AH),
        this  represents  a virtual  destination  port
        number.   A value of zero indicates that the IP
        protocol in use  does  not  have  ports.   This
        object may not be changed when the value of the
        RowStatus object is 'active'."
    ::= { rsvpResvFwdEntry 8 }

rsvpResvFwdPort OBJECT-TYPE
    SYNTAX Port
--    Rsyntax OCTET STRING(SIZE(2..4))
    ACCESS read-only
    STATUS mandatory
    DESCRIPTION
        "The UDP or TCP port number used  as  a  source
        port  for  this sender in this session.  If the
        IP  protocol    in    use,    specified by
        rsvpResvFwdProtocol is  50 (ESP)  or 51 (AH),
        this represents a generalized  port identifier
        (GPI).   A  value of zero indicates that the IP
        protocol in use  does  not  have  ports.   This
        object may not be changed when the value of the
        RowStatus object is 'active'."
    ::= { rsvpResvFwdEntry 9 }

rsvpResvFwdHopAddr OBJECT-TYPE
    SYNTAX OCTET STRING(SIZE(4..16))
    ACCESS read-only
    STATUS mandatory
    DESCRIPTION
        "The address of the (previous) RSVP that  will
        receive this message."
    ::= { rsvpResvFwdEntry 10 }

rsvpResvFwdHopLih OBJECT-TYPE
    SYNTAX INTEGER
    ACCESS read-only
    STATUS mandatory
    DESCRIPTION
        "The  Logical  Interface  Handle  sent  to  the
        (previous) RSVP   that   will   receive  this
        message."
    ::= { rsvpResvFwdEntry 11 }

rsvpResvFwdInterface OBJECT-TYPE
    SYNTAX InterfaceIndex
--    Rsyntax INTEGER(1..2147483647)
    ACCESS read-only
    STATUS mandatory
    DESCRIPTION
        "The ifIndex value of the  interface  on  which
        this RESV message was most recently sent."
    ::= { rsvpResvFwdEntry 12 }

rsvpResvFwdService OBJECT-TYPE
    SYNTAX QosService
--    Rsyntax INTEGER {
--        bestEffort(1),
--        guaranteedDelay(2),
--        controlledLoad(5)
--        }
    ACCESS read-only
    STATUS mandatory
    DESCRIPTION
        "The QoS Service classification requested."
    ::= { rsvpResvFwdEntry 13 }

rsvpResvFwdTSpecRate OBJECT-TYPE
    SYNTAX BitRate
--    Rsyntax INTEGER(0..2147483647)
--  Units
--    bits per second
    ACCESS read-only
    STATUS mandatory
    DESCRIPTION
        "The Average Bit  Rate  of  the  sender's  data
        stream.    Within  a  transmission  burst,  the
        arrival   rate    may    be   as fast as
        rsvpResvFwdTSpecPeakRate  (if  supported by the
        service model); however, averaged across two or
        more  burst intervals,  the  rate  should  not
        exceed rsvpResvFwdTSpecRate.
        
        Note that this is a prediction, often based on
        the general  capability  of a type of codec or
        particular encoding; the measured average  rate
        may be significantly lower."
    ::= { rsvpResvFwdEntry 14 }

rsvpResvFwdTSpecPeakRate OBJECT-TYPE
    SYNTAX BitRate
--    Rsyntax INTEGER(0..2147483647)
--  Units
--    bits per second
    ACCESS read-only
    STATUS mandatory
    DESCRIPTION
        "The Peak Bit Rate of the sender's data  stream
        Traffic  arrival is not expected to exceed this
        rate at any time, apart  from  the  effects of
        jitter in the network.  If not specified in the
        TSpec, this returns zero or noSuchValue."
    ::= { rsvpResvFwdEntry 15 }

rsvpResvFwdTSpecBurst OBJECT-TYPE
    SYNTAX BurstSize
--    Rsyntax INTEGER(0..2147483647)
--  Units
--    bytes
    ACCESS read-only
    STATUS mandatory
    DESCRIPTION
        "The size of the largest  burst  expected  from
        the sender at a time.
        
        If this is less than  the  sender's advertised
        burst  size, the receiver is asking the network
        to provide flow pacing  beyond  what  would be
        provided   under   normal  circumstances.  Such
        pacing is at the network's option."
    ::= { rsvpResvFwdEntry 16 }

rsvpResvFwdTSpecMinTU OBJECT-TYPE
    SYNTAX MessageSize
--    Rsyntax INTEGER(0..2147483647)
    ACCESS read-only
    STATUS mandatory
    DESCRIPTION
        "The minimum message size for  this flow.  The
        policing  algorithm will treat smaller messages
        as though they are this size."
    ::= { rsvpResvFwdEntry 17 }

rsvpResvFwdTSpecMaxTU OBJECT-TYPE
    SYNTAX MessageSize
--    Rsyntax INTEGER(0..2147483647)
    ACCESS read-only
    STATUS mandatory
    DESCRIPTION
        "The maximum message size for  this flow.  The
        admission  algorithm  will  reject TSpecs whose
        Maximum Transmission Unit, plus  the  interface
        headers, exceed the interface MTU."
    ::= { rsvpResvFwdEntry 18 }

rsvpResvFwdRSpecRate OBJECT-TYPE
    SYNTAX BitRate
--    Rsyntax INTEGER(0..2147483647)
--  Units
--    bytes per second
    ACCESS read-only
    STATUS mandatory
    DESCRIPTION
        "If the requested  service  is  Guaranteed, as
        specified   by  rsvpResvService,  this  is  the
        clearing  rate   that   is being requested.
        Otherwise,  it is zero, or the agent may return
        noSuchValue."
    ::= { rsvpResvFwdEntry 19 }

rsvpResvFwdRSpecSlack OBJECT-TYPE
    SYNTAX INTEGER
--  Units
--    microseconds
    ACCESS read-only
    STATUS mandatory
    DESCRIPTION
        "If the requested  service  is  Guaranteed, as
        specified by rsvpResvService, this is the delay
        slack.  Otherwise, it is zero, or the agent may
        return noSuchValue."
    ::= { rsvpResvFwdEntry 20 }

rsvpResvFwdInterval OBJECT-TYPE
    SYNTAX RefreshInterval
--    Rsyntax INTEGER(0..2147483647)
    ACCESS read-only
    STATUS mandatory
    DESCRIPTION
        "The   interval   between   refresh   messages
        advertised to the Previous Hop."
    ::= { rsvpResvFwdEntry 21 }

rsvpResvFwdScope OBJECT-TYPE
    SYNTAX OCTET STRING(SIZE(0..65536))
    ACCESS read-only
    STATUS mandatory
    DESCRIPTION
        "The contents of the scope object, displayed as
        an  uninterpreted  string  of octets, including
        the object header.  In the absence of  such an
        object, this should be of zero length."
    ::= { rsvpResvFwdEntry 22 }

rsvpResvFwdShared OBJECT-TYPE
    SYNTAX TruthValue
--    Rsyntax INTEGER {
--        true(1),
--        false(2)
--        }
    ACCESS read-only
    STATUS mandatory
    DESCRIPTION
        "If TRUE, a reservation shared among senders is
        requested.  If FALSE, a reservation specific to
        this sender is requested."
    ::= { rsvpResvFwdEntry 23 }

rsvpResvFwdExplicit OBJECT-TYPE
    SYNTAX TruthValue
--    Rsyntax INTEGER {
--        true(1),
--        false(2)
--        }
    ACCESS read-only
    STATUS mandatory
    DESCRIPTION
        "If TRUE, individual senders are  listed  using
        Filter  Specifications.   If FALSE, all senders
        are implicitly selected.  The Scope Object will
        contain  a list of senders that need to receive
        this reservation request  for  the  purpose of
        routing the RESV message."
    ::= { rsvpResvFwdEntry 24 }

rsvpResvFwdRSVPHop OBJECT-TYPE
    SYNTAX TruthValue
--    Rsyntax INTEGER {
--        true(1),
--        false(2)
--        }
    ACCESS read-only
    STATUS mandatory
    DESCRIPTION
        "If TRUE, the node believes that  the  next IP
        hop is  an RSVP  hop.   If  FALSE,  the  node
        believes that the next IP hop  may  not  be an
        RSVP hop."
    ::= { rsvpResvFwdEntry 25 }

rsvpResvFwdLastChange OBJECT-TYPE
    SYNTAX TimeStamp
--    Rsyntax TimeTicks
    ACCESS read-only
    STATUS mandatory
    DESCRIPTION
        "The time of the last change in  this  request;
        This  is  either  the first time it was sent or
        the time  of  the  most   recent   change in
        parameters."
    ::= { rsvpResvFwdEntry 26 }

rsvpResvFwdPolicy OBJECT-TYPE
    SYNTAX OCTET STRING(SIZE(0..65536))
    ACCESS read-only
    STATUS mandatory
    DESCRIPTION
        "The contents of the policy object,  displayed
        as an uninterpreted string of octets, including
        the object header.  In the absence of  such an
        object, this should be of zero length."
    ::= { rsvpResvFwdEntry 27 }

rsvpResvFwdStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' for all active RESV  messages.   This
        object may be used to delete RESV information."
    ::= { rsvpResvFwdEntry 28 }

rsvpResvFwdTTL OBJECT-TYPE
    SYNTAX INTEGER(0..255)
    ACCESS read-only
    STATUS mandatory
    DESCRIPTION
        "The TTL value in the RSVP header that was last
        received."
    ::= { rsvpResvFwdEntry 29 }

rsvpResvFwdFlowId OBJECT-TYPE
    SYNTAX INTEGER(0..16777215)
    ACCESS read-only
    STATUS mandatory
    DESCRIPTION
        "The flow ID that this receiver  is using, if
        this  is  an IPv6 session."
    ::= { rsvpResvFwdEntry 30 }

rsvpIfTable OBJECT-TYPE
    SYNTAX SEQUENCE OF RsvpIfEntry
    ACCESS not-accessible
    STATUS mandatory
    DESCRIPTION
        "The RSVP-specific attributes of  the  system's
        interfaces."
    ::= { rsvpObjects 6 }

rsvpIfEntry OBJECT-TYPE
    SYNTAX RsvpIfEntry
    ACCESS not-accessible
    STATUS mandatory
    DESCRIPTION
        "The RSVP-specific attributes of  the  a  given
        interface."
    INDEX { ifIndex }
    ::= { rsvpIfTable 1 }

RsvpIfEntry ::= SEQUENCE {
    rsvpIfUdpNbrs Gauge,
    rsvpIfIpNbrs Gauge,
    rsvpIfNbrs Gauge,
    rsvpIfEnabled TruthValue,
    rsvpIfUdpRequired TruthValue,
    rsvpIfRefreshBlockadeMultiple INTEGER,
    rsvpIfRefreshMultiple INTEGER,
    rsvpIfTTL INTEGER,
    rsvpIfRefreshInterval TimeInterval,
    rsvpIfRouteDelay TimeInterval,
    rsvpIfStatus RowStatus
    }

rsvpIfUdpNbrs OBJECT-TYPE
    SYNTAX Gauge
    ACCESS read-only
    STATUS mandatory
    DESCRIPTION
        "The number of neighbors perceived to be  using
        only the RSVP UDP Encapsulation."
    ::= { rsvpIfEntry 1 }

rsvpIfIpNbrs OBJECT-TYPE
    SYNTAX Gauge
    ACCESS read-only
    STATUS mandatory
    DESCRIPTION
        "The number of neighbors perceived to be  using
        only the RSVP IP Encapsulation."
    ::= { rsvpIfEntry 2 }

rsvpIfNbrs OBJECT-TYPE
    SYNTAX Gauge
    ACCESS read-only
    STATUS mandatory
    DESCRIPTION
        "The number of neighbors  currently perceived;
        this  will  exceed rsvpIfIpNbrs + rsvpIfUdpNbrs
        by  the  number   of   neighbors   using   both
        encapsulations."
    ::= { rsvpIfEntry 3 }

rsvpIfRefreshBlockadeMultiple OBJECT-TYPE
    SYNTAX INTEGER(1..65536)
    ACCESS read-write
    STATUS mandatory
    DESCRIPTION
        "The value of the RSVP value 'Kb', Which is the
        minimum   number   of  refresh  intervals  that
        blockade state will last once entered."
    DEFVAL { 4 }
    ::= { rsvpIfEntry 4 }

rsvpIfRefreshMultiple OBJECT-TYPE
    SYNTAX INTEGER(1..65536)
    ACCESS read-write
    STATUS mandatory
    DESCRIPTION
        "The value of the RSVP value 'K', which is  the
        number  of  refresh intervals which must elapse
        (minimum) before a PATH or RESV  message  which
        is not being refreshed will be aged out."
    DEFVAL { 3 }
    ::= { rsvpIfEntry 5 }

rsvpIfTTL OBJECT-TYPE
    SYNTAX INTEGER(0..255)
    ACCESS read-write
    STATUS mandatory
    DESCRIPTION
        "The value of SEND_TTL used on  this  interface
        for messages  this node originates.  If set to
        zero, the node determines  the  TTL via  other
        means."
    DEFVAL { 0 }
    ::= { rsvpIfEntry 6 }

rsvpIfRefreshInterval OBJECT-TYPE
    SYNTAX TimeInterval
--    Rsyntax INTEGER(0..2147483647)
--  Units
--    milliseconds
    ACCESS read-write
    STATUS mandatory
    DESCRIPTION
        "The value of the RSVP value 'R', which is  the
        minimum period between refresh transmissions of
        a given PATH or RESV message on an interface."
    DEFVAL { 3000 }
    ::= { rsvpIfEntry 7 }

rsvpIfRouteDelay OBJECT-TYPE
    SYNTAX TimeInterval
--    Rsyntax INTEGER(0..2147483647)
--  Units
--    hundredths of a second
    ACCESS read-write
    STATUS mandatory
    DESCRIPTION
        "The approximate period from the time  a  route
        is  changed to  the  time  a resulting message
        appears on the interface."
    DEFVAL { 200 }
    ::= { rsvpIfEntry 8 }

rsvpIfEnabled OBJECT-TYPE
    SYNTAX TruthValue
--    Rsyntax INTEGER {
--        true(1),
--        false(2)
--        }
    ACCESS read-write
    STATUS mandatory
    DESCRIPTION
        "If TRUE, RSVP is enabled  on  this Interface.
        If FALSE,  RSVP is  not  enabled  on  this
        interface."
    ::= { rsvpIfEntry 9 }

rsvpIfUdpRequired OBJECT-TYPE
    SYNTAX TruthValue
--    Rsyntax INTEGER {
--        true(1),
--        false(2)
--        }
    ACCESS read-write
    STATUS mandatory
    DESCRIPTION
        "If TRUE, manual configuration forces  the  use
        of  UDP  encapsulation  on  the  interface. If
        FALSE,  UDP encapsulation  is  only  used if
        rsvpIfUdpNbrs is not zero."
    ::= { rsvpIfEntry 10 }

rsvpIfStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' on interfaces that are configured for
        RSVP."
    ::= { rsvpIfEntry 11 }

rsvpNbrTable OBJECT-TYPE
    SYNTAX SEQUENCE OF RsvpNbrEntry
    ACCESS not-accessible
    STATUS mandatory
    DESCRIPTION
        "Information describing  the  Neighbors  of an
        RSVP system."
    ::= { rsvpObjects 7 }

rsvpNbrEntry OBJECT-TYPE
    SYNTAX RsvpNbrEntry
    ACCESS not-accessible
    STATUS mandatory
    DESCRIPTION
        "Information   describing   a    single    RSVP
        Neighbor."
    INDEX { ifIndex, rsvpNbrAddress }
    ::= { rsvpNbrTable 1 }

RsvpNbrEntry ::= SEQUENCE {
    rsvpNbrAddress OCTET STRING,
    rsvpNbrProtocol RsvpEncapsulation,
    rsvpNbrStatus RowStatus
    }

rsvpNbrAddress OBJECT-TYPE
    SYNTAX OCTET STRING(SIZE(4..16))
    ACCESS not-accessible
    STATUS mandatory
    DESCRIPTION
        "The IP4 or IP6 Address used by this  neighbor.
        This  object  may not be changed when the value
        of the RowStatus object is 'active'."
    ::= { rsvpNbrEntry 1 }

rsvpNbrProtocol OBJECT-TYPE
    SYNTAX RsvpEncapsulation
--    Rsyntax INTEGER {
--        ip(1),
--        udp(2),
--        both(3)
--        }
    ACCESS read-write
    STATUS mandatory
    DESCRIPTION
        "The   encapsulation   being   used  by   this
        neighbor."
    ::= { rsvpNbrEntry 2 }

rsvpNbrStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "'active' for all neighbors.  This  object  may
        be used   to  configure  neighbors.   In  the
        presence   of   configured  neighbors,    the
        implementation  may (but  is  not required to)
        limit the  set  of  valid  neighbors  to  those
        configured."
    ::= { rsvpNbrEntry 3 }

newFlow TRAP-TYPE
-- Reverse mappable trap
    ENTERPRISE rsvpNotificationsPrefix
    VARIABLES {
        intSrvFlowStatus, rsvpSessionDestAddr, rsvpResvFwdStatus, 
        rsvpResvStatus, rsvpSenderStatus }
--  Status
--    mandatory
    DESCRIPTION
        "The   newFlow   trap   indicates   that    the
        originating system has installed a new flow in
        its  classifier, or    (when    reservation
        authorization   is  in  view)  is  prepared to
        install such a flow in the  classifier  and is
        requesting authorization.  The objects included
        with the  Notification  may be  used  to  read
        further   information   using   the Integrated
        Services and RSVP MIBs.  Authorization or  non-
        authorization  may be enacted by a write to the
        variable intSrvFlowStatus."
    ::= 1

lostFlow TRAP-TYPE
-- Reverse mappable trap
    ENTERPRISE rsvpNotificationsPrefix
    VARIABLES {
        intSrvFlowStatus, rsvpSessionDestAddr, rsvpResvFwdStatus, 
        rsvpResvStatus, rsvpSenderStatus }
--  Status
--    mandatory
    DESCRIPTION
        "The   lostFlow   trap   indicates that   the
        originating system has removed a flow from its
        classifier."
    ::= 2

rsvpSessionGroup OBJECT IDENTIFIER ::= { rsvpGroups 1 }
-- OBJECT-GROUP
--  Status
--    mandatory
--  Descr
--    These objects are required for RSVP Systems.
--  objects
--    rsvpSessionType, rsvpSessionDestAddr, 
--    rsvpSessionDestAddrLength, rsvpSessionProtocol, 
--    rsvpSessionPort, rsvpSessionSenders, rsvpSessionReceivers, 
--    rsvpSessionRequests, rsvpSessionNewIndex

rsvpSenderGroup OBJECT IDENTIFIER ::= { rsvpGroups 2 }
-- OBJECT-GROUP
--  Status
--    mandatory
--  Descr
--    These objects are required for RSVP Systems.
--  objects
--    rsvpSenderType, rsvpSenderDestAddr, rsvpSenderAddr, 
--    rsvpSenderDestAddrLength, rsvpSenderAddrLength, 
--    rsvpSenderProtocol, rsvpSenderDestPort, rsvpSenderPort, 
--    rsvpSenderFlowId, rsvpSenderTTL, rsvpSenderHopAddr, 
--    rsvpSenderHopLih, rsvpSenderInterface, rsvpSenderTSpecRate, 
--    rsvpSenderTSpecPeakRate, rsvpSenderTSpecBurst, 
--    rsvpSenderTSpecMinTU, rsvpSenderTSpecMaxTU, 
--    rsvpSenderInterval, rsvpSenderLastChange, rsvpSenderStatus, 
--    rsvpSenderRSVPHop, rsvpSenderPolicy, rsvpSenderAdspecBreak, 
--    rsvpSenderAdspecHopCount, rsvpSenderAdspecPathBw, 
--    rsvpSenderAdspecMinLatency, rsvpSenderAdspecMtu, 
--    rsvpSenderAdspecGuaranteedSvc, 
--    rsvpSenderAdspecGuaranteedBreak, 
--    rsvpSenderAdspecGuaranteedCtot, 
--    rsvpSenderAdspecGuaranteedDtot, 
--    rsvpSenderAdspecGuaranteedCsum, 
--    rsvpSenderAdspecGuaranteedDsum, 
--    rsvpSenderAdspecGuaranteedHopCount, 
--    rsvpSenderAdspecGuaranteedPathBw, 
--    rsvpSenderAdspecGuaranteedMinLatency, 
--    rsvpSenderAdspecGuaranteedMtu, rsvpSenderAdspecCtrlLoadSvc, 
--    rsvpSenderAdspecCtrlLoadBreak, 
--    rsvpSenderAdspecCtrlLoadHopCount, 
--    rsvpSenderAdspecCtrlLoadPathBw, 
--    rsvpSenderAdspecCtrlLoadMinLatency, 
--    rsvpSenderAdspecCtrlLoadMtu, rsvpSenderNewIndex

rsvpResvGroup OBJECT IDENTIFIER ::= { rsvpGroups 3 }
-- OBJECT-GROUP
--  Status
--    mandatory
--  Descr
--    These objects are required for RSVP Systems.
--  objects
--    rsvpResvType, rsvpResvDestAddr, rsvpResvSenderAddr, 
--    rsvpResvDestAddrLength, rsvpResvSenderAddrLength, 
--    rsvpResvProtocol, rsvpResvDestPort, rsvpResvPort, 
--    rsvpResvHopAddr, rsvpResvHopLih, rsvpResvInterface, 
--    rsvpResvService, rsvpResvTSpecRate, rsvpResvTSpecBurst, 
--    rsvpResvTSpecPeakRate, rsvpResvTSpecMinTU, rsvpResvTSpecMaxTU, 
--    rsvpResvRSpecRate, rsvpResvRSpecSlack, rsvpResvInterval, 
--    rsvpResvScope, rsvpResvShared, rsvpResvExplicit, 
--    rsvpResvRSVPHop, rsvpResvLastChange, rsvpResvPolicy, 
--    rsvpResvStatus, rsvpResvNewIndex, rsvpResvTTL, rsvpResvFlowId

rsvpResvFwdGroup OBJECT IDENTIFIER ::= { rsvpGroups 4 }
-- OBJECT-GROUP
--  Status
--    mandatory
--  Descr
--    These objects are optional, used for some RSVP
--    Systems.
--  objects
--    rsvpResvFwdType, rsvpResvFwdDestAddr, rsvpResvFwdSenderAddr, 
--    rsvpResvFwdDestAddrLength, rsvpResvFwdSenderAddrLength, 
--    rsvpResvFwdProtocol, rsvpResvFwdDestPort, rsvpResvFwdPort, 
--    rsvpResvFwdHopAddr, rsvpResvFwdHopLih, rsvpResvFwdInterface, 
--    rsvpResvFwdNewIndex, rsvpResvFwdService, 
--    rsvpResvFwdTSpecPeakRate, rsvpResvFwdTSpecMinTU, 
--    rsvpResvFwdTSpecMaxTU, rsvpResvFwdTSpecRate, 
--    rsvpResvFwdTSpecBurst, rsvpResvFwdRSpecRate, 
--    rsvpResvFwdRSpecSlack, rsvpResvFwdInterval, rsvpResvFwdScope, 
--    rsvpResvFwdShared, rsvpResvFwdExplicit, rsvpResvFwdRSVPHop, 
--    rsvpResvFwdLastChange, rsvpResvFwdPolicy, rsvpResvFwdStatus, 
--    rsvpResvFwdTTL, rsvpResvFwdFlowId

rsvpIfGroup OBJECT IDENTIFIER ::= { rsvpGroups 5 }
-- OBJECT-GROUP
--  Status
--    mandatory
--  Descr
--    These objects are required for RSVP Systems.
--  objects
--    rsvpIfUdpNbrs, rsvpIfIpNbrs, rsvpIfNbrs, rsvpIfEnabled, 
--    rsvpIfUdpRequired, rsvpIfRefreshBlockadeMultiple, 
--    rsvpIfRefreshMultiple, rsvpIfRefreshInterval, rsvpIfTTL, 
--    rsvpIfRouteDelay, rsvpIfStatus

rsvpNbrGroup OBJECT IDENTIFIER ::= { rsvpGroups 6 }
-- OBJECT-GROUP
--  Status
--    mandatory
--  Descr
--    These objects are required for RSVP Systems.
--  objects
--    rsvpNbrProtocol, rsvpNbrStatus

rsvpGenObjectsGroup OBJECT IDENTIFIER ::= { rsvpGroups 7 }
-- OBJECT-GROUP
--  Status
--    mandatory
--  Descr
--    This objects are required for RSVP Systems.
--  objects
--    rsvpBadPackets

rsvpSenderOutInterfaceGroup OBJECT IDENTIFIER ::= { rsvpGroups 8 }
-- OBJECT-GROUP
--  Status
--    mandatory
--  Descr
--    These objects are required for RSVP Systems.
--  objects
--    rsvpSenderOutInterfaceStatus

rsvpNotificationGroup OBJECT IDENTIFIER ::= { rsvpGroups 9 }
-- NOTIFICATION-GROUP
--  Status
--    mandatory
--  Descr
--    This  notification is  required  for  Systems
--    supporting the RSVP Policy Module using an SNMP
--    interface to the Policy Manager.
--  notifications
--    newFlow, lostFlow

rsvpCompliance OBJECT IDENTIFIER ::= { rsvpCompliances 1 }
-- MODULE-COMPLIANCE
--  Status
--    mandatory
--  Descr
--    The  compliance  statement.   Note that   the
--    implementation    of   this  module   requires
--    implementation of the Integrated  Services  MIB
--    as well.
--  Module
--    >>current<<
--   MandGroup
--    rsvpSessionGroup
--   MandGroup
--    rsvpSenderGroup
--   MandGroup
--    rsvpResvGroup
--   MandGroup
--    rsvpIfGroup
--   MandGroup
--    rsvpNbrGroup
--   MandGroup
--    rsvpGenObjectsGroup
--   MandGroup
--    rsvpSenderOutInterfaceGroup
--   OptGroup
--    rsvpResvFwdGroup
--   OptGroup
--    rsvpNotificationGroup
--   ObjVar
--    rsvpSessionRequests
--   ObjVar
--    rsvpSenderType
--   ObjVar
--    rsvpSenderDestAddr
--   ObjVar
--    rsvpSenderAddr
--   ObjVar
--    rsvpSenderDestAddrLength
--   ObjVar
--    rsvpSenderAddrLength
--   ObjVar
--    rsvpSenderProtocol
--   ObjVar
--    rsvpSenderDestPort
--   ObjVar
--    rsvpSenderPort
--   ObjVar
--    rsvpSenderHopAddr
--   ObjVar
--    rsvpSenderHopLih
--   ObjVar
--    rsvpSenderInterface
--   ObjVar
--    rsvpSenderTSpecRate
--   ObjVar
--    rsvpSenderTSpecPeakRate
--   ObjVar
--    rsvpSenderTSpecBurst
--   ObjVar
--    rsvpSenderTSpecMinTU
--   ObjVar
--    rsvpSenderTSpecMaxTU
--   ObjVar
--    rsvpSenderInterval
--   ObjVar
--    rsvpSenderRSVPHop
--   ObjVar
--    rsvpSenderPolicy
--   ObjVar
--    rsvpSenderAdspecBreak
--   ObjVar
--    rsvpSenderAdspecHopCount
--   ObjVar
--    rsvpSenderAdspecPathBw
--   ObjVar
--    rsvpSenderAdspecMinLatency
--   ObjVar
--    rsvpSenderAdspecMtu
--   ObjVar
--    rsvpSenderAdspecGuaranteedSvc
--   ObjVar
--    rsvpSenderAdspecGuaranteedBreak
--   ObjVar
--    rsvpSenderAdspecGuaranteedCtot
--   ObjVar
--    rsvpSenderAdspecGuaranteedDtot
--   ObjVar
--    rsvpSenderAdspecGuaranteedCsum
--   ObjVar
--    rsvpSenderAdspecGuaranteedDsum
--   ObjVar
--    rsvpSenderAdspecGuaranteedHopCount
--   ObjVar
--    rsvpSenderAdspecGuaranteedPathBw
--   ObjVar
--    rsvpSenderAdspecGuaranteedMinLatency
--   ObjVar
--    rsvpSenderAdspecGuaranteedMtu
--   ObjVar
--    rsvpSenderAdspecCtrlLoadSvc
--   ObjVar
--    rsvpSenderAdspecCtrlLoadBreak
--   ObjVar
--    rsvpSenderAdspecCtrlLoadHopCount
--   ObjVar
--    rsvpSenderAdspecCtrlLoadPathBw
--   ObjVar
--    rsvpSenderAdspecCtrlLoadMinLatency
--   ObjVar
--    rsvpSenderAdspecCtrlLoadMtu
--   ObjVar
--    rsvpSenderStatus
--   ObjVar
--    rsvpSenderFlowId
--   ObjVar
--    rsvpResvType
--   ObjVar
--    rsvpResvDestAddr
--   ObjVar
--    rsvpResvSenderAddr
--   ObjVar
--    rsvpResvDestAddrLength
--   ObjVar
--    rsvpResvSenderAddrLength
--   ObjVar
--    rsvpResvProtocol
--   ObjVar
--    rsvpResvDestPort
--   ObjVar
--    rsvpResvPort
--   ObjVar
--    rsvpResvHopAddr
--   ObjVar
--    rsvpResvHopLih
--   ObjVar
--    rsvpResvInterface
--   ObjVar
--    rsvpResvService
--   ObjVar
--    rsvpResvTSpecRate
--   ObjVar
--    rsvpResvTSpecPeakRate
--   ObjVar
--    rsvpResvTSpecBurst
--   ObjVar
--    rsvpResvTSpecMinTU
--   ObjVar
--    rsvpResvTSpecMaxTU
--   ObjVar
--    rsvpResvRSpecRate
--   ObjVar
--    rsvpResvRSpecSlack
--   ObjVar
--    rsvpResvInterval
--   ObjVar
--    rsvpResvScope
--   ObjVar
--    rsvpResvShared
--   ObjVar
--    rsvpResvExplicit
--   ObjVar
--    rsvpResvRSVPHop
--   ObjVar
--    rsvpResvPolicy
--   ObjVar
--    rsvpResvStatus
--   ObjVar
--    rsvpResvFlowId
--   ObjVar
--    rsvpResvFwdStatus
--   ObjVar
--    rsvpResvFwdFlowId


END
