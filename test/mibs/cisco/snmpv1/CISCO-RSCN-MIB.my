-- MIB file created 28-Dec-2002 10:33:05, by
--   SMICng version 2.2.11-beta(PRO)(Solaris), January 20, 2001. Enterprise key cisco.com

CISCO-RSCN-MIB DEFINITIONS ::= BEGIN

-- From file: "CISCO-RSCN-MIB.my"
-- Compile options "4 7 F H N W 03 06 0B 0G 0N 0T"

IMPORTS
    TruthValue
            FROM SNMPv2-TC-v1
    ciscoMgmt
            FROM CISCO-SMI
    FcAddressId
            FROM CISCO-ST-TC
    vsanIndex
            FROM CISCO-VSAN-MIB
    FcGs3RejectReasonCode
            FROM CISCO-NS-MIB
    Counter
            FROM RFC1155-SMI
    OBJECT-TYPE
            FROM RFC-1212
    TRAP-TYPE
            FROM RFC-1215;

ciscoRscnMIB OBJECT IDENTIFIER ::= { ciscoMgmt 292 }
-- MODULE-IDENTITY
--  LastUpdated
--    200209200000Z
--  OrgName
--    Cisco Systems Inc.
--  ContactInfo
--         Cisco Systems 
--          Customer Service 
--    Postal: 170 W Tasman Drive 
--          San Jose, CA  95134 
--          USA 
--    Tel: +1 800 553 -NETS 
--    E-mail: cs-san@cisco.com
--  Descr
--    The MIB module for the management of the Fibre 
--     Channel's Registered State Change Notification  
--     (RSCN) functionality, which is specified by 
--     FC-FLA and FC-FS.
--  RevDate
--    200209200000Z
--  RevDescr
--    Initial version of this MIB module.

ciscoRscnMIBObjects OBJECT IDENTIFIER ::= { ciscoRscnMIB 1 }
rscnMIBConformance OBJECT IDENTIFIER ::= { ciscoRscnMIB 2 }
rscnConfiguration OBJECT IDENTIFIER ::= { ciscoRscnMIBObjects 1 }
rscnStats       OBJECT IDENTIFIER ::= { ciscoRscnMIBObjects 2 }
rscnInformation OBJECT IDENTIFIER ::= { ciscoRscnMIBObjects 3 }
rscnNotification OBJECT IDENTIFIER ::= { ciscoRscnMIBObjects 4 }
rscnNotifications OBJECT IDENTIFIER ::= { rscnNotification 0 }
rscnMIBCompliances OBJECT IDENTIFIER ::= { rscnMIBConformance 1 }
rscnMIBGroups   OBJECT IDENTIFIER ::= { rscnMIBConformance 2 }

rscnScrNumber OBJECT-TYPE
    SYNTAX INTEGER(0..2147483647)
    ACCESS read-only
    STATUS mandatory
    DESCRIPTION
        "The number of Nx_Ports currently registered 
         to receive RSCNs."
    ::= { rscnConfiguration 1 }

rscnScrTable OBJECT-TYPE
    SYNTAX SEQUENCE OF RscnScrEntry
    ACCESS not-accessible
    STATUS mandatory
    DESCRIPTION
        "A table of Nx_Ports that have registered to 
         receive RSCNs on all VSANs configured on the  
         local switch."
    ::= { rscnConfiguration 2 }

rscnScrEntry OBJECT-TYPE
    SYNTAX RscnScrEntry
    ACCESS not-accessible
    STATUS mandatory
    DESCRIPTION
        "An entry (conceptual row) containing information 
         about one Nx_Port which has registered to receive 
         RSCNs on the VSAN indicated by vsanIndex."
    INDEX { vsanIndex, rscnScrFcId }
    ::= { rscnScrTable 1 }

RscnScrEntry ::= SEQUENCE {
    rscnScrFcId FcAddressId,
    rscnScrRegType INTEGER
    }

rscnScrFcId OBJECT-TYPE
    SYNTAX FcAddressId
--    Rsyntax OCTET STRING(SIZE(3))
    ACCESS not-accessible
    STATUS mandatory
    DESCRIPTION
        "The Fibre Channel Identifier (FC-ID) of the 
         subscribing Nx_Port."
    ::= { rscnScrEntry 1 }

rscnScrRegType OBJECT-TYPE
    SYNTAX INTEGER {
        fromFabricCtrlr(1),
        fromNxPort(2),
        fromBoth(3)
        }
    ACCESS read-only
    STATUS mandatory
    DESCRIPTION
        "This object indicates the type of registration 
         desired by the subscriber. 
        
         'fromFabricCtrlr' indicates RSCNs generated by the  
         Fabric Controller. 
        
         'fromNxPort' indicates RSCNs generated by  
         Nx_Ports. 
        
         'fromBoth' indicates RSCNs generated by Fabric 
         Controller and Nx_Ports."
    ::= { rscnScrEntry 2 }

rscnScrTotalRejects OBJECT-TYPE
    SYNTAX Counter
    ACCESS read-only
    STATUS mandatory
    DESCRIPTION
        "The total number of SCRs rejected 
         across all VSANs by the local switch."
    ::= { rscnStats 1 }

rscnRscnReqTotalRejects OBJECT-TYPE
    SYNTAX Counter
    ACCESS read-only
    STATUS mandatory
    DESCRIPTION
        "The total number of RSCN requests rejected 
         across all VSANs by the local switch."
    ::= { rscnStats 2 }

rscnSwRscnReqTotalRejects OBJECT-TYPE
    SYNTAX Counter
    ACCESS read-only
    STATUS mandatory
    DESCRIPTION
        "The total number of SW_RSCN requests rejected 
         across all VSANs by the local switch."
    ::= { rscnStats 3 }

rscnStatsTable OBJECT-TYPE
    SYNTAX SEQUENCE OF RscnStatsEntry
    ACCESS not-accessible
    STATUS mandatory
    DESCRIPTION
        "The statistics related to the RSCN module. The 
         statistics are maintained per VSAN."
    ::= { rscnStats 4 }

rscnStatsEntry OBJECT-TYPE
    SYNTAX RscnStatsEntry
    ACCESS not-accessible
    STATUS mandatory
    DESCRIPTION
        "An entry (conceptual row) in this table."
    INDEX { vsanIndex }
    ::= { rscnStatsTable 1 }

RscnStatsEntry ::= SEQUENCE {
    rscnRxScrs Counter,
    rscnRxRscns Counter,
    rscnTxRscns Counter,
    rscnRxSwRscns Counter,
    rscnTxSwRscns Counter,
    rscnScrRej Counter,
    rscnRscnReqRej Counter,
    rscnSwRscnReqRej Counter
    }

rscnRxScrs OBJECT-TYPE
    SYNTAX Counter
    ACCESS read-only
    STATUS mandatory
    DESCRIPTION
        "The number of SCRs received from Nx_Ports 
         on this VSAN."
    ::= { rscnStatsEntry 1 }

rscnRxRscns OBJECT-TYPE
    SYNTAX Counter
    ACCESS read-only
    STATUS mandatory
    DESCRIPTION
        "The number of RSCNs from Nx_Ports received on 
         this VSAN."
    ::= { rscnStatsEntry 2 }

rscnTxRscns OBJECT-TYPE
    SYNTAX Counter
    ACCESS read-only
    STATUS mandatory
    DESCRIPTION
        "The total number of RSCNs transmitted on this  
         VSAN."
    ::= { rscnStatsEntry 3 }

rscnRxSwRscns OBJECT-TYPE
    SYNTAX Counter
    ACCESS read-only
    STATUS mandatory
    DESCRIPTION
        "The number of Inter-Switch Registered State 
         Change Notifications (SW_RSCN) received on this 
         VSAN from other switches."
    ::= { rscnStatsEntry 4 }

rscnTxSwRscns OBJECT-TYPE
    SYNTAX Counter
    ACCESS read-only
    STATUS mandatory
    DESCRIPTION
        "The number of Inter-Switch Registered State 
         Change Notifications (SW_RSCN) transmitted 
         on this VSAN to other switches."
    ::= { rscnStatsEntry 5 }

rscnScrRej OBJECT-TYPE
    SYNTAX Counter
    ACCESS read-only
    STATUS mandatory
    DESCRIPTION
        "The number of SCR rejected on this VSAN."
    ::= { rscnStatsEntry 6 }

rscnRscnReqRej OBJECT-TYPE
    SYNTAX Counter
    ACCESS read-only
    STATUS mandatory
    DESCRIPTION
        "The number of RSCN requests rejected on this VSAN."
    ::= { rscnStatsEntry 7 }

rscnSwRscnReqRej OBJECT-TYPE
    SYNTAX Counter
    ACCESS read-only
    STATUS mandatory
    DESCRIPTION
        "The number of SW_RSCN requests rejected on this VSAN."
    ::= { rscnStatsEntry 8 }

rscnIlsRejReasonCode OBJECT-TYPE
    SYNTAX FcGs3RejectReasonCode
--    Rsyntax INTEGER {
--        none(1),
--        invalidCmdCode(2),
--        invalidVerLevel(3),
--        logicalError(4),
--        invalidIUSize(5),
--        logicalBusy(6),
--        protocolError(7),
--        unableToPerformCmdReq(8),
--        cmdNotSupported(9),
--        vendorError(10)
--        }
    ACCESS read-only
    STATUS mandatory
    DESCRIPTION
        "The reason code corresponding to an ILS 
         request rejection. This object contains the  
         reason code corresponding to the most recent  
         SCR or RSCN  request rejection by the RSCN  
         module."
    ::= { rscnInformation 1 }

rscnElsRejReasonCode OBJECT-TYPE
    SYNTAX FcGs3RejectReasonCode
--    Rsyntax INTEGER {
--        none(1),
--        invalidCmdCode(2),
--        invalidVerLevel(3),
--        logicalError(4),
--        invalidIUSize(5),
--        logicalBusy(6),
--        protocolError(7),
--        unableToPerformCmdReq(8),
--        cmdNotSupported(9),
--        vendorError(10)
--        }
    ACCESS read-only
    STATUS mandatory
    DESCRIPTION
        "The reason code corresponding to an ELS 
         request rejection. This object contains the 
         reason code corresponding the most recent 
         SW_RSCN request rejection by the RSCN module."
    ::= { rscnInformation 2 }

rscnIlsRejectReqNotifyEnable OBJECT-TYPE
    SYNTAX TruthValue
--    Rsyntax INTEGER {
--        true(1),
--        false(2)
--        }
    ACCESS read-write
    STATUS mandatory
    DESCRIPTION
        "This object specifies if the RSCN module should 
        generate 'rscnIlsRejectReqNotify' notifications. 
          
        If value of this object is 'true', then the  
        notification is generated when a SW_RSCN request  
        is rejected.  
        
        If it is 'false', the notification is not generated."
    DEFVAL { false }
    ::= { rscnConfiguration 3 }

rscnElsRejectReqNotifyEnable OBJECT-TYPE
    SYNTAX TruthValue
--    Rsyntax INTEGER {
--        true(1),
--        false(2)
--        }
    ACCESS read-write
    STATUS mandatory
    DESCRIPTION
        "This object specifies if the RSCN module should 
        generate 'rscnElsRejectReqNotify' notifications. 
          
        If value of this object is 'true', then the  
        notification is generated when a SCR or RSCN request  
        is rejected.  
        
        If it is 'false', the notification is not generated."
    DEFVAL { false }
    ::= { rscnConfiguration 4 }

rscnNotifyFcId OBJECT-TYPE
    SYNTAX FcAddressId
--    Rsyntax OCTET STRING(SIZE(3))
    ACCESS not-accessible
    STATUS mandatory
    DESCRIPTION
        "The FC-ID of an Nx_Port.  
         This object is to be used in the notifications: 
         rscnElsRejectReqNotify and rscnIlsRejectReqNotify. 
         This object is defined since the rscnScrFcId 
         object in the rscnScrTable is not-accessible."
    ::= { rscnConfiguration 5 }

rscnElsRejectReqNotify TRAP-TYPE
-- Reverse mappable trap
    ENTERPRISE rscnNotification
    VARIABLES {
        rscnElsRejReasonCode, rscnNotifyFcId }
--  Status
--    mandatory
    DESCRIPTION
        "This notification is generated by the RSCN module  
         on this switch whenever it rejects a SCR or RSCN  
         request. 
        
         The RSCN module  should update the  
         rscnElsRejReasonCode object with the corresponding  
         reason code before sending the notification. 
        
         The rscnScrFcId object indicates the FC-ID of the  
         sender of the request that was rejected."
    ::= 1

rscnIlsRejectReqNotify TRAP-TYPE
-- Reverse mappable trap
    ENTERPRISE rscnNotification
    VARIABLES {
        rscnIlsRejReasonCode, rscnNotifyFcId }
--  Status
--    mandatory
    DESCRIPTION
        "This notification is generated by the RSCN module  
         on this switch whenever it rejects a SW_RSCN  
         request. 
        
         The RSCN module  should update the  
         rscnIlsRejReasonCode object with the corresponding  
         reason code before sending the notification. 
        
         The rscnScrFcId object contains the FC-ID of the 
         sender of the request that was rejected."
    ::= 2

rscnConfigGroup OBJECT IDENTIFIER ::= { rscnMIBGroups 1 }
-- OBJECT-GROUP
--  Status
--    mandatory
--  Descr
--    A collection of objects for configuring 
--     and displaying SCR entries.
--  objects
--    rscnScrNumber, rscnScrRegType, rscnNotifyFcId

rscnStatsGroup OBJECT IDENTIFIER ::= { rscnMIBGroups 2 }
-- OBJECT-GROUP
--  Status
--    mandatory
--  Descr
--    A collection of objects for displaying  
--     RSCN statistics.
--  objects
--    rscnScrTotalRejects, rscnRscnReqTotalRejects, 
--    rscnSwRscnReqTotalRejects, rscnRxScrs, rscnRxRscns, 
--    rscnTxRscns, rscnRxSwRscns, rscnTxSwRscns, rscnScrRej, 
--    rscnRscnReqRej, rscnSwRscnReqRej

rscnNotifyControlGroup OBJECT IDENTIFIER ::= { rscnMIBGroups 3 }
-- OBJECT-GROUP
--  Status
--    mandatory
--  Descr
--    A collection of notification control and 
--     notification information objects.
--  objects
--    rscnIlsRejReasonCode, rscnElsRejReasonCode, 
--    rscnIlsRejectReqNotifyEnable, rscnElsRejectReqNotifyEnable

rscnNotifyGroup OBJECT IDENTIFIER ::= { rscnMIBGroups 4 }
-- NOTIFICATION-GROUP
--  Status
--    mandatory
--  Descr
--    A collection of notifications for monitoring 
--     ILS and ELS request rejection by the RSCN 
--     module.
--  notifications
--    rscnIlsRejectReqNotify, rscnElsRejectReqNotify

rscnMIBCompliance OBJECT IDENTIFIER ::= { rscnMIBCompliances 1 }
-- MODULE-COMPLIANCE
--  Status
--    mandatory
--  Descr
--    The compliance statement for entities which  
--     implement RSCN feature.
--  Module
--    >>current<<
--   MandGroup
--    rscnConfigGroup
--   MandGroup
--    rscnStatsGroup
--   MandGroup
--    rscnNotifyControlGroup
--   MandGroup
--    rscnNotifyGroup


END
