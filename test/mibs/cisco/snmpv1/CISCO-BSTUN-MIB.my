-- MIB file created 10-Dec-2001 12:18:58, by
--   SMICng version 2.2.11-beta(PRO)(Solaris), January 20, 2001. Enterprise key cisco.com

CISCO-BSTUN-MIB DEFINITIONS ::= BEGIN

-- From file: "CISCO-BSTUN-MIB.my"
-- Compile options "4 7 F H N W 03 06 0B 0G 0N 0T"

IMPORTS
    ifIndex, InterfaceIndex
            FROM IF-MIB
    TruthValue
            FROM SNMPv2-TC-v1
    ciscoMgmt
            FROM CISCO-SMI
    Counter, IpAddress
            FROM RFC1155-SMI
    OBJECT-TYPE
            FROM RFC-1212
    TRAP-TYPE
            FROM RFC-1215;

ciscoBstunMIB OBJECT IDENTIFIER ::= { ciscoMgmt 35 }
-- MODULE-IDENTITY
--  LastUpdated
--    200106190000Z
--  OrgName
--    Cisco Systems, Inc.
--  ContactInfo
--           Cisco Systems
--     Customer Service
--                       
--    Postal: 170 W. Tasman Drive
--     San Jose, CA 95134
--     USA
--    
--       Tel: +1 800 553-NETS
--    E-mail: cs-bisync@cisco.com
--  Descr
--    The MIB module for Block Serial Tunneling.
--              
--     Overview of BSTUN MIB
--    
--     MIB description
--     
--     The BSTUN MIB provides the configuration and operational information 
--     on Cisco's blocked serial tunnelling implementation.  The following 
--     entities are managed:
--      1) Global BSTUN information
--      2) BSTUN groups
--      3) BSTUN ports
--      4) BSTUN routes
--    
--     The following example configuration shows how the BSTUN MIB returns
--     BSTUN information, from either CISCO A or CISCO B.
--    
--      HOST == BSC  == Cisco A == IP Network == Cisco B == BSC   == BSC
--              line                                        line     device
--    
--     1) The BSTUN global entry identifies the IP address by which the
--        router is known to other BSTUN peers, a configurable SAP value
--        on which to listen to LLC2 peers, and keepalive values to maintain
--        a session between TCP/IP peers.
--     2) The BSTUN group table identifies the BSTUN group number and protocol
--        type that Cisco A and Cisco B use to route BSC traffic over the 
--        IP network.  The table contains an entry for each BSTUN group
--        defined on the router. (The group number must be the same in Cisco A 
--        and Cisco B, for traffic to flow from one router to the other.)
--     3) The BSTUN port table identifies the serial interface to the BSC 
--        line for which the router is doing serial tunnelling.  The MIB also
--        identifies the BSTUN group this interface is defined for, and
--        identifies the default routing for unrecognized BSC addresses.
--        There is a port entry for each BSTUN-enabled interface on the router.
--     4) The BSTUN route table has an entry for each address defined for
--        routing within the BSTUN group, and an entry for the default routing
--        if the 'bstun route all' command is configured.  The route entry
--        includes identification of the BSTUN peer, priority, state, and 
--        packet and byte counters.
--              
--              
--  RevDate
--    200106190000Z
--  RevDescr
--    Added Bisync to IP conversion peer support
--  RevDate
--    9701220000Z
--  RevDescr
--    Added frame-relay and other support
--  RevDate
--    9508210000Z
--  RevDescr
--    Minor cleanups to pacify mib compiler.

bstunObjects    OBJECT IDENTIFIER ::= { ciscoBstunMIB 1 }
bstunGlobal     OBJECT IDENTIFIER ::= { bstunObjects 1 }
bstunGroups     OBJECT IDENTIFIER ::= { bstunObjects 2 }
bstunPorts      OBJECT IDENTIFIER ::= { bstunObjects 3 }
bstunRoutes     OBJECT IDENTIFIER ::= { bstunObjects 4 }
bstunNotificationPrefix OBJECT IDENTIFIER ::= { ciscoBstunMIB 2 }
bstunNotifications OBJECT IDENTIFIER ::= { bstunNotificationPrefix 0 }
bstunMibConformance OBJECT IDENTIFIER ::= { ciscoBstunMIB 3 }
bstunMibCompliances OBJECT IDENTIFIER ::= { bstunMibConformance 1 }
bstunMibGroups  OBJECT IDENTIFIER ::= { bstunMibConformance 2 }

bstunIPAddr OBJECT-TYPE
    SYNTAX IpAddress
    ACCESS read-only
    STATUS mandatory
    DESCRIPTION
        "The configured IP address used by the BSTUN component in
         this router."
    ::= { bstunGlobal 1 }

bstunLisnSap OBJECT-TYPE
    SYNTAX INTEGER(1..255)
    ACCESS read-only
    STATUS mandatory
    DESCRIPTION
        "The configured Listening SAP address used by the BSTUN 
         component when routed via frame-relay local-ack in
         this router."
    ::= { bstunGlobal 2 }

bstunPeerKeepaliveInterval OBJECT-TYPE
    SYNTAX INTEGER(1..300)
--  Units
--    deciseconds
    ACCESS read-only
    STATUS mandatory
    DESCRIPTION
        "The time interval between keepalives in this router."
    ::= { bstunGlobal 3 }

bstunPeerKeepaliveLimit OBJECT-TYPE
    SYNTAX INTEGER(2..10)
    ACCESS read-only
    STATUS mandatory
    DESCRIPTION
        "The number of keepalives which can be missed in a continuous
         interval before session declared down in this router."
    ::= { bstunGlobal 4 }

bstunGroupTable OBJECT-TYPE
    SYNTAX SEQUENCE OF BstunGroupEntry
    ACCESS not-accessible
    STATUS mandatory
    DESCRIPTION
        "A table of entries representing BSTUN groups configured on the
         router.  Each BSTUN-enabled interface is assigned to a BSTUN
         group, and packets can only travel between BSTUN-enabled
         interfaces in the same group."
    ::= { bstunGroups 1 }

bstunGroupEntry OBJECT-TYPE
    SYNTAX BstunGroupEntry
    ACCESS not-accessible
    STATUS mandatory
    DESCRIPTION
        "Status and parameter values for a group."
    INDEX { bstunGroupIndex }
    ::= { bstunGroupTable 1 }

BstunGroupEntry ::= SEQUENCE {
    bstunGroupIndex INTEGER,
    bstunProtocolType INTEGER,
    bstunLocalAck TruthValue,
    bstunGroupUnroutableTransmit Counter,
    bstunGroupUnroutableReceive Counter
    }

bstunGroupIndex OBJECT-TYPE
    SYNTAX INTEGER(1..255)
    ACCESS not-accessible
    STATUS mandatory
    DESCRIPTION
        "The configured BSTUN group number.  The significance of this 
        number is that it must match the BSTUN group number configured in 
        the router at the other end of the BSTUN tunnel."
    ::= { bstunGroupEntry 1 }

bstunProtocolType OBJECT-TYPE
    SYNTAX INTEGER {
        bsc(1),
        adtVariPoll(2),
        adtPollSelect(3),
        adplex(4),
        diebold(5),
        asyncGeneric(6),
        mdi(7)
        }
    ACCESS read-only
    STATUS mandatory
    DESCRIPTION
        "The protocol type for this BSTUN group."
    ::= { bstunGroupEntry 2 }

bstunLocalAck OBJECT-TYPE
    SYNTAX TruthValue
--    Rsyntax INTEGER {
--        true(1),
--        false(2)
--        }
    ACCESS read-only
    STATUS mandatory
    DESCRIPTION
        "Indicates if the BSTUN connection is locally acknowledged.       
         TRUE-> BSTUN connection is locally acknowledged
         FALSE-> BSTUN connection is not locally acknowledged"
    ::= { bstunGroupEntry 3 }

bstunGroupUnroutableTransmit OBJECT-TYPE
    SYNTAX Counter
    ACCESS read-only
    STATUS mandatory
    DESCRIPTION
        "The number of unroutable frames received
         by this group from the remote partner.  They
         were unroutable because the address was not
         recognized; that is there is no bstun route command
         configured for this address.  This indicates that the
         configuration in this router is incompatible with the
         peer router."
    ::= { bstunGroupEntry 4 }

bstunGroupUnroutableReceive OBJECT-TYPE
    SYNTAX Counter
    ACCESS read-only
    STATUS mandatory
    DESCRIPTION
        "Count of frames received from a serial
         interface with an unsupported poll address.
         Note that there may be several ports configured
         within this bstun group; a non-zero value in this
         field indicates that a least one of these ports
         is receiving frames for which there are no 
         bstun route commands configured.  This indicates that
         the configuration in this router is incompatible with
         the configuration in at least one of the attached devices."
    ::= { bstunGroupEntry 5 }

bstunPortTable OBJECT-TYPE
    SYNTAX SEQUENCE OF BstunPortEntry
    ACCESS not-accessible
    STATUS mandatory
    DESCRIPTION
        "A list of BSTUN-enabled interfaces (ports)."
    ::= { bstunPorts 1 }

bstunPortEntry OBJECT-TYPE
    SYNTAX BstunPortEntry
    ACCESS not-accessible
    STATUS mandatory
    DESCRIPTION
        "Status and parameter values for a BSTUN port."
    INDEX { ifIndex }
    ::= { bstunPortTable 1 }

BstunPortEntry ::= SEQUENCE {
    bstunPortGroupNumber INTEGER,
    bstunPortDefaultPeerType INTEGER,
    bstunPortDefaultPeerIP IpAddress,
    bstunPortDefaultPeerSerial InterfaceIndex
    }

bstunPortGroupNumber OBJECT-TYPE
    SYNTAX INTEGER(1..255)
    ACCESS read-only
    STATUS mandatory
    DESCRIPTION
        "The group number to which the bstun port
         belongs.  Frames will only be routed to other 
         ports (on this or another router) in the same 
         bstun group.  This group should match a bstunGroupIndex
         in the bstunGroupTable."
    ::= { bstunPortEntry 1 }

bstunPortDefaultPeerType OBJECT-TYPE
    SYNTAX INTEGER {
        none(1),
        ip(2),
        serial(3),
        serialDirect(4),
        serialFrameRelay(5),
        serialLLC2(6)
        }
    ACCESS read-only
    STATUS mandatory
    DESCRIPTION
        "The type of identification of the remote default partner. 
         (This is as configured with the 'route all' command.)
         If ip then the value is in bstunPortDefaultPeerIP; if serial or
         serialDirect then the value is in bstunPortDefaultPeerSerial."
    ::= { bstunPortEntry 2 }

bstunPortDefaultPeerIP OBJECT-TYPE
    SYNTAX IpAddress
    ACCESS read-only
    STATUS mandatory
    DESCRIPTION
        "The ip address of the remote default BSTUN partner,
         for unrecognized addresses. 
         0.0.0.0 if partner address type is not ip."
    ::= { bstunPortEntry 3 }

bstunPortDefaultPeerSerial OBJECT-TYPE
    SYNTAX InterfaceIndex
--    Rsyntax INTEGER(1..2147483647)
    ACCESS read-only
    STATUS mandatory
    DESCRIPTION
        "If bstunRouteType is serial then this is the 
         serial interface index of the point-to-point
         link to the remote partner; 
         if bstunRouteType is serialDirect then the 
         partner is in the local BSTUN.
         if bstunRouteType is ip then this field is
         0."
    ::= { bstunPortEntry 4 }

bstunRouteTable OBJECT-TYPE
    SYNTAX SEQUENCE OF BstunRouteEntry
    ACCESS not-accessible
    STATUS mandatory
    DESCRIPTION
        "A table containing information about specific poll
         addresses.  There is one table entry for each 
         address configured by the BSTUN ROUTE command."
    ::= { bstunRoutes 1 }

bstunRouteEntry OBJECT-TYPE
    SYNTAX BstunRouteEntry
    ACCESS not-accessible
    STATUS mandatory
    DESCRIPTION
        "The information regarding a single poll address."
    INDEX { bstunRouteGroupIndex, bstunRouteStationAddress }
    ::= { bstunRouteTable 1 }

BstunRouteEntry ::= SEQUENCE {
    bstunRouteGroupIndex INTEGER,
    bstunRouteStationAddress INTEGER,
    bstunRouteType INTEGER,
    bstunRouteIP IpAddress,
    bstunRouteSerial InterfaceIndex,
    bstunRoutePriority INTEGER,
    bstunRoutePeerState INTEGER,
    bstunRouteRxPackets Counter,
    bstunRouteTxPackets Counter,
    bstunRouteRxBytes Counter,
    bstunRouteTxBytes Counter,
    bstunRouteDLCI INTEGER,
    bstunRouteRSAP INTEGER,
    bstunLLC2Priority INTEGER,
    bstunRouteBIPPassive TruthValue,
    bstunRouteBIPLocalPort INTEGER,
    bstunRouteBIPForeignPort INTEGER,
    bstunRouteBIPDeviceStatus OCTET STRING
    }

bstunRouteGroupIndex OBJECT-TYPE
    SYNTAX INTEGER(1..255)
    ACCESS not-accessible
    STATUS mandatory
    DESCRIPTION
        "The index of the BSTUN Group owning this 
         station."
    ::= { bstunRouteEntry 1 }

bstunRouteStationAddress OBJECT-TYPE
    SYNTAX INTEGER(1..256)
    ACCESS not-accessible
    STATUS mandatory
    DESCRIPTION
        "The poll address of the station.  256 indicates the ALL parameter
         on the STUN ROUTE command, which is the route for all 
         unrecognized addresses."
    ::= { bstunRouteEntry 2 }

bstunRouteType OBJECT-TYPE
    SYNTAX INTEGER {
        none(1),
        ip(2),
        serial(3),
        serialDirect(4),
        serialFrameRelay(5),
        serialLLC2(6),
        bip(7)
        }
    ACCESS read-only
    STATUS mandatory
    DESCRIPTION
        "The type of identification of the remote partner.
         If ip then the value is in bstunRouteIP; if serial or
         serialDirect then the value is in bstunRouteSerial; if bip 
         then the value is in bstunRouteIP, bstunRouteBIPLocalPort 
         and bstunRouteBIPForeignPort."
    ::= { bstunRouteEntry 3 }

bstunRouteIP OBJECT-TYPE
    SYNTAX IpAddress
    ACCESS read-only
    STATUS mandatory
    DESCRIPTION
        "The ip address of the remote BSTUN partner. 
         0.0.0.0 if partner address type is not ip."
    ::= { bstunRouteEntry 4 }

bstunRouteSerial OBJECT-TYPE
    SYNTAX InterfaceIndex
--    Rsyntax INTEGER(1..2147483647)
    ACCESS read-only
    STATUS mandatory
    DESCRIPTION
        "If bstunRouteType is serial then this is the 
         serial interface index of the point-to-point
         link to the remote partner; 
         if bstunRouteType is serialDirect then the 
         partner is in the local BSTUN.
         if bstunRouteType is ip then this field is
         0."
    ::= { bstunRouteEntry 5 }

bstunRoutePriority OBJECT-TYPE
    SYNTAX INTEGER {
        low(1),
        normal(2),
        medium(3),
        high(4)
        }
    ACCESS read-only
    STATUS mandatory
    DESCRIPTION
        "The priority with which this station's traffic will
         be routed across the network."
    ::= { bstunRouteEntry 6 }

bstunRoutePeerState OBJECT-TYPE
    SYNTAX INTEGER {
        dead(1),
        closed(2),
        opening(3),
        openWait(4),
        connected(5),
        direct(6)
        }
    ACCESS read-only
    STATUS mandatory
    DESCRIPTION
        "The state of the peer connection through the
         BSTUN tunnel."
    ::= { bstunRouteEntry 7 }

bstunRouteRxPackets OBJECT-TYPE
    SYNTAX Counter
    ACCESS read-only
    STATUS mandatory
    DESCRIPTION
        "Count of frames received from the serial
         interface with this station's address."
    ::= { bstunRouteEntry 8 }

bstunRouteTxPackets OBJECT-TYPE
    SYNTAX Counter
    ACCESS read-only
    STATUS mandatory
    DESCRIPTION
        "Count of frames transmitted at the serial
         interface with this station's address."
    ::= { bstunRouteEntry 9 }

bstunRouteRxBytes OBJECT-TYPE
    SYNTAX Counter
    ACCESS read-only
    STATUS mandatory
    DESCRIPTION
        "Count of bytes received from the serial
         interface with this station's address."
    ::= { bstunRouteEntry 10 }

bstunRouteTxBytes OBJECT-TYPE
    SYNTAX Counter
    ACCESS read-only
    STATUS mandatory
    DESCRIPTION
        "Count of bytes transmitted at the serial
         interface with this station's address."
    ::= { bstunRouteEntry 11 }

bstunRouteDLCI OBJECT-TYPE
    SYNTAX INTEGER(16..1007)
    ACCESS read-only
    STATUS mandatory
    DESCRIPTION
        "If bstunRouteType is serialFrameRelay or serialLLC2
         then this is the frame relay dlci circuit used for 
         the point-to-point link to the remote partner; 
         if bstunRouteType is ip or serial then this field is
         0."
    ::= { bstunRouteEntry 12 }

bstunRouteRSAP OBJECT-TYPE
    SYNTAX INTEGER(1..255)
    ACCESS read-only
    STATUS mandatory
    DESCRIPTION
        "If bstunRouteType is serialLLC2 then this 
         is the llc2 sap value used for the point-to-point
         link to the remote partner; 
         if bstunRouteType is ip or serial or serialFrameRelay
         then this field is 0."
    ::= { bstunRouteEntry 13 }

bstunLLC2Priority OBJECT-TYPE
    SYNTAX INTEGER(1..10)
    ACCESS read-only
    STATUS mandatory
    DESCRIPTION
        "If bstunRouteType is serialLLC2 then this 
         is the llc2 priority used for the point-to-point
         link to the remote partner; 
         if bstunRouteType is ip or serial or serialFrameRelay
         then this field is 0."
    ::= { bstunRouteEntry 14 }

bstunRouteBIPPassive OBJECT-TYPE
    SYNTAX TruthValue
--    Rsyntax INTEGER {
--        true(1),
--        false(2)
--        }
    ACCESS read-only
    STATUS mandatory
    DESCRIPTION
        "Specifies whether the bip peer will wait for an inbound connection 
                or actively connect to the remote peer."
    DEFVAL { false }
    ::= { bstunRouteEntry 15 }

bstunRouteBIPLocalPort OBJECT-TYPE
    SYNTAX INTEGER(1025..32000)
    ACCESS read-only
    STATUS mandatory
    DESCRIPTION
        "If bstunRouteType is bip then this is the local port used when 
         connecting to the remote peer."
    ::= { bstunRouteEntry 16 }

bstunRouteBIPForeignPort OBJECT-TYPE
    SYNTAX INTEGER(1025..32000)
    ACCESS read-only
    STATUS mandatory
    DESCRIPTION
        "If bstunRouteType is bip then this is the for port used to 
         connect to the remote peer."
    ::= { bstunRouteEntry 17 }

bstunRouteBIPDeviceStatus OBJECT-TYPE
    SYNTAX OCTET STRING(SIZE(1..2))
        -- BITS are:
        --   operationcheck(0)
        --   reservedBit1(1)
        --   datacheck(2)
        --   equipmentcheck(3)
        --   interventionrequired(4)
        --   commandreject(5)
        --   deviceinactive(6)
        --   deviceactive(7)
        --   reservedBit8(8)
        --   deviceend(9)
        --   unitspecify(10)
        --   devicebusy(11)
    ACCESS read-only
    STATUS mandatory
    DESCRIPTION
        "If bstunRouteType is bip then this indicates the OR bit mask
          status of the mapped bisync device:
                            
                            if no bits are set, indicates that the 
                            bisync device is up and operational.        
              Bit 0, if set, indicates that the bisync device is
                            reporting  an operation check error.
                     Bit 2, if set, indicates that the bisync device is
                            reporting  a data check error.
                     Bit 3, if set, indicates that the bisync device is
                            reporting  an equipment check error.
                     Bit 4, if set, indicates that the bisync device is
                            reporting  that intervention is required.
                     Bit 5, if set, indicates that the bisync device is
                            reporting  that a command has been rejected.
                     Bit 6, if set, indicates that the bisync device is
                            not responding to polls.
                     Bit 7, if set, indicates that the bisync device is
                            now responding to polls and is operational.
                     Bit 9, if set, indicates that the bisync device is
                            reporting  that is no longer busy.
                     Bit 10, if set, indicates that the bisync device is
                             reporting  a device unit specify.
                     Bit 11, if set, indicates that the bisync device is
                             reporting  a busy condition."
    ::= { bstunRouteEntry 18 }

bstunPeerStateChangeNotification TRAP-TYPE
-- Reverse mappable trap
    ENTERPRISE bstunNotificationPrefix
    VARIABLES {
        bstunRoutePeerState }
--  Status
--    deprecated
    DESCRIPTION
        "This notification indicates that the state of a BSTUN route
         has transitioned to active (connected) or inactive
         (dead or closed)."
    ::= 1

bstunPeerStateChangeNotification2 TRAP-TYPE
-- Reverse mappable trap
    ENTERPRISE bstunNotificationPrefix
    VARIABLES {
        bstunRoutePeerState, bstunRouteType, bstunRouteRxPackets, 
        bstunRouteTxPackets }
--  Status
--    mandatory
    DESCRIPTION
        "This notification indicates that the state of a BSTUN route
         has transitioned to active (connected) or inactive
         (dead or closed)."
    ::= 2

bstunCUStatusChangeNotification TRAP-TYPE
-- Reverse mappable trap
    ENTERPRISE bstunNotificationPrefix
    VARIABLES {
        bstunRouteIP, bstunRouteBIPForeignPort, 
        bstunRouteBIPLocalPort, bstunRouteBIPDeviceStatus }
--  Status
--    mandatory
    DESCRIPTION
        "This notification is generated when a mapped BIP bisync 
         device state has changed."
    ::= 3

bstunGlobalGroup OBJECT IDENTIFIER ::= { bstunMibGroups 1 }
-- OBJECT-GROUP
--  Status
--    obsolete
--  Descr
--    A collection of objects providing global BSTUN information.
--  objects
--    bstunIPAddr

bstunGroupGroup OBJECT IDENTIFIER ::= { bstunMibGroups 2 }
-- OBJECT-GROUP
--  Status
--    mandatory
--  Descr
--    A collection of objects providing information about 
--     BSTUN groups .
--  objects
--    bstunProtocolType, bstunLocalAck, 
--    bstunGroupUnroutableTransmit, bstunGroupUnroutableReceive

bstunPortGroup OBJECT IDENTIFIER ::= { bstunMibGroups 3 }
-- OBJECT-GROUP
--  Status
--    mandatory
--  Descr
--    A collection of objects providing information about
--     BSTUN enabled interfaces.
--  objects
--    bstunPortGroupNumber, bstunPortDefaultPeerType, 
--    bstunPortDefaultPeerIP, bstunPortDefaultPeerSerial

bstunRouteGroup OBJECT IDENTIFIER ::= { bstunMibGroups 4 }
-- OBJECT-GROUP
--  Status
--    obsolete
--  Descr
--    A collection of objects providing information about
--     BSTUN defined routes.
--  objects
--    bstunRouteType, bstunRouteIP, bstunRouteSerial, 
--    bstunRoutePriority, bstunRoutePeerState, bstunRouteRxPackets, 
--    bstunRouteTxPackets, bstunRouteRxBytes, bstunRouteTxBytes

bstunGlobalGroupRev1 OBJECT IDENTIFIER ::= { bstunMibGroups 5 }
-- OBJECT-GROUP
--  Status
--    mandatory
--  Descr
--    A collection of objects providing global BSTUN information.
--  objects
--    bstunIPAddr, bstunLisnSap, bstunPeerKeepaliveInterval, 
--    bstunPeerKeepaliveLimit

bstunRouteGroupRev1 OBJECT IDENTIFIER ::= { bstunMibGroups 6 }
-- OBJECT-GROUP
--  Status
--    deprecated
--  Descr
--    A collection of objects providing information about
--     BSTUN defined routes.
--  objects
--    bstunRouteType, bstunRouteIP, bstunRouteSerial, 
--    bstunRoutePriority, bstunRoutePeerState, bstunRouteRxPackets, 
--    bstunRouteTxPackets, bstunRouteRxBytes, bstunRouteTxBytes, 
--    bstunRouteDLCI, bstunRouteRSAP, bstunLLC2Priority

bstunRouteGroupRev2 OBJECT IDENTIFIER ::= { bstunMibGroups 7 }
-- OBJECT-GROUP
--  Status
--    mandatory
--  Descr
--    A collection of objects providing information about
--     BSTUN defined routes.
--  objects
--    bstunRouteType, bstunRouteIP, bstunRouteSerial, 
--    bstunRoutePriority, bstunRoutePeerState, bstunRouteRxPackets, 
--    bstunRouteTxPackets, bstunRouteRxBytes, bstunRouteTxBytes, 
--    bstunRouteDLCI, bstunRouteRSAP, bstunLLC2Priority, 
--    bstunRouteBIPPassive, bstunRouteBIPLocalPort, 
--    bstunRouteBIPForeignPort, bstunRouteBIPDeviceStatus

bstunNotificationGroup OBJECT IDENTIFIER ::= { bstunMibGroups 8 }
-- NOTIFICATION-GROUP
--  Status
--    deprecated
--  Descr
--    A collection of notifications. 
--  notifications
--    bstunPeerStateChangeNotification

bstunNotificationGroupRev1 OBJECT IDENTIFIER ::= { bstunMibGroups 9 }
-- NOTIFICATION-GROUP
--  Status
--    mandatory
--  Descr
--    A collection of notifications. 
--  notifications
--    bstunPeerStateChangeNotification2, 
--    bstunCUStatusChangeNotification

bstunMibCompliance OBJECT IDENTIFIER ::= { bstunMibCompliances 1 }
-- MODULE-COMPLIANCE
--  Status
--    obsolete
--  Descr
--    The compliance statement for BSTUN.
--  Module
--    >>current<<
--   MandGroup
--    bstunGlobalGroup
--   MandGroup
--    bstunGroupGroup
--   MandGroup
--    bstunPortGroup
--   MandGroup
--    bstunRouteGroup

bstunMibComplianceRev1 OBJECT IDENTIFIER ::= { bstunMibCompliances 2 }
-- MODULE-COMPLIANCE
--  Status
--    deprecated
--  Descr
--    The compliance statement for all Cisco systems that 
--    implement  BSTUN functions.
--  Module
--    >>current<<
--   MandGroup
--    bstunGlobalGroupRev1
--   MandGroup
--    bstunGroupGroup
--   MandGroup
--    bstunPortGroup
--   MandGroup
--    bstunRouteGroupRev1

bstunMibComplianceRev2 OBJECT IDENTIFIER ::= { bstunMibCompliances 3 }
-- MODULE-COMPLIANCE
--  Status
--    mandatory
--  Descr
--    The compliance statement for all Cisco systems that 
--    implement  BSTUN functions.
--  Module
--    >>current<<
--   MandGroup
--    bstunGlobalGroupRev1
--   MandGroup
--    bstunGroupGroup
--   MandGroup
--    bstunPortGroup
--   MandGroup
--    bstunRouteGroupRev2
--   MandGroup
--    bstunNotificationGroupRev1


END
