-- MIB file created 05-Sep-2006 11:40:46, by
--   SMICng version 2.2.11-beta(PRO)(Solaris), January 20, 2001. Enterprise key cisco.com

CISCO-PRODUCTS-MIB DEFINITIONS ::= BEGIN

-- From file: "CISCO-PRODUCTS-MIB.my"
-- Compile options "4 7 F H N O W 03 06 0B 0G 0N 0T"

IMPORTS
    ciscoModules, ciscoProducts
            FROM CISCO-SMI;

ciscoProductsMIB OBJECT IDENTIFIER ::= { ciscoModules 2 }
-- MODULE-IDENTITY
--  LastUpdated
--    200505051930Z
--  OrgName
--    Cisco Systems, Inc.
--  ContactInfo
--           Cisco Systems
--     Customer Service
--    
--    Postal: 170 W Tasman Drive
--     San Jose, CA  95134
--     USA
--    
--       Tel: +1 800 553-NETS
--    
--    E-mail: cs-snmp@cisco.com
--  Descr
--    This module defines the object identifiers that are
--    assigned to various hardware platforms, and hence are
--    returned as values for sysObjectID
--  RevDate
--    200505051930Z
--  RevDescr
--    Added following OIDs:
--    ciscoMPX, ciscoNMCUEEC, ciscoWLSE1132, 
--    ciscoME6340ACA, ciscoME6340DCA,
--    ciscoME6340DCA, catalyst296024TT,
--    catalyst296048TT
--  RevDate
--    200504201930Z
--  RevDescr
--    Removed DNP of catalyst6kGateway
--  RevDate
--    200504181930Z
--  RevDescr
--    Added following OIDs:
--    ciscoNme16Es1GeNoPwr, ciscoNmeX24Es1GeNoPwr,
--    ciscoNmeXd24Es2StNoPwr, ciscoNmeXd48Es2GeNoPwr,
--    catalyst6kMsfc2a, ciscoEDI, ciscoCe611K9,
--    ciscoWLSEs20.
--  RevDate
--    200204051400Z
--  RevDescr
--    CANA Assignments.
--  RevDate
--    9505310000Z
--  RevDescr
--    Miscellaneous updates.

ciscoGatewayServer OBJECT IDENTIFIER ::= { ciscoProducts 1 }
ciscoTerminalServer OBJECT IDENTIFIER ::= { ciscoProducts 2 }
ciscoTrouter    OBJECT IDENTIFIER ::= { ciscoProducts 3 }
ciscoProtocolTranslator OBJECT IDENTIFIER ::= { ciscoProducts 4 }
ciscoIGS        OBJECT IDENTIFIER ::= { ciscoProducts 5 }
cisco3000       OBJECT IDENTIFIER ::= { ciscoProducts 6 }
cisco4000       OBJECT IDENTIFIER ::= { ciscoProducts 7 }
cisco7000       OBJECT IDENTIFIER ::= { ciscoProducts 8 }
ciscoCS500      OBJECT IDENTIFIER ::= { ciscoProducts 9 }
cisco2000       OBJECT IDENTIFIER ::= { ciscoProducts 10 }
ciscoAGSplus    OBJECT IDENTIFIER ::= { ciscoProducts 11 }
cisco7010       OBJECT IDENTIFIER ::= { ciscoProducts 12 }
cisco2500       OBJECT IDENTIFIER ::= { ciscoProducts 13 }
cisco4500       OBJECT IDENTIFIER ::= { ciscoProducts 14 }
cisco2102       OBJECT IDENTIFIER ::= { ciscoProducts 15 }
cisco2202       OBJECT IDENTIFIER ::= { ciscoProducts 16 }
cisco2501       OBJECT IDENTIFIER ::= { ciscoProducts 17 }
cisco2502       OBJECT IDENTIFIER ::= { ciscoProducts 18 }
cisco2503       OBJECT IDENTIFIER ::= { ciscoProducts 19 }
cisco2504       OBJECT IDENTIFIER ::= { ciscoProducts 20 }
cisco2505       OBJECT IDENTIFIER ::= { ciscoProducts 21 }
cisco2506       OBJECT IDENTIFIER ::= { ciscoProducts 22 }
cisco2507       OBJECT IDENTIFIER ::= { ciscoProducts 23 }
cisco2508       OBJECT IDENTIFIER ::= { ciscoProducts 24 }
cisco2509       OBJECT IDENTIFIER ::= { ciscoProducts 25 }
cisco2510       OBJECT IDENTIFIER ::= { ciscoProducts 26 }
cisco2511       OBJECT IDENTIFIER ::= { ciscoProducts 27 }
cisco2512       OBJECT IDENTIFIER ::= { ciscoProducts 28 }
cisco2513       OBJECT IDENTIFIER ::= { ciscoProducts 29 }
cisco2514       OBJECT IDENTIFIER ::= { ciscoProducts 30 }
cisco2515       OBJECT IDENTIFIER ::= { ciscoProducts 31 }
cisco3101       OBJECT IDENTIFIER ::= { ciscoProducts 32 }
cisco3102       OBJECT IDENTIFIER ::= { ciscoProducts 33 }
cisco3103       OBJECT IDENTIFIER ::= { ciscoProducts 34 }
cisco3104       OBJECT IDENTIFIER ::= { ciscoProducts 35 }
cisco3202       OBJECT IDENTIFIER ::= { ciscoProducts 36 }
cisco3204       OBJECT IDENTIFIER ::= { ciscoProducts 37 }
ciscoAccessProRC OBJECT IDENTIFIER ::= { ciscoProducts 38 }
ciscoAccessProEC OBJECT IDENTIFIER ::= { ciscoProducts 39 }
cisco1000       OBJECT IDENTIFIER ::= { ciscoProducts 40 }
cisco1003       OBJECT IDENTIFIER ::= { ciscoProducts 41 }
cisco2516       OBJECT IDENTIFIER ::= { ciscoProducts 42 }
cisco1020       OBJECT IDENTIFIER ::= { ciscoProducts 43 }
cisco1004       OBJECT IDENTIFIER ::= { ciscoProducts 44 }
cisco7507       OBJECT IDENTIFIER ::= { ciscoProducts 45 }
cisco7513       OBJECT IDENTIFIER ::= { ciscoProducts 46 }
cisco7506       OBJECT IDENTIFIER ::= { ciscoProducts 47 }
cisco7505       OBJECT IDENTIFIER ::= { ciscoProducts 48 }
cisco1005       OBJECT IDENTIFIER ::= { ciscoProducts 49 }
cisco4700       OBJECT IDENTIFIER ::= { ciscoProducts 50 }
ciscoPro1003    OBJECT IDENTIFIER ::= { ciscoProducts 51 }
ciscoPro1004    OBJECT IDENTIFIER ::= { ciscoProducts 52 }
ciscoPro1005    OBJECT IDENTIFIER ::= { ciscoProducts 53 }
ciscoPro1020    OBJECT IDENTIFIER ::= { ciscoProducts 54 }
ciscoPro2500PCE OBJECT IDENTIFIER ::= { ciscoProducts 55 }
ciscoPro2501    OBJECT IDENTIFIER ::= { ciscoProducts 56 }
ciscoPro2503    OBJECT IDENTIFIER ::= { ciscoProducts 57 }
ciscoPro2505    OBJECT IDENTIFIER ::= { ciscoProducts 58 }
ciscoPro2507    OBJECT IDENTIFIER ::= { ciscoProducts 59 }
ciscoPro2509    OBJECT IDENTIFIER ::= { ciscoProducts 60 }
ciscoPro2511    OBJECT IDENTIFIER ::= { ciscoProducts 61 }
ciscoPro2514    OBJECT IDENTIFIER ::= { ciscoProducts 62 }
ciscoPro2516    OBJECT IDENTIFIER ::= { ciscoProducts 63 }
ciscoPro2519    OBJECT IDENTIFIER ::= { ciscoProducts 64 }
ciscoPro2521    OBJECT IDENTIFIER ::= { ciscoProducts 65 }
ciscoPro4500    OBJECT IDENTIFIER ::= { ciscoProducts 66 }
cisco2517       OBJECT IDENTIFIER ::= { ciscoProducts 67 }
cisco2518       OBJECT IDENTIFIER ::= { ciscoProducts 68 }
cisco2519       OBJECT IDENTIFIER ::= { ciscoProducts 69 }
cisco2520       OBJECT IDENTIFIER ::= { ciscoProducts 70 }
cisco2521       OBJECT IDENTIFIER ::= { ciscoProducts 71 }
cisco2522       OBJECT IDENTIFIER ::= { ciscoProducts 72 }
cisco2523       OBJECT IDENTIFIER ::= { ciscoProducts 73 }
cisco2524       OBJECT IDENTIFIER ::= { ciscoProducts 74 }
cisco2525       OBJECT IDENTIFIER ::= { ciscoProducts 75 }
ciscoPro751     OBJECT IDENTIFIER ::= { ciscoProducts 76 }
ciscoPro752     OBJECT IDENTIFIER ::= { ciscoProducts 77 }
ciscoPro753     OBJECT IDENTIFIER ::= { ciscoProducts 78 }
cisco751        OBJECT IDENTIFIER ::= { ciscoProducts 81 }
cisco752        OBJECT IDENTIFIER ::= { ciscoProducts 82 }
cisco753        OBJECT IDENTIFIER ::= { ciscoProducts 83 }
ciscoPro741     OBJECT IDENTIFIER ::= { ciscoProducts 84 }
ciscoPro742     OBJECT IDENTIFIER ::= { ciscoProducts 85 }
ciscoPro743     OBJECT IDENTIFIER ::= { ciscoProducts 86 }
ciscoPro744     OBJECT IDENTIFIER ::= { ciscoProducts 87 }
ciscoPro761     OBJECT IDENTIFIER ::= { ciscoProducts 88 }
ciscoPro762     OBJECT IDENTIFIER ::= { ciscoProducts 89 }
ciscoPro765     OBJECT IDENTIFIER ::= { ciscoProducts 92 }
ciscoPro766     OBJECT IDENTIFIER ::= { ciscoProducts 93 }
cisco741        OBJECT IDENTIFIER ::= { ciscoProducts 94 }
cisco742        OBJECT IDENTIFIER ::= { ciscoProducts 95 }
cisco743        OBJECT IDENTIFIER ::= { ciscoProducts 96 }
cisco744        OBJECT IDENTIFIER ::= { ciscoProducts 97 }
cisco761        OBJECT IDENTIFIER ::= { ciscoProducts 98 }
cisco762        OBJECT IDENTIFIER ::= { ciscoProducts 99 }
cisco765        OBJECT IDENTIFIER ::= { ciscoProducts 102 }
cisco766        OBJECT IDENTIFIER ::= { ciscoProducts 103 }
ciscoPro2520    OBJECT IDENTIFIER ::= { ciscoProducts 104 }
ciscoPro2522    OBJECT IDENTIFIER ::= { ciscoProducts 105 }
ciscoPro2524    OBJECT IDENTIFIER ::= { ciscoProducts 106 }
ciscoLS1010     OBJECT IDENTIFIER ::= { ciscoProducts 107 }
cisco7206       OBJECT IDENTIFIER ::= { ciscoProducts 108 }
ciscoAS5200     OBJECT IDENTIFIER ::= { ciscoProducts 109 }
cisco3640       OBJECT IDENTIFIER ::= { ciscoProducts 110 }
ciscoCatalyst3500 OBJECT IDENTIFIER ::= { ciscoProducts 111 }
ciscoWSX3011    OBJECT IDENTIFIER ::= { ciscoProducts 112 }
cisco1601       OBJECT IDENTIFIER ::= { ciscoProducts 113 }
cisco1602       OBJECT IDENTIFIER ::= { ciscoProducts 114 }
cisco1603       OBJECT IDENTIFIER ::= { ciscoProducts 115 }
cisco1604       OBJECT IDENTIFIER ::= { ciscoProducts 116 }
ciscoPro1601    OBJECT IDENTIFIER ::= { ciscoProducts 117 }
ciscoPro1602    OBJECT IDENTIFIER ::= { ciscoProducts 118 }
ciscoPro1603    OBJECT IDENTIFIER ::= { ciscoProducts 119 }
ciscoPro1604    OBJECT IDENTIFIER ::= { ciscoProducts 120 }
cisco3620       OBJECT IDENTIFIER ::= { ciscoProducts 122 }
ciscoPro3620    OBJECT IDENTIFIER ::= { ciscoProducts 123 }
ciscoPro3640    OBJECT IDENTIFIER ::= { ciscoProducts 124 }
cisco7204       OBJECT IDENTIFIER ::= { ciscoProducts 125 }
cisco771        OBJECT IDENTIFIER ::= { ciscoProducts 126 }
cisco772        OBJECT IDENTIFIER ::= { ciscoProducts 127 }
cisco775        OBJECT IDENTIFIER ::= { ciscoProducts 128 }
cisco776        OBJECT IDENTIFIER ::= { ciscoProducts 129 }
ciscoPro2502    OBJECT IDENTIFIER ::= { ciscoProducts 130 }
ciscoPro2504    OBJECT IDENTIFIER ::= { ciscoProducts 131 }
ciscoPro2506    OBJECT IDENTIFIER ::= { ciscoProducts 132 }
ciscoPro2508    OBJECT IDENTIFIER ::= { ciscoProducts 133 }
ciscoPro2510    OBJECT IDENTIFIER ::= { ciscoProducts 134 }
ciscoPro2512    OBJECT IDENTIFIER ::= { ciscoProducts 135 }
ciscoPro2513    OBJECT IDENTIFIER ::= { ciscoProducts 136 }
ciscoPro2515    OBJECT IDENTIFIER ::= { ciscoProducts 137 }
ciscoPro2517    OBJECT IDENTIFIER ::= { ciscoProducts 138 }
ciscoPro2518    OBJECT IDENTIFIER ::= { ciscoProducts 139 }
ciscoPro2523    OBJECT IDENTIFIER ::= { ciscoProducts 140 }
ciscoPro2525    OBJECT IDENTIFIER ::= { ciscoProducts 141 }
ciscoPro4700    OBJECT IDENTIFIER ::= { ciscoProducts 142 }
ciscoPro316T    OBJECT IDENTIFIER ::= { ciscoProducts 147 }
ciscoPro316C    OBJECT IDENTIFIER ::= { ciscoProducts 148 }
ciscoPro3116    OBJECT IDENTIFIER ::= { ciscoProducts 149 }
catalyst116T    OBJECT IDENTIFIER ::= { ciscoProducts 150 }
catalyst116C    OBJECT IDENTIFIER ::= { ciscoProducts 151 }
catalyst1116    OBJECT IDENTIFIER ::= { ciscoProducts 152 }
ciscoAS2509RJ   OBJECT IDENTIFIER ::= { ciscoProducts 153 }
ciscoAS2511RJ   OBJECT IDENTIFIER ::= { ciscoProducts 154 }
ciscoMC3810     OBJECT IDENTIFIER ::= { ciscoProducts 157 }
cisco1503       OBJECT IDENTIFIER ::= { ciscoProducts 160 }
cisco1502       OBJECT IDENTIFIER ::= { ciscoProducts 161 }
ciscoAS5300     OBJECT IDENTIFIER ::= { ciscoProducts 162 }
ciscoLS1015     OBJECT IDENTIFIER ::= { ciscoProducts 164 }
cisco2501FRADFX OBJECT IDENTIFIER ::= { ciscoProducts 165 }
cisco2501LANFRADFX OBJECT IDENTIFIER ::= { ciscoProducts 166 }
cisco2502LANFRADFX OBJECT IDENTIFIER ::= { ciscoProducts 167 }
ciscoWSX5302    OBJECT IDENTIFIER ::= { ciscoProducts 168 }
ciscoFastHub216T OBJECT IDENTIFIER ::= { ciscoProducts 169 }
catalyst2908xl  OBJECT IDENTIFIER ::= { ciscoProducts 170 }
catalyst2916m-xl OBJECT IDENTIFIER ::= { ciscoProducts 171 }
cisco1605       OBJECT IDENTIFIER ::= { ciscoProducts 172 }
cisco12012      OBJECT IDENTIFIER ::= { ciscoProducts 173 }
catalyst1912C   OBJECT IDENTIFIER ::= { ciscoProducts 175 }
ciscoMicroWebServer2 OBJECT IDENTIFIER ::= { ciscoProducts 176 }
ciscoFastHubBMMTX OBJECT IDENTIFIER ::= { ciscoProducts 177 }
ciscoFastHubBMMFX OBJECT IDENTIFIER ::= { ciscoProducts 178 }
ciscoUBR7246    OBJECT IDENTIFIER ::= { ciscoProducts 179 }
cisco6400       OBJECT IDENTIFIER ::= { ciscoProducts 180 }
cisco12004      OBJECT IDENTIFIER ::= { ciscoProducts 181 }
cisco12008      OBJECT IDENTIFIER ::= { ciscoProducts 182 }
catalyst2924XL  OBJECT IDENTIFIER ::= { ciscoProducts 183 }
catalyst2924CXL OBJECT IDENTIFIER ::= { ciscoProducts 184 }
cisco2610       OBJECT IDENTIFIER ::= { ciscoProducts 185 }
cisco2611       OBJECT IDENTIFIER ::= { ciscoProducts 186 }
cisco2612       OBJECT IDENTIFIER ::= { ciscoProducts 187 }
ciscoAS5800     OBJECT IDENTIFIER ::= { ciscoProducts 188 }
ciscoSC3640     OBJECT IDENTIFIER ::= { ciscoProducts 189 }
cisco8510       OBJECT IDENTIFIER ::= { ciscoProducts 190 }
ciscoUBR904     OBJECT IDENTIFIER ::= { ciscoProducts 191 }
cisco6200       OBJECT IDENTIFIER ::= { ciscoProducts 192 }
cisco7202       OBJECT IDENTIFIER ::= { ciscoProducts 194 }
cisco2613       OBJECT IDENTIFIER ::= { ciscoProducts 195 }
cisco8515       OBJECT IDENTIFIER ::= { ciscoProducts 196 }
catalyst9006    OBJECT IDENTIFIER ::= { ciscoProducts 197 }
catalyst9009    OBJECT IDENTIFIER ::= { ciscoProducts 198 }
ciscoRPM        OBJECT IDENTIFIER ::= { ciscoProducts 199 }
cisco1710       OBJECT IDENTIFIER ::= { ciscoProducts 200 }
cisco1720       OBJECT IDENTIFIER ::= { ciscoProducts 201 }
catalyst8540msr OBJECT IDENTIFIER ::= { ciscoProducts 202 }
catalyst8540csr OBJECT IDENTIFIER ::= { ciscoProducts 203 }
cisco7576       OBJECT IDENTIFIER ::= { ciscoProducts 204 }
cisco3660       OBJECT IDENTIFIER ::= { ciscoProducts 205 }
cisco1401       OBJECT IDENTIFIER ::= { ciscoProducts 206 }
cisco2620       OBJECT IDENTIFIER ::= { ciscoProducts 208 }
cisco2621       OBJECT IDENTIFIER ::= { ciscoProducts 209 }
ciscoUBR7223    OBJECT IDENTIFIER ::= { ciscoProducts 210 }
cisco6400Nrp    OBJECT IDENTIFIER ::= { ciscoProducts 211 }
cisco801        OBJECT IDENTIFIER ::= { ciscoProducts 212 }
cisco802        OBJECT IDENTIFIER ::= { ciscoProducts 213 }
cisco803        OBJECT IDENTIFIER ::= { ciscoProducts 214 }
cisco804        OBJECT IDENTIFIER ::= { ciscoProducts 215 }
cisco1750       OBJECT IDENTIFIER ::= { ciscoProducts 216 }
catalyst2924XLv OBJECT IDENTIFIER ::= { ciscoProducts 217 }
catalyst2924CXLv OBJECT IDENTIFIER ::= { ciscoProducts 218 }
catalyst2912XL  OBJECT IDENTIFIER ::= { ciscoProducts 219 }
catalyst2924MXL OBJECT IDENTIFIER ::= { ciscoProducts 220 }
catalyst2912MfXL OBJECT IDENTIFIER ::= { ciscoProducts 221 }
cisco7206VXR    OBJECT IDENTIFIER ::= { ciscoProducts 222 }
cisco7204VXR    OBJECT IDENTIFIER ::= { ciscoProducts 223 }
cisco1538M      OBJECT IDENTIFIER ::= { ciscoProducts 224 }
cisco1548M      OBJECT IDENTIFIER ::= { ciscoProducts 225 }
ciscoFasthub100 OBJECT IDENTIFIER ::= { ciscoProducts 226 }
ciscoPIXFirewall OBJECT IDENTIFIER ::= { ciscoProducts 227 }
ciscoMGX8850    OBJECT IDENTIFIER ::= { ciscoProducts 228 }
ciscoMGX8830    OBJECT IDENTIFIER ::= { ciscoProducts 229 }
catalyst8510msr OBJECT IDENTIFIER ::= { ciscoProducts 230 }
catalyst8515msr OBJECT IDENTIFIER ::= { ciscoProducts 231 }
ciscoIGX8410    OBJECT IDENTIFIER ::= { ciscoProducts 232 }
ciscoIGX8420    OBJECT IDENTIFIER ::= { ciscoProducts 233 }
ciscoIGX8430    OBJECT IDENTIFIER ::= { ciscoProducts 234 }
ciscoIGX8450    OBJECT IDENTIFIER ::= { ciscoProducts 235 }
ciscoBPX8620    OBJECT IDENTIFIER ::= { ciscoProducts 237 }
ciscoBPX8650    OBJECT IDENTIFIER ::= { ciscoProducts 238 }
ciscoBPX8680    OBJECT IDENTIFIER ::= { ciscoProducts 239 }
ciscoCacheEngine OBJECT IDENTIFIER ::= { ciscoProducts 240 }
ciscoCat6000    OBJECT IDENTIFIER ::= { ciscoProducts 241 }
ciscoBPXSes     OBJECT IDENTIFIER ::= { ciscoProducts 242 }
ciscoIGXSes     OBJECT IDENTIFIER ::= { ciscoProducts 243 }
ciscoLocalDirector OBJECT IDENTIFIER ::= { ciscoProducts 244 }
cisco805        OBJECT IDENTIFIER ::= { ciscoProducts 245 }
catalyst3508GXL OBJECT IDENTIFIER ::= { ciscoProducts 246 }
catalyst3512XL  OBJECT IDENTIFIER ::= { ciscoProducts 247 }
catalyst3524XL  OBJECT IDENTIFIER ::= { ciscoProducts 248 }
cisco1407       OBJECT IDENTIFIER ::= { ciscoProducts 249 }
cisco1417       OBJECT IDENTIFIER ::= { ciscoProducts 250 }
cisco6100       OBJECT IDENTIFIER ::= { ciscoProducts 251 }
cisco6130       OBJECT IDENTIFIER ::= { ciscoProducts 252 }
cisco6260       OBJECT IDENTIFIER ::= { ciscoProducts 253 }
ciscoOpticalRegenerator OBJECT IDENTIFIER ::= { ciscoProducts 254 }
ciscoUBR924     OBJECT IDENTIFIER ::= { ciscoProducts 255 }
ciscoWSX6302Msm OBJECT IDENTIFIER ::= { ciscoProducts 256 }
catalyst5kRsfc  OBJECT IDENTIFIER ::= { ciscoProducts 257 }
catalyst6kMsfc  OBJECT IDENTIFIER ::= { ciscoProducts 258 }
cisco7120Quadt1 OBJECT IDENTIFIER ::= { ciscoProducts 259 }
cisco7120T3     OBJECT IDENTIFIER ::= { ciscoProducts 260 }
cisco7120E3     OBJECT IDENTIFIER ::= { ciscoProducts 261 }
cisco7120At3    OBJECT IDENTIFIER ::= { ciscoProducts 262 }
cisco7120Ae3    OBJECT IDENTIFIER ::= { ciscoProducts 263 }
cisco7120Smi3   OBJECT IDENTIFIER ::= { ciscoProducts 264 }
cisco7140Dualt3 OBJECT IDENTIFIER ::= { ciscoProducts 265 }
cisco7140Duale3 OBJECT IDENTIFIER ::= { ciscoProducts 266 }
cisco7140Dualat3 OBJECT IDENTIFIER ::= { ciscoProducts 267 }
cisco7140Dualae3 OBJECT IDENTIFIER ::= { ciscoProducts 268 }
cisco7140Dualmm3 OBJECT IDENTIFIER ::= { ciscoProducts 269 }
cisco827QuadV   OBJECT IDENTIFIER ::= { ciscoProducts 270 }
ciscoUBR7246VXR OBJECT IDENTIFIER ::= { ciscoProducts 271 }
cisco10400      OBJECT IDENTIFIER ::= { ciscoProducts 272 }
cisco12016      OBJECT IDENTIFIER ::= { ciscoProducts 273 }
ciscoAs5400     OBJECT IDENTIFIER ::= { ciscoProducts 274 }
cat2948gL3      OBJECT IDENTIFIER ::= { ciscoProducts 275 }
cisco7140Octt1  OBJECT IDENTIFIER ::= { ciscoProducts 276 }
cisco7140Dualfe OBJECT IDENTIFIER ::= { ciscoProducts 277 }
cat3548XL       OBJECT IDENTIFIER ::= { ciscoProducts 278 }
ciscoVG200      OBJECT IDENTIFIER ::= { ciscoProducts 279 }
cat6006         OBJECT IDENTIFIER ::= { ciscoProducts 280 }
cat6009         OBJECT IDENTIFIER ::= { ciscoProducts 281 }
cat6506         OBJECT IDENTIFIER ::= { ciscoProducts 282 }
cat6509         OBJECT IDENTIFIER ::= { ciscoProducts 283 }
cisco827        OBJECT IDENTIFIER ::= { ciscoProducts 284 }
ciscoManagementEngine1100 OBJECT IDENTIFIER ::= { ciscoProducts 285 }
ciscoMc3810V3   OBJECT IDENTIFIER ::= { ciscoProducts 286 }
cat3524tXLEn    OBJECT IDENTIFIER ::= { ciscoProducts 287 }
cisco7507z      OBJECT IDENTIFIER ::= { ciscoProducts 288 }
cisco7513z      OBJECT IDENTIFIER ::= { ciscoProducts 289 }
cisco7507mx     OBJECT IDENTIFIER ::= { ciscoProducts 290 }
cisco7513mx     OBJECT IDENTIFIER ::= { ciscoProducts 291 }
ciscoUBR912C    OBJECT IDENTIFIER ::= { ciscoProducts 292 }
ciscoUBR912S    OBJECT IDENTIFIER ::= { ciscoProducts 293 }
ciscoUBR914     OBJECT IDENTIFIER ::= { ciscoProducts 294 }
cisco802J       OBJECT IDENTIFIER ::= { ciscoProducts 295 }
cisco804J       OBJECT IDENTIFIER ::= { ciscoProducts 296 }
cisco6160       OBJECT IDENTIFIER ::= { ciscoProducts 297 }
cat4908gL3      OBJECT IDENTIFIER ::= { ciscoProducts 298 }
cisco6015       OBJECT IDENTIFIER ::= { ciscoProducts 299 }
cat4232L3       OBJECT IDENTIFIER ::= { ciscoProducts 300 }
catalyst6kMsfc2 OBJECT IDENTIFIER ::= { ciscoProducts 301 }
cisco7750Mrp200 OBJECT IDENTIFIER ::= { ciscoProducts 302 }
cisco7750Ssp80  OBJECT IDENTIFIER ::= { ciscoProducts 303 }
ciscoMGX8230    OBJECT IDENTIFIER ::= { ciscoProducts 304 }
ciscoMGX8250    OBJECT IDENTIFIER ::= { ciscoProducts 305 }
ciscoCVA122     OBJECT IDENTIFIER ::= { ciscoProducts 306 }
ciscoCVA124     OBJECT IDENTIFIER ::= { ciscoProducts 307 }
ciscoAs5850     OBJECT IDENTIFIER ::= { ciscoProducts 308 }
cat6509Sp       OBJECT IDENTIFIER ::= { ciscoProducts 310 }
ciscoMGX8240    OBJECT IDENTIFIER ::= { ciscoProducts 311 }
cat4840gL3      OBJECT IDENTIFIER ::= { ciscoProducts 312 }
ciscoAS5350     OBJECT IDENTIFIER ::= { ciscoProducts 313 }
cisco7750       OBJECT IDENTIFIER ::= { ciscoProducts 314 }
ciscoMGX8950    OBJECT IDENTIFIER ::= { ciscoProducts 315 }
ciscoUBR925     OBJECT IDENTIFIER ::= { ciscoProducts 316 }
ciscoUBR10012   OBJECT IDENTIFIER ::= { ciscoProducts 317 }
catalyst4kGateway OBJECT IDENTIFIER ::= { ciscoProducts 318 }
cisco2650       OBJECT IDENTIFIER ::= { ciscoProducts 319 }
cisco2651       OBJECT IDENTIFIER ::= { ciscoProducts 320 }
cisco826QuadV   OBJECT IDENTIFIER ::= { ciscoProducts 321 }
cisco826        OBJECT IDENTIFIER ::= { ciscoProducts 322 }
catalyst295012  OBJECT IDENTIFIER ::= { ciscoProducts 323 }
catalyst295024  OBJECT IDENTIFIER ::= { ciscoProducts 324 }
catalyst295024C OBJECT IDENTIFIER ::= { ciscoProducts 325 }
cisco1751       OBJECT IDENTIFIER ::= { ciscoProducts 326 }
cisco626        OBJECT IDENTIFIER ::= { ciscoProducts 329 }
cisco627        OBJECT IDENTIFIER ::= { ciscoProducts 330 }
cisco633        OBJECT IDENTIFIER ::= { ciscoProducts 331 }
cisco673        OBJECT IDENTIFIER ::= { ciscoProducts 332 }
cisco675        OBJECT IDENTIFIER ::= { ciscoProducts 333 }
cisco675e       OBJECT IDENTIFIER ::= { ciscoProducts 334 }
cisco676        OBJECT IDENTIFIER ::= { ciscoProducts 335 }
cisco677        OBJECT IDENTIFIER ::= { ciscoProducts 336 }
cisco678        OBJECT IDENTIFIER ::= { ciscoProducts 337 }
cisco3661Ac     OBJECT IDENTIFIER ::= { ciscoProducts 338 }
cisco3661Dc     OBJECT IDENTIFIER ::= { ciscoProducts 339 }
cisco3662Ac     OBJECT IDENTIFIER ::= { ciscoProducts 340 }
cisco3662Dc     OBJECT IDENTIFIER ::= { ciscoProducts 341 }
cisco3662AcCo   OBJECT IDENTIFIER ::= { ciscoProducts 342 }
cisco3662DcCo   OBJECT IDENTIFIER ::= { ciscoProducts 343 }
ciscoUBR7111    OBJECT IDENTIFIER ::= { ciscoProducts 344 }
ciscoUBR7111E   OBJECT IDENTIFIER ::= { ciscoProducts 345 }
ciscoUBR7114    OBJECT IDENTIFIER ::= { ciscoProducts 346 }
ciscoUBR7114E   OBJECT IDENTIFIER ::= { ciscoProducts 347 }
cisco12010      OBJECT IDENTIFIER ::= { ciscoProducts 348 }
cisco8110       OBJECT IDENTIFIER ::= { ciscoProducts 349 }
ciscoUBR905     OBJECT IDENTIFIER ::= { ciscoProducts 351 }
ciscoSOHO77     OBJECT IDENTIFIER ::= { ciscoProducts 353 }
ciscoSOHO76     OBJECT IDENTIFIER ::= { ciscoProducts 354 }
cisco7150Dualfe OBJECT IDENTIFIER ::= { ciscoProducts 355 }
cisco7150Octt1  OBJECT IDENTIFIER ::= { ciscoProducts 356 }
cisco7150Dualt3 OBJECT IDENTIFIER ::= { ciscoProducts 357 }
ciscoOlympus    OBJECT IDENTIFIER ::= { ciscoProducts 358 }
catalyst2950t24 OBJECT IDENTIFIER ::= { ciscoProducts 359 }
ciscoVPS1110    OBJECT IDENTIFIER ::= { ciscoProducts 360 }
ciscoContentEngine OBJECT IDENTIFIER ::= { ciscoProducts 361 }
ciscoIAD2420    OBJECT IDENTIFIER ::= { ciscoProducts 362 }
cisco677i       OBJECT IDENTIFIER ::= { ciscoProducts 363 }
cisco674        OBJECT IDENTIFIER ::= { ciscoProducts 364 }
ciscoDPA7630    OBJECT IDENTIFIER ::= { ciscoProducts 365 }
catalyst355024  OBJECT IDENTIFIER ::= { ciscoProducts 366 }
catalyst355048  OBJECT IDENTIFIER ::= { ciscoProducts 367 }
catalyst355012T OBJECT IDENTIFIER ::= { ciscoProducts 368 }
catalyst2924LREXL OBJECT IDENTIFIER ::= { ciscoProducts 369 }
catalyst2912LREXL OBJECT IDENTIFIER ::= { ciscoProducts 370 }
ciscoCVA122E    OBJECT IDENTIFIER ::= { ciscoProducts 371 }
ciscoCVA124E    OBJECT IDENTIFIER ::= { ciscoProducts 372 }
ciscoURM        OBJECT IDENTIFIER ::= { ciscoProducts 373 }
ciscoURM2FE     OBJECT IDENTIFIER ::= { ciscoProducts 374 }
ciscoURM2FE2V   OBJECT IDENTIFIER ::= { ciscoProducts 375 }
cisco7401VXR    OBJECT IDENTIFIER ::= { ciscoProducts 376 }
ciscoCAP340     OBJECT IDENTIFIER ::= { ciscoProducts 379 }
ciscoCAP350     OBJECT IDENTIFIER ::= { ciscoProducts 380 }
ciscoDPA7610    OBJECT IDENTIFIER ::= { ciscoProducts 381 }
cisco828        OBJECT IDENTIFIER ::= { ciscoProducts 382 }
cisco806        OBJECT IDENTIFIER ::= { ciscoProducts 384 }
cisco12416      OBJECT IDENTIFIER ::= { ciscoProducts 385 }
cat2948gL3Dc    OBJECT IDENTIFIER ::= { ciscoProducts 386 }
cat4908gL3Dc    OBJECT IDENTIFIER ::= { ciscoProducts 387 }
cisco12406      OBJECT IDENTIFIER ::= { ciscoProducts 388 }
ciscoPIXFirewall506 OBJECT IDENTIFIER ::= { ciscoProducts 389 }
ciscoPIXFirewall515 OBJECT IDENTIFIER ::= { ciscoProducts 390 }
ciscoPIXFirewall520 OBJECT IDENTIFIER ::= { ciscoProducts 391 }
ciscoPIXFirewall525 OBJECT IDENTIFIER ::= { ciscoProducts 392 }
ciscoPIXFirewall535 OBJECT IDENTIFIER ::= { ciscoProducts 393 }
cisco12410      OBJECT IDENTIFIER ::= { ciscoProducts 394 }
cisco811        OBJECT IDENTIFIER ::= { ciscoProducts 395 }
cisco813        OBJECT IDENTIFIER ::= { ciscoProducts 396 }
cisco10720      OBJECT IDENTIFIER ::= { ciscoProducts 397 }
ciscoMWR1900    OBJECT IDENTIFIER ::= { ciscoProducts 398 }
cisco4224       OBJECT IDENTIFIER ::= { ciscoProducts 399 }
ciscoWSC6513    OBJECT IDENTIFIER ::= { ciscoProducts 400 }
cisco7603       OBJECT IDENTIFIER ::= { ciscoProducts 401 }
cisco7606       OBJECT IDENTIFIER ::= { ciscoProducts 402 }
cisco7401ASR    OBJECT IDENTIFIER ::= { ciscoProducts 403 }
ciscoVG248      OBJECT IDENTIFIER ::= { ciscoProducts 404 }
ciscoHSE        OBJECT IDENTIFIER ::= { ciscoProducts 405 }
ciscoONS15540ESP OBJECT IDENTIFIER ::= { ciscoProducts 406 }
ciscoSN5420     OBJECT IDENTIFIER ::= { ciscoProducts 407 }
ciscoCe507      OBJECT IDENTIFIER ::= { ciscoProducts 409 }
ciscoCe560      OBJECT IDENTIFIER ::= { ciscoProducts 410 }
ciscoCe590      OBJECT IDENTIFIER ::= { ciscoProducts 411 }
ciscoCe7320     OBJECT IDENTIFIER ::= { ciscoProducts 412 }
cisco2691       OBJECT IDENTIFIER ::= { ciscoProducts 413 }
cisco3725       OBJECT IDENTIFIER ::= { ciscoProducts 414 }
cisco1760       OBJECT IDENTIFIER ::= { ciscoProducts 416 }
ciscoPIXFirewall501 OBJECT IDENTIFIER ::= { ciscoProducts 417 }
cisco2610M      OBJECT IDENTIFIER ::= { ciscoProducts 418 }
cisco2611M      OBJECT IDENTIFIER ::= { ciscoProducts 419 }
cisco12404      OBJECT IDENTIFIER ::= { ciscoProducts 423 }
cisco9004       OBJECT IDENTIFIER ::= { ciscoProducts 424 }
cisco3631Co     OBJECT IDENTIFIER ::= { ciscoProducts 425 }
catalyst295012G OBJECT IDENTIFIER ::= { ciscoProducts 427 }
catalyst295024G OBJECT IDENTIFIER ::= { ciscoProducts 428 }
catalyst295048G OBJECT IDENTIFIER ::= { ciscoProducts 429 }
catalyst295024S OBJECT IDENTIFIER ::= { ciscoProducts 430 }
catalyst355012G OBJECT IDENTIFIER ::= { ciscoProducts 431 }
ciscoCE507AV    OBJECT IDENTIFIER ::= { ciscoProducts 432 }
ciscoCE560AV    OBJECT IDENTIFIER ::= { ciscoProducts 433 }
ciscoIE2105     OBJECT IDENTIFIER ::= { ciscoProducts 434 }
ciscoMGX8850Pxm1E OBJECT IDENTIFIER ::= { ciscoProducts 435 }
cisco3745       OBJECT IDENTIFIER ::= { ciscoProducts 436 }
cisco10005      OBJECT IDENTIFIER ::= { ciscoProducts 437 }
cisco10008      OBJECT IDENTIFIER ::= { ciscoProducts 438 }
cisco7304       OBJECT IDENTIFIER ::= { ciscoProducts 439 }
ciscoRpmXf      OBJECT IDENTIFIER ::= { ciscoProducts 440 }
cisco1721       OBJECT IDENTIFIER ::= { ciscoProducts 444 }
cisco827H       OBJECT IDENTIFIER ::= { ciscoProducts 446 }
cat4006         OBJECT IDENTIFIER ::= { ciscoProducts 448 }
ciscoWSC6503    OBJECT IDENTIFIER ::= { ciscoProducts 449 }
ciscoPIXFirewall506E OBJECT IDENTIFIER ::= { ciscoProducts 450 }
ciscoPIXFirewall515E OBJECT IDENTIFIER ::= { ciscoProducts 451 }
cat355024Dc     OBJECT IDENTIFIER ::= { ciscoProducts 452 }
cat355024Mmf    OBJECT IDENTIFIER ::= { ciscoProducts 453 }
ciscoCE2636     OBJECT IDENTIFIER ::= { ciscoProducts 454 }
ciscoDwCE       OBJECT IDENTIFIER ::= { ciscoProducts 455 }
cisco7750Mrp300 OBJECT IDENTIFIER ::= { ciscoProducts 456 }
ciscoRPMPR      OBJECT IDENTIFIER ::= { ciscoProducts 457 }
cisco14MGX8830Pxm1E OBJECT IDENTIFIER ::= { ciscoProducts 458 }
ciscoWlse       OBJECT IDENTIFIER ::= { ciscoProducts 459 }
ciscoONS15530   OBJECT IDENTIFIER ::= { ciscoProducts 460 }
ciscoONS15530NEBS OBJECT IDENTIFIER ::= { ciscoProducts 461 }
ciscoONS15530ETSI OBJECT IDENTIFIER ::= { ciscoProducts 462 }
cisco6400UAC    OBJECT IDENTIFIER ::= { ciscoProducts 464 }
ciscoAIRAP1200  OBJECT IDENTIFIER ::= { ciscoProducts 474 }
ciscoSN5428     OBJECT IDENTIFIER ::= { ciscoProducts 475 }
cisco2610XM     OBJECT IDENTIFIER ::= { ciscoProducts 466 }
cisco2611XM     OBJECT IDENTIFIER ::= { ciscoProducts 467 }
cisco2620XM     OBJECT IDENTIFIER ::= { ciscoProducts 468 }
cisco2621XM     OBJECT IDENTIFIER ::= { ciscoProducts 469 }
cisco2650XM     OBJECT IDENTIFIER ::= { ciscoProducts 470 }
cisco2651XM     OBJECT IDENTIFIER ::= { ciscoProducts 471 }
catalyst295024GDC OBJECT IDENTIFIER ::= { ciscoProducts 472 }
cisco7301       OBJECT IDENTIFIER ::= { ciscoProducts 476 }
cisco3250       OBJECT IDENTIFIER ::= { ciscoProducts 479 }
catalyst295024SX OBJECT IDENTIFIER ::= { ciscoProducts 480 }
ciscoONS15540ESPx OBJECT IDENTIFIER ::= { ciscoProducts 481 }
catalyst295024LRESt OBJECT IDENTIFIER ::= { ciscoProducts 482 }
catalyst29508LRESt OBJECT IDENTIFIER ::= { ciscoProducts 483 }
catalyst295024LREG OBJECT IDENTIFIER ::= { ciscoProducts 484 }
catalyst355024PWR OBJECT IDENTIFIER ::= { ciscoProducts 485 }
ciscoCDM4630    OBJECT IDENTIFIER ::= { ciscoProducts 486 }
ciscoCDM4650    OBJECT IDENTIFIER ::= { ciscoProducts 487 }
catalyst2955T12 OBJECT IDENTIFIER ::= { ciscoProducts 488 }
catalyst2955C12 OBJECT IDENTIFIER ::= { ciscoProducts 489 }
ciscoCE508      OBJECT IDENTIFIER ::= { ciscoProducts 490 }
ciscoCE565      OBJECT IDENTIFIER ::= { ciscoProducts 491 }
ciscoCE7325     OBJECT IDENTIFIER ::= { ciscoProducts 492 }
ciscoONS15454   OBJECT IDENTIFIER ::= { ciscoProducts 493 }
ciscoONS15327   OBJECT IDENTIFIER ::= { ciscoProducts 494 }
cisco837        OBJECT IDENTIFIER ::= { ciscoProducts 495 }
ciscoSOHO97     OBJECT IDENTIFIER ::= { ciscoProducts 496 }
cisco831        OBJECT IDENTIFIER ::= { ciscoProducts 497 }
ciscoSOHO91     OBJECT IDENTIFIER ::= { ciscoProducts 498 }
cisco836        OBJECT IDENTIFIER ::= { ciscoProducts 499 }
ciscoSOHO96     OBJECT IDENTIFIER ::= { ciscoProducts 500 }
cat4507         OBJECT IDENTIFIER ::= { ciscoProducts 501 }
cat4506         OBJECT IDENTIFIER ::= { ciscoProducts 502 }
cat4503         OBJECT IDENTIFIER ::= { ciscoProducts 503 }
ciscoCE7305     OBJECT IDENTIFIER ::= { ciscoProducts 504 }
ciscoCE510      OBJECT IDENTIFIER ::= { ciscoProducts 505 }
ciscoAIRAP1100  OBJECT IDENTIFIER ::= { ciscoProducts 507 }
catalyst2955S12 OBJECT IDENTIFIER ::= { ciscoProducts 508 }
cisco7609       OBJECT IDENTIFIER ::= { ciscoProducts 509 }
catalyst375024  OBJECT IDENTIFIER ::= { ciscoProducts 511 }
catalyst375048  OBJECT IDENTIFIER ::= { ciscoProducts 512 }
catalyst375024TS OBJECT IDENTIFIER ::= { ciscoProducts 513 }
catalyst375024T OBJECT IDENTIFIER ::= { ciscoProducts 514 }
catalyst37xxStack OBJECT IDENTIFIER ::= { ciscoProducts 516 }
ciscoGSS        OBJECT IDENTIFIER ::= { ciscoProducts 517 }
ciscoPrimaryGSSM OBJECT IDENTIFIER ::= { ciscoProducts 518 }
ciscoStandbyGSSM OBJECT IDENTIFIER ::= { ciscoProducts 519 }
ciscoMWR1941DC  OBJECT IDENTIFIER ::= { ciscoProducts 520 }
ciscoDSC9216K9  OBJECT IDENTIFIER ::= { ciscoProducts 521 }
cat6500FirewallSm OBJECT IDENTIFIER ::= { ciscoProducts 522 }
ciscoCSM        OBJECT IDENTIFIER ::= { ciscoProducts 524 }
ciscoAIRAP1210  OBJECT IDENTIFIER ::= { ciscoProducts 525 }
catalyst297024  OBJECT IDENTIFIER ::= { ciscoProducts 527 }
cisco7613       OBJECT IDENTIFIER ::= { ciscoProducts 528 }
catalyst3750Ge12Sfp OBJECT IDENTIFIER ::= { ciscoProducts 530 }
ciscoCR4430     OBJECT IDENTIFIER ::= { ciscoProducts 531 }
ciscoCR4450     OBJECT IDENTIFIER ::= { ciscoProducts 532 }
ciscoAIRBR1410  OBJECT IDENTIFIER ::= { ciscoProducts 533 }
ciscoWSC6509neba OBJECT IDENTIFIER ::= { ciscoProducts 534 }
catalyst4510    OBJECT IDENTIFIER ::= { ciscoProducts 537 }
cisco1711       OBJECT IDENTIFIER ::= { ciscoProducts 538 }
cisco1712       OBJECT IDENTIFIER ::= { ciscoProducts 539 }
catalyst29408TT OBJECT IDENTIFIER ::= { ciscoProducts 540 }
catalyst29408TF OBJECT IDENTIFIER ::= { ciscoProducts 542 }
cisco3825       OBJECT IDENTIFIER ::= { ciscoProducts 543 }
cisco3845       OBJECT IDENTIFIER ::= { ciscoProducts 544 }
cisco2430Iad24Fxs OBJECT IDENTIFIER ::= { ciscoProducts 545 }
cisco2431Iad8Fxs OBJECT IDENTIFIER ::= { ciscoProducts 546 }
cisco2431Iad16Fxs OBJECT IDENTIFIER ::= { ciscoProducts 547 }
cisco2431Iad1T1E1 OBJECT IDENTIFIER ::= { ciscoProducts 548 }
cisco2432Iad24Fxs OBJECT IDENTIFIER ::= { ciscoProducts 549 }
cisco1701ADSLBRI OBJECT IDENTIFIER ::= { ciscoProducts 550 }
catalyst2950St24LRE997 OBJECT IDENTIFIER ::= { ciscoProducts 551 }
ciscoAirAp350IOS OBJECT IDENTIFIER ::= { ciscoProducts 552 }
cisco3220       OBJECT IDENTIFIER ::= { ciscoProducts 553 }
cat6500SslSm    OBJECT IDENTIFIER ::= { ciscoProducts 554 }
ciscoSIMSE      OBJECT IDENTIFIER ::= { ciscoProducts 555 }
ciscoESSE       OBJECT IDENTIFIER ::= { ciscoProducts 556 }
catalyst6kSup720 OBJECT IDENTIFIER ::= { ciscoProducts 557 }
catalyst295048T OBJECT IDENTIFIER ::= { ciscoProducts 559 }
catalyst295048SX OBJECT IDENTIFIER ::= { ciscoProducts 560 }
catalyst297024TS OBJECT IDENTIFIER ::= { ciscoProducts 561 }
ciscoNmNam      OBJECT IDENTIFIER ::= { ciscoProducts 562 }
catalyst356024PS OBJECT IDENTIFIER ::= { ciscoProducts 563 }
catalyst356048PS OBJECT IDENTIFIER ::= { ciscoProducts 564 }
ciscoAIRBR1300  OBJECT IDENTIFIER ::= { ciscoProducts 565 }
cisco877        OBJECT IDENTIFIER ::= { ciscoProducts 569 }
cisco878        OBJECT IDENTIFIER ::= { ciscoProducts 570 }
cisco871        OBJECT IDENTIFIER ::= { ciscoProducts 571 }
catalyst6kGateway OBJECT IDENTIFIER ::= { ciscoProducts 573 }
catalyst375024ME OBJECT IDENTIFIER ::= { ciscoProducts 574 }
catalyst4000NAM OBJECT IDENTIFIER ::= { ciscoProducts 575 }
cisco2811       OBJECT IDENTIFIER ::= { ciscoProducts 576 }
cisco2821       OBJECT IDENTIFIER ::= { ciscoProducts 577 }
cisco2851       OBJECT IDENTIFIER ::= { ciscoProducts 578 }
ciscoMCS7815I   OBJECT IDENTIFIER ::= { ciscoProducts 582 }
ciscoMCS7825H   OBJECT IDENTIFIER ::= { ciscoProducts 583 }
ciscoMCS7835H   OBJECT IDENTIFIER ::= { ciscoProducts 584 }
ciscoMCS7835I   OBJECT IDENTIFIER ::= { ciscoProducts 585 }
ciscoMCS7845H   OBJECT IDENTIFIER ::= { ciscoProducts 586 }
ciscoMCS7845I   OBJECT IDENTIFIER ::= { ciscoProducts 587 }
ciscoMCS7855I   OBJECT IDENTIFIER ::= { ciscoProducts 588 }
ciscoMCS7865I   OBJECT IDENTIFIER ::= { ciscoProducts 589 }
cisco12006      OBJECT IDENTIFIER ::= { ciscoProducts 590 }
catalyst3750G16TD OBJECT IDENTIFIER ::= { ciscoProducts 591 }
ciscoIGESM      OBJECT IDENTIFIER ::= { ciscoProducts 592 }
ciscoCCM        OBJECT IDENTIFIER ::= { ciscoProducts 593 }
ciscoCe511K9    OBJECT IDENTIFIER ::= { ciscoProducts 595 }
ciscoCe566K9    OBJECT IDENTIFIER ::= { ciscoProducts 596 }
ciscoMGX8880    OBJECT IDENTIFIER ::= { ciscoProducts 598 }
ciscoWsSvcWLAN1K9 OBJECT IDENTIFIER ::= { ciscoProducts 599 }
ciscoCe7306K9   OBJECT IDENTIFIER ::= { ciscoProducts 600 }
ciscoCe7326K9   OBJECT IDENTIFIER ::= { ciscoProducts 601 }
ciscoBMGX8830Pxm45 OBJECT IDENTIFIER ::= { ciscoProducts 606 }
ciscoBMGX8830Pxm1E OBJECT IDENTIFIER ::= { ciscoProducts 607 }
ciscoBMGX8850Pxm45 OBJECT IDENTIFIER ::= { ciscoProducts 608 }
ciscoBMGX8850Pxm1E OBJECT IDENTIFIER ::= { ciscoProducts 609 }
ciscoNetworkRegistrar OBJECT IDENTIFIER ::= { ciscoProducts 611 }
ciscoCe501K9    OBJECT IDENTIFIER ::= { ciscoProducts 612 }
ciscoCRS16S     OBJECT IDENTIFIER ::= { ciscoProducts 613 }
catalyst3560G24PS OBJECT IDENTIFIER ::= { ciscoProducts 614 }
catalyst3560G24TS OBJECT IDENTIFIER ::= { ciscoProducts 615 }
catalyst3560G48PS OBJECT IDENTIFIER ::= { ciscoProducts 616 }
catalyst3560G48TS OBJECT IDENTIFIER ::= { ciscoProducts 617 }
ciscoAIRAP1130  OBJECT IDENTIFIER ::= { ciscoProducts 618 }
cisco2801       OBJECT IDENTIFIER ::= { ciscoProducts 619 }
cisco1841       OBJECT IDENTIFIER ::= { ciscoProducts 620 }
ciscoWsSvcMWAM1 OBJECT IDENTIFIER ::= { ciscoProducts 621 }
ciscoNMCUE      OBJECT IDENTIFIER ::= { ciscoProducts 622 }
ciscoAIMCUE     OBJECT IDENTIFIER ::= { ciscoProducts 623 }
cisco371098HP001 OBJECT IDENTIFIER ::= { ciscoProducts 625 }
catalyst4948    OBJECT IDENTIFIER ::= { ciscoProducts 626 }
ciscoWLSE1130   OBJECT IDENTIFIER ::= { ciscoProducts 630 }
ciscoWLSE1030   OBJECT IDENTIFIER ::= { ciscoProducts 631 }
ciscoHSE1140    OBJECT IDENTIFIER ::= { ciscoProducts 632 }
catalyst356024TS OBJECT IDENTIFIER ::= { ciscoProducts 633 }
cisco1801       OBJECT IDENTIFIER ::= { ciscoProducts 638 }
cisco1811       OBJECT IDENTIFIER ::= { ciscoProducts 641 }
cisco1812       OBJECT IDENTIFIER ::= { ciscoProducts 642 }
ciscoCRS8S      OBJECT IDENTIFIER ::= { ciscoProducts 643 }
ciscoIDS4210    OBJECT IDENTIFIER ::= { ciscoProducts 645 }
ciscoIDS4215    OBJECT IDENTIFIER ::= { ciscoProducts 646 }
ciscoIDS4235    OBJECT IDENTIFIER ::= { ciscoProducts 647 }
ciscoIPS4240    OBJECT IDENTIFIER ::= { ciscoProducts 648 }
ciscoIDS4250    OBJECT IDENTIFIER ::= { ciscoProducts 649 }
ciscoIDS4250SX  OBJECT IDENTIFIER ::= { ciscoProducts 650 }
ciscoIDS4250XL  OBJECT IDENTIFIER ::= { ciscoProducts 651 }
ciscoIPS4255    OBJECT IDENTIFIER ::= { ciscoProducts 652 }
ciscoIDSIDSM2   OBJECT IDENTIFIER ::= { ciscoProducts 653 }
ciscoIDSNMCIDS  OBJECT IDENTIFIER ::= { ciscoProducts 654 }
ciscoIPSSSM20   OBJECT IDENTIFIER ::= { ciscoProducts 655 }
ciscoWSC6504E   OBJECT IDENTIFIER ::= { ciscoProducts 657 }
cisco7604       OBJECT IDENTIFIER ::= { ciscoProducts 658 }
catalyst494810GE OBJECT IDENTIFIER ::= { ciscoProducts 659 }
ciscoFE6326K9   OBJECT IDENTIFIER ::= { ciscoProducts 661 }
ciscoIPSSSM10   OBJECT IDENTIFIER ::= { ciscoProducts 662 }
ciscoNme16Es1Ge OBJECT IDENTIFIER ::= { ciscoProducts 663 }
ciscoNmeX24Es1Ge OBJECT IDENTIFIER ::= { ciscoProducts 664 }
ciscoNmeXd24Es2St OBJECT IDENTIFIER ::= { ciscoProducts 665 }
ciscoNmeXd48Es2Ge OBJECT IDENTIFIER ::= { ciscoProducts 666 }
ciscoAs5400XM   OBJECT IDENTIFIER ::= { ciscoProducts 668 }
ciscoASA5510    OBJECT IDENTIFIER ::= { ciscoProducts 669 }
ciscoASA5520    OBJECT IDENTIFIER ::= { ciscoProducts 670 }
ciscoASA5520sc  OBJECT IDENTIFIER ::= { ciscoProducts 671 }
ciscoASA5540    OBJECT IDENTIFIER ::= { ciscoProducts 672 }
ciscoASA5540sc  OBJECT IDENTIFIER ::= { ciscoProducts 673 }
ciscoWsSvcFwm1sc OBJECT IDENTIFIER ::= { ciscoProducts 674 }
ciscoPIXFirewall535sc OBJECT IDENTIFIER ::= { ciscoProducts 675 }
ciscoPIXFirewall525sc OBJECT IDENTIFIER ::= { ciscoProducts 676 }
ciscoPIXFirewall515Esc OBJECT IDENTIFIER ::= { ciscoProducts 677 }
ciscoPIXFirewall515sc OBJECT IDENTIFIER ::= { ciscoProducts 678 }
ciscoAs5350XM   OBJECT IDENTIFIER ::= { ciscoProducts 679 }
ciscoFe7326K9   OBJECT IDENTIFIER ::= { ciscoProducts 680 }
ciscoFe511K9    OBJECT IDENTIFIER ::= { ciscoProducts 681 }
ciscoSCEDispatcher OBJECT IDENTIFIER ::= { ciscoProducts 682 }
ciscoSCE1000    OBJECT IDENTIFIER ::= { ciscoProducts 683 }
ciscoSCE2000    OBJECT IDENTIFIER ::= { ciscoProducts 684 }
ciscoAIRAP1240  OBJECT IDENTIFIER ::= { ciscoProducts 685 }
ciscoDSC9120CLK9 OBJECT IDENTIFIER ::= { ciscoProducts 686 }
ciscoFe611K9    OBJECT IDENTIFIER ::= { ciscoProducts 687 }
ciscoICM        OBJECT IDENTIFIER ::= { ciscoProducts 693 }
catalyst6kMsfc2a OBJECT IDENTIFIER ::= { ciscoProducts 706 }
ciscoCe611K9    OBJECT IDENTIFIER ::= { ciscoProducts 708 }
ciscoWLSEs20    OBJECT IDENTIFIER ::= { ciscoProducts 709 }
ciscoMPX        OBJECT IDENTIFIER ::= { ciscoProducts 710 }
ciscoNMCUEEC    OBJECT IDENTIFIER ::= { ciscoProducts 711 }
ciscoWLSE1132   OBJECT IDENTIFIER ::= { ciscoProducts 712 }
ciscoME6340ACA  OBJECT IDENTIFIER ::= { ciscoProducts 713 }
ciscoME6340DCA  OBJECT IDENTIFIER ::= { ciscoProducts 714 }
ciscoME6340DCB  OBJECT IDENTIFIER ::= { ciscoProducts 715 }
catalyst296024TT OBJECT IDENTIFIER ::= { ciscoProducts 716 }
catalyst296048TT OBJECT IDENTIFIER ::= { ciscoProducts 717 }
catalystsExpress50024TT OBJECT IDENTIFIER ::= { ciscoProducts 724 }
catalystsExpress50024LC OBJECT IDENTIFIER ::= { ciscoProducts 725 }
catalystsExpress50024PC OBJECT IDENTIFIER ::= { ciscoProducts 726 }
catalystsExpress50012TC OBJECT IDENTIFIER ::= { ciscoProducts 727 }
ciscoACE10K9    OBJECT IDENTIFIER ::= { ciscoProducts 730 }
cisco5750       OBJECT IDENTIFIER ::= { ciscoProducts 731 }
ciscoCrs18Linecard OBJECT IDENTIFIER ::= { ciscoProducts 738 }
ciscoCrs1Fabric OBJECT IDENTIFIER ::= { ciscoProducts 739 }
ciscoFE2636     OBJECT IDENTIFIER ::= { ciscoProducts 740 }
ciscoIDS4220    OBJECT IDENTIFIER ::= { ciscoProducts 741 }
ciscoIDS4230    OBJECT IDENTIFIER ::= { ciscoProducts 742 }
ciscoMCS7825I   OBJECT IDENTIFIER ::= { ciscoProducts 746 }
ciscoWsC3750g24ps OBJECT IDENTIFIER ::= { ciscoProducts 747 }
ciscoWs3020Hpq  OBJECT IDENTIFIER ::= { ciscoProducts 748 }
ciscoWs3030Del  OBJECT IDENTIFIER ::= { ciscoProducts 749 }
ciscoSpaOc48posSfp OBJECT IDENTIFIER ::= { ciscoProducts 750 }
ciscoWLSE1133   OBJECT IDENTIFIER ::= { ciscoProducts 752 }
ciscoNMAONK9    OBJECT IDENTIFIER ::= { ciscoProducts 754 }
ciscoNMAONWS    OBJECT IDENTIFIER ::= { ciscoProducts 755 }
ciscoNMAONAPS   OBJECT IDENTIFIER ::= { ciscoProducts 756 }
ciscoWae612K9   OBJECT IDENTIFIER ::= { ciscoProducts 757 }
ciscoCe512K9    OBJECT IDENTIFIER ::= { ciscoProducts 759 }
ciscoFe512K9    OBJECT IDENTIFIER ::= { ciscoProducts 760 }
ciscoCe612K9    OBJECT IDENTIFIER ::= { ciscoProducts 761 }
ciscoFe612K9    OBJECT IDENTIFIER ::= { ciscoProducts 762 }
ciscoASA5520sy  OBJECT IDENTIFIER ::= { ciscoProducts 764 }
ciscoASA5540sy  OBJECT IDENTIFIER ::= { ciscoProducts 765 }
ciscoASA5550sy  OBJECT IDENTIFIER ::= { ciscoProducts 766 }
ciscoWsSvcFwm1sy OBJECT IDENTIFIER ::= { ciscoProducts 767 }
ciscoPIXFirewall515sy OBJECT IDENTIFIER ::= { ciscoProducts 768 }
ciscoPIXFirewall515Esy OBJECT IDENTIFIER ::= { ciscoProducts 769 }
ciscoPIXFirewall525sy OBJECT IDENTIFIER ::= { ciscoProducts 770 }
ciscoPIXFirewall535sy OBJECT IDENTIFIER ::= { ciscoProducts 771 }
ciscoOe512K9    OBJECT IDENTIFIER ::= { ciscoProducts 776 }
ciscoOe612K9    OBJECT IDENTIFIER ::= { ciscoProducts 777 }
ciscoOe511K9    OBJECT IDENTIFIER ::= { ciscoProducts 785 }
ciscoOe611K9    OBJECT IDENTIFIER ::= { ciscoProducts 786 }
ciscoOe7326K9   OBJECT IDENTIFIER ::= { ciscoProducts 787 }
ciscoUWIpPhone7920 OBJECT IDENTIFIER ::= { ciscoProducts 803 }
cisco3200WirelessMic OBJECT IDENTIFIER ::= { ciscoProducts 804 }
ciscoISRWireless OBJECT IDENTIFIER ::= { ciscoProducts 805 }
ciscoIPSVirtual OBJECT IDENTIFIER ::= { ciscoProducts 806 }
ciscoIDS4215Virtual OBJECT IDENTIFIER ::= { ciscoProducts 807 }
ciscoIDS4235Virtual OBJECT IDENTIFIER ::= { ciscoProducts 808 }
ciscoIDS4250Virtual OBJECT IDENTIFIER ::= { ciscoProducts 809 }
ciscoIDS4250SXVirtual OBJECT IDENTIFIER ::= { ciscoProducts 810 }
ciscoIDS4250XLVirtual OBJECT IDENTIFIER ::= { ciscoProducts 811 }
ciscoIDS4240Virtual OBJECT IDENTIFIER ::= { ciscoProducts 812 }
ciscoIDS4255Virtual OBJECT IDENTIFIER ::= { ciscoProducts 813 }
ciscoIDS4260Virtual OBJECT IDENTIFIER ::= { ciscoProducts 814 }
ciscoIDSIDSM2Virtual OBJECT IDENTIFIER ::= { ciscoProducts 815 }
ciscoIPSSSM20Virtual OBJECT IDENTIFIER ::= { ciscoProducts 816 }
ciscoIPSSSM10Virtual OBJECT IDENTIFIER ::= { ciscoProducts 817 }
cisco7201       OBJECT IDENTIFIER ::= { ciscoProducts 821 }
ciscoNmWae      OBJECT IDENTIFIER ::= { ciscoProducts 823 }


END
