-- MIB file created 25-Mar-2003 15:57:32, by
--   SMICng version 2.2.11-beta(PRO)(Solaris), January 20, 2001. Enterprise key cisco.com

CISCO-ATM-CONN-MIB DEFINITIONS ::= BEGIN

-- From file: "CISCO-ATM-CONN-MIB.my"
-- Compile options "4 7 F H N W 03 06 0B 0G 0N 0T"

IMPORTS
    TimeStamp, TruthValue, RowStatus
            FROM SNMPv2-TC-v1
    ifIndex, InterfaceIndexOrZero
            FROM IF-MIB
-- FIX: changed type import to ATM-TC-MIB
--    atmVplVpi, atmVclVpi, atmVclVci, AtmTrafficDescrParamIndex
    atmVplVpi, atmVclVpi, atmVclVci
            FROM ATM-MIB
    AtmTrafficDescrParamIndex
            FROM ATM-TC-MIB
    NsapAtmAddr
            FROM CISCO-ATM-IF-MIB
    ciscoExperiment
            FROM CISCO-SMI
    LsPerVcqThresholdGroup
            FROM CISCO-ATM-RM-MIB
    SnmpAdminString
            FROM SNMP-FRAMEWORK-MIB
    Counter, Gauge
            FROM RFC1155-SMI
    OBJECT-TYPE
            FROM RFC-1212;

ciscoAtmConnMIB OBJECT IDENTIFIER ::= { ciscoExperiment 13 }
-- MODULE-IDENTITY
--  LastUpdated
--    200207120000Z
--  OrgName
--    Cisco Systems, Inc.
--  ContactInfo
--           Cisco Systems
--            Customer Service
--    
--    Postal: 170 W Tasman Drive
--            San Jose, CA  95134
--            USA
--    
--       Tel: +1 800 553-NETS
--    
--    E-mail: cs-atm@cisco.com
--  Descr
--    This MIB module is a cisco extension to VPL/VCL table defined 
--     in rfc1695 for ATM switch connection management.
--  RevDate
--    200207120000Z
--  RevDescr
--    Added a new enumeration 'useTrafficDescr' to the syntax of 
--     ciscoAtmVclEpdEnable.
--  RevDate
--    200110300000Z
--  RevDescr
--    Added ciscoAtmVplConnType and ciscoAtmVclConnType objects  
--     to the VPL and VCL tables.
--  RevDate
--    200110100000Z
--  RevDescr
--    Added ciscoAtmVplConnName and ciscoAtmVclConnName objects  
--     to the VPL and VCL tables.
--  RevDate
--    200108060000Z
--  RevDescr
--    Added a enumeration for ConfigType to enable configuration
--     of Passive Half leg for 2-ended Soft PVC/PVP
--  RevDate
--    200101290000Z
--  RevDescr
--    Added objects that provide per-connection Transmit 
--     statistics for the switch fabric.
--  RevDate
--    9810020000Z
--  RevDescr
--    Added objects for reporting negotiated traffic parameters.
--  RevDate
--    9705260000Z
--  RevDescr
--    Added objects for management of new features made possible
--     on the LS1010 by the Feature Card Plus.  This includes
--     support for:
--        -  per-VC queueing hardware structures,
--        - enhanced UPC, 
--        - per-connection snooping,
--        - enhanced per-connection statistics.
--  RevDate
--    9611010000Z
--  RevDescr
--    Added 
--        - VPL/VCL violation counter, 
--        - SVC frame discard using AAL5IE, 
--        - default VPL/VCL tolerance 
--     objects.
--  RevDate
--    9807260000Z
--  RevDescr
--    Added
--        - object to configure a VP leg as a 
--          hierarchical VP.

ciscoAtmConnMIBObjects OBJECT IDENTIFIER ::= { ciscoAtmConnMIB 1 }
ciscoAtmVpl     OBJECT IDENTIFIER ::= { ciscoAtmConnMIBObjects 1 }
ciscoAtmVcl     OBJECT IDENTIFIER ::= { ciscoAtmConnMIBObjects 2 }
ciscoAtmSvp     OBJECT IDENTIFIER ::= { ciscoAtmConnMIBObjects 3 }
ciscoAtmSvc     OBJECT IDENTIFIER ::= { ciscoAtmConnMIBObjects 4 }
ciscoAtmSnoopVc OBJECT IDENTIFIER ::= { ciscoAtmConnMIBObjects 5 }
ciscoAtmSnoopVp OBJECT IDENTIFIER ::= { ciscoAtmConnMIBObjects 6 }
ciscoAtmConnMIBConformance OBJECT IDENTIFIER ::= { ciscoAtmConnMIB 3 }
ciscoAtmConnMIBCompliances OBJECT IDENTIFIER ::= { ciscoAtmConnMIBConformance 1 }
ciscoAtmConnMIBGroups OBJECT IDENTIFIER ::= { ciscoAtmConnMIBConformance 2 }

CastType ::= INTEGER {
        pointToPoint(1),
        pointToMultiPointRoot(2),
        pointToMultiPointLeaf(3)
        }
-- TEXTUAL-CONVENTION
--  Status
--    mandatory
--  Descr
--    Specifies the type of the connection. It can be either a point 
--     to point connection or point to multipoint root or leaf.

ConfigType ::= INTEGER {
        other(1),
        permanent(2),
        switch(3),
        soft(4),
        softPassive(5)
        }
-- TEXTUAL-CONVENTION
--  Status
--    mandatory
--  Descr
--    Specifies whether it's a permanent, switched, soft or 
--     soft passive config type.

SpanType ::= INTEGER {
        unknown(1),
        transit(2),
        terminate(3),
        both(4)
        }
-- TEXTUAL-CONVENTION
--  Status
--    mandatory
--  Descr
--    The SpanType textual convention is used to specify different 
--     connection span types.
--     The connection span types are:
--    
--     - 'unknown', which indicates that the connection entry is not 
--     cross-connected.
--    
--     - 'transit', which indicates that the connection entry is 
--     cross-connected and is not a connection end point.
--    
--     - 'terminate', which indicates that the connection entry is 
--     cross-connected and is a connection end point.
--    
--     - 'both', which indicates that the connection is transit as 
--     well as terminating. This will be true only if the connection 
--     cast type is a pointToMultiPointRoot and has transit and 
--     terminating connection leaves.
--    
--    None of the above values may be specified in a management 
--    protocol set operation.

EnableStatus ::= INTEGER {
        enable(1),
        disable(2)
        }
-- TEXTUAL-CONVENTION
--  Status
--    mandatory
--  Descr
--    Enable or Disable operation.

UpcStatus ::= INTEGER {
        passing(1),
        tagging(2),
        dropping(3),
        localShaping(4)
        }
-- TEXTUAL-CONVENTION
--  Status
--    mandatory
--  Descr
--    Define the Usage Parameter Control (UPC) operation as one of 
--     pass,tag or drop at this connection.

ConnState ::= INTEGER {
        setup(1),
        release(2),
        notInstalled(3),
        down(4),
        up(5)
        }
-- TEXTUAL-CONVENTION
--  Status
--    mandatory
--  Descr
--    The ConnState textual convention is used to specify different 
--     connection states. 
--     The connections states are:
--    
--     - 'setup', which indicates that the connection entry is to be 
--     created and installed in the hardware and software connection 
--     tables. 
--    
--     - 'release', which indicates that the connection entry is to 
--     be removed from the hardware and software connection tables.
--    
--     - 'notInstalled', which indicates connection entry is created 
--     only in the software connection tables. The connection entry is 
--     not installed in the hardware connection table.
--    
--     - 'down' which indicates that connection is down and is present 
--     in both software and hardware connection tables.
--    
--     - 'up' which indicates that connection is up and is present 
--     in both software and hardware connection tables.
--    
--    -  'setup' and 'release' are only two values may be specified 
--    in a management protocol set operation, only three values will 
--    be returned in response to a management protocol retrieval 
--    operation: 'notInstalled', 'down' or 'up'.

Location ::= INTEGER {
        unknown(1),
        calling(2),
        called(3)
        }
-- TEXTUAL-CONVENTION
--  Status
--    mandatory
--  Descr
--    Location of calling or called or unknown.

Direction ::= INTEGER {
        unknown(1),
        p2pCallingSide(2),
        p2pCalledSide(3),
        p2mpRoot(4),
        p2mpLeaf(5)
        }
-- TEXTUAL-CONVENTION
--  Status
--    mandatory
--  Descr
--    Calling or called side associated with address.

SnoopDirType ::= INTEGER {
        transmit(1),
        receive(2)
        }
-- TEXTUAL-CONVENTION
--  Status
--    mandatory
--  Descr
--    Direction of Snooped Traffic

ciscoAtmVplTable OBJECT-TYPE
    SYNTAX SEQUENCE OF CiscoAtmVplEntry
    ACCESS not-accessible
    STATUS mandatory
    DESCRIPTION
        "The Virtual Path Link extension Table."
    ::= { ciscoAtmVpl 1 }

ciscoAtmVplEntry OBJECT-TYPE
    SYNTAX CiscoAtmVplEntry
    ACCESS not-accessible
    STATUS mandatory
    DESCRIPTION
        " An entry in the Vpl table.This entry is used to model
        a bi-directional Vpl. This table augments the atmVplTable 
        defined in RFC 1695. However it uses ifIndex and atmVplVpi 
        as an Index for historical reasons. The entries are 
        created/deleted as a by-product of creating and deleting 
        entries in the atmVplTable."
    INDEX { ifIndex, atmVplVpi }
    ::= { ciscoAtmVplTable 1 }

CiscoAtmVplEntry ::= SEQUENCE {
    ciscoAtmVplCastType CastType,
    ciscoAtmVplSpanType SpanType,
    ciscoAtmVplConfigType ConfigType,
    ciscoAtmVplRxUpcMode UpcStatus,
    ciscoAtmVplConnState ConnState,
    ciscoAtmVplOamLoopbkTxInterval INTEGER,
    ciscoAtmVplOamSegmentLoopback EnableStatus,
    ciscoAtmVplOamEndLoopback EnableStatus,
    ciscoAtmVplOamAisEnable EnableStatus,
    ciscoAtmVplOamRdiEnable EnableStatus,
    ciscoAtmVplInstallTime TimeStamp,
    ciscoAtmVplInCells Counter,
    ciscoAtmVplOutCells Counter,
    ciscoAtmVplCrossIfIndex InterfaceIndexOrZero,
    ciscoAtmVplCrossVpi INTEGER,
    ciscoAtmVplNextLeafIfIndex InterfaceIndexOrZero,
    ciscoAtmVplNextLeafVpi INTEGER,
    ciscoAtmVplRemoteAddr NsapAtmAddr,
    ciscoAtmVplRemoteVpi INTEGER,
    ciscoAtmVplLocation Location,
    ciscoAtmVplSlowRetryIntv INTEGER,
    ciscoAtmVplNumAttempts Counter,
    ciscoAtmVplLastReleaseCause INTEGER,
    ciscoAtmVplLogicalPortDef INTEGER,
    ciscoAtmVplLogicalPortIndex InterfaceIndexOrZero,
    ciscoAtmVplUpcViolations Counter,
    ciscoAtmVplEpdTpdCellDrops Counter,
    ciscoAtmVplEpdTpdPacketDrops Counter,
    ciscoAtmVplEpdTpdPacketsIn Counter,
    ciscoAtmVplClp1Drops Counter,
    ciscoAtmVplDefaultRxUpcTolerance INTEGER,
    ciscoAtmVplDefaultRxUpcVbrCdvt INTEGER,
    ciscoAtmVplLsPerVcqWrrWeight INTEGER,
    ciscoAtmVplLsPerVcqTunnelIsShaped TruthValue,
    ciscoAtmVplLsPerVcqXmtQueuedCells Gauge,
    ciscoAtmVplLsPerVcQThreshGrp LsPerVcqThresholdGroup,
    ciscoAtmVplInClp0Cells Counter,
    ciscoAtmVplInClp1Cells Counter,
    ciscoAtmVplOutClp0Cells Counter,
    ciscoAtmVplOutClp1Cells Counter,
    ciscoAtmVplCellDrops Counter,
    ciscoAtmVplClp0VcqFullCellDrops Counter,
    ciscoAtmVplVcqClpThreshCellDrops Counter,
    ciscoAtmVplLsPerVcqTunnelIsHierarchical TruthValue,
    ciscoAtmVplRxNegTraffDescrIndex AtmTrafficDescrParamIndex,
    ciscoAtmVplTxNegTraffDescrIndex AtmTrafficDescrParamIndex,
    ciscoAtmVplSwFabOutCells Counter,
    ciscoAtmVplSwFabOutClp0Cells Counter,
    ciscoAtmVplSwFabOutClp1Cells Counter,
    ciscoAtmVplConnName SnmpAdminString,
    ciscoAtmVplConnType INTEGER
    }

ciscoAtmVplCastType OBJECT-TYPE
    SYNTAX CastType
--    Rsyntax INTEGER {
--        pointToPoint(1),
--        pointToMultiPointRoot(2),
--        pointToMultiPointLeaf(3)
--        }
    ACCESS read-write
    STATUS mandatory
    DESCRIPTION
        " Vpl type is either a point to point connection or point 
        to multipoint root or leaf."
    DEFVAL { pointToPoint }
    ::= { ciscoAtmVplEntry 1 }

ciscoAtmVplSpanType OBJECT-TYPE
    SYNTAX SpanType
--    Rsyntax INTEGER {
--        unknown(1),
--        transit(2),
--        terminate(3),
--        both(4)
--        }
    ACCESS read-only
    STATUS mandatory
    DESCRIPTION
        " Vpl span is either a transit one or a terminating one."
    DEFVAL { transit }
    ::= { ciscoAtmVplEntry 2 }

ciscoAtmVplConfigType OBJECT-TYPE
    SYNTAX ConfigType
--    Rsyntax INTEGER {
--        other(1),
--        permanent(2),
--        switch(3),
--        soft(4),
--        softPassive(5)
--        }
    ACCESS read-write
    STATUS mandatory
    DESCRIPTION
        " Vpl type is either a PVC, SVC, Soft PVC or Soft Passive half leg.
          The half leg can be set to Passive through user configuration only."
    DEFVAL { permanent }
    ::= { ciscoAtmVplEntry 3 }

ciscoAtmVplRxUpcMode OBJECT-TYPE
    SYNTAX UpcStatus
--    Rsyntax INTEGER {
--        passing(1),
--        tagging(2),
--        dropping(3),
--        localShaping(4)
--        }
    ACCESS read-write
    STATUS mandatory
    DESCRIPTION
        " Usage Parameter Control opeartion is pass,tag,drop or 
        local shaping at this connection."
    DEFVAL { passing }
    ::= { ciscoAtmVplEntry 4 }

ciscoAtmVplConnState OBJECT-TYPE
    SYNTAX ConnState
--    Rsyntax INTEGER {
--        setup(1),
--        release(2),
--        notInstalled(3),
--        down(4),
--        up(5)
--        }
    ACCESS read-write
    STATUS mandatory
    DESCRIPTION
        "The connection state of this VPL. "
    ::= { ciscoAtmVplEntry 5 }

ciscoAtmVplOamLoopbkTxInterval OBJECT-TYPE
    SYNTAX INTEGER(5..60)
--  Units
--    seconds
    ACCESS read-write
    STATUS mandatory
    DESCRIPTION
        "Frequency of OAM loopback cells generated."
    DEFVAL { 5 }
    ::= { ciscoAtmVplEntry 6 }

ciscoAtmVplOamSegmentLoopback OBJECT-TYPE
    SYNTAX EnableStatus
--    Rsyntax INTEGER {
--        enable(1),
--        disable(2)
--        }
    ACCESS read-write
    STATUS mandatory
    DESCRIPTION
        "Enable segment loopback on this virtual path."
    DEFVAL { disable }
    ::= { ciscoAtmVplEntry 7 }

ciscoAtmVplOamEndLoopback OBJECT-TYPE
    SYNTAX EnableStatus
--    Rsyntax INTEGER {
--        enable(1),
--        disable(2)
--        }
    ACCESS read-write
    STATUS mandatory
    DESCRIPTION
        "Enable end to end loopback on this virtual path."
    DEFVAL { disable }
    ::= { ciscoAtmVplEntry 8 }

ciscoAtmVplOamAisEnable OBJECT-TYPE
    SYNTAX EnableStatus
--    Rsyntax INTEGER {
--        enable(1),
--        disable(2)
--        }
    ACCESS read-write
    STATUS mandatory
    DESCRIPTION
        "Enable Alarm Indication Signal OAM cell generation
         if the interafce goes down on a crossconnect virtual path."
    DEFVAL { disable }
    ::= { ciscoAtmVplEntry 9 }

ciscoAtmVplOamRdiEnable OBJECT-TYPE
    SYNTAX EnableStatus
--    Rsyntax INTEGER {
--        enable(1),
--        disable(2)
--        }
    ACCESS read-write
    STATUS mandatory
    DESCRIPTION
        "Enable Remote Defect Indication OAM cell generation
         if an Alarm Indication Signal OAM cell is received."
    DEFVAL { disable }
    ::= { ciscoAtmVplEntry 10 }

ciscoAtmVplInstallTime OBJECT-TYPE
    SYNTAX TimeStamp
--    Rsyntax TimeTicks
    ACCESS read-only
    STATUS mandatory
    DESCRIPTION
        "The time stamp derived from sysUpTime when this VPL gets 
         created. The VPL entries are created/deleted as a by-product 
         of creating and deleting entries in the atmVplTable defined 
         in RFC1695."
    ::= { ciscoAtmVplEntry 11 }

ciscoAtmVplInCells OBJECT-TYPE
    SYNTAX Counter
    ACCESS read-only
    STATUS mandatory
    DESCRIPTION
        "The total number of cells received on this 
        VPL."
    ::= { ciscoAtmVplEntry 12 }

ciscoAtmVplOutCells OBJECT-TYPE
    SYNTAX Counter
    ACCESS read-only
    STATUS mandatory
    DESCRIPTION
        "The total number of cells transmitted on 
        this VPL."
    ::= { ciscoAtmVplEntry 13 }

ciscoAtmVplCrossIfIndex OBJECT-TYPE
    SYNTAX InterfaceIndexOrZero
--    Rsyntax INTEGER(0..2147483647)
    ACCESS read-write
    STATUS mandatory
    DESCRIPTION
        "For point to point, this is the cross-connected VPL's 
        ifIndex of this VPL. For point to multi-point connection, 
        this will be the root VPL's ifIndex for a leaf VPL entry in 
        the multicast chain, or it's the 1st leaf for a root VPL entry. 
        If it's zero, it means it's not cross-connected yet. 
        Atomically set ciscoAtmVplConnState, ciscoAtmVplCrossIfIndex 
        and ciscoAtmVplCrossVpi will create or delete a cross 
        connection to crossed half leg of this ciscoAtmVplCrossIfindex 
        and ciscoAtmVplCrossVpi for p2p PVP, or add or drop a multicast 
        connection of this ciscoAtmVplCrossIfindex and 
        ciscoAtmVplCrossVpi to/from the root on the multicast chain 
        for p2mp PVP."
    DEFVAL { 0 }
    ::= { ciscoAtmVplEntry 14 }

ciscoAtmVplCrossVpi OBJECT-TYPE
    SYNTAX INTEGER(0..4095)
    ACCESS read-write
    STATUS mandatory
    DESCRIPTION
        "This specifies the VPI value of the VPL to which this VPL is
         cross-connected. For point to multi-point connection, this is
         the root VPL's VPI for the leaf entry. Similarly it is the
         1st leaf's VPI value for the root entry."
    DEFVAL { 0 }
    ::= { ciscoAtmVplEntry 15 }

ciscoAtmVplNextLeafIfIndex OBJECT-TYPE
    SYNTAX InterfaceIndexOrZero
--    Rsyntax INTEGER(0..2147483647)
    ACCESS read-only
    STATUS mandatory
    DESCRIPTION
        "For point to point, this is zero i.e. not used. 
        For point to multi-point connection, this will be the next 
        leaf VPL's ifIndex on the multicast chain. This will be 0 
        if this is the root VPL entry. If it's zero for a leaf VPL,
        it means this is the last leaf."
    DEFVAL { 0 }
    ::= { ciscoAtmVplEntry 16 }

ciscoAtmVplNextLeafVpi OBJECT-TYPE
    SYNTAX INTEGER(0..4095)
    ACCESS read-only
    STATUS mandatory
    DESCRIPTION
        "For point to point, this is zero i.e. not used. 
        This apply only to point to multi-point connection, 
        this will be the next leaf VPL's VPI on the multicast chain."
    DEFVAL { 0 }
    ::= { ciscoAtmVplEntry 17 }

ciscoAtmVplRemoteAddr OBJECT-TYPE
    SYNTAX NsapAtmAddr
--    Rsyntax OCTET STRING(SIZE(20))
    ACCESS read-write
    STATUS mandatory
    DESCRIPTION
        "Soft PVP target address if this is the calling side
        Soft PVP source address if this is called side. 
        Atomically set ConnState, RemoteAddr
        and RemoteVpi will create or delete a soft PVP. 
        Atomically set ConnState, RemoteAddr without RemoteVpi will 
        also create or delete a soft PVP but let target switch 
        assign the vpi."
    ::= { ciscoAtmVplEntry 18 }

ciscoAtmVplRemoteVpi OBJECT-TYPE
    SYNTAX INTEGER(0..4095)
    ACCESS read-write
    STATUS mandatory
    DESCRIPTION
        "Soft PVP target VPI in calling side. 0 in called side."
    ::= { ciscoAtmVplEntry 19 }

ciscoAtmVplLocation OBJECT-TYPE
    SYNTAX Location
--    Rsyntax INTEGER {
--        unknown(1),
--        calling(2),
--        called(3)
--        }
    ACCESS read-only
    STATUS mandatory
    DESCRIPTION
        "Indicate calling or called side of a soft PVP.
         If ciscoAtmVplConfigType is not soft then 
        ciscoAtmVplLocation value should be ignored."
    ::= { ciscoAtmVplEntry 20 }

ciscoAtmVplSlowRetryIntv OBJECT-TYPE
    SYNTAX INTEGER(0..65535)
    ACCESS read-write
    STATUS mandatory
    DESCRIPTION
        "Soft PVP slow retry interval time in seconds."
    ::= { ciscoAtmVplEntry 21 }

ciscoAtmVplNumAttempts OBJECT-TYPE
    SYNTAX Counter
    ACCESS read-only
    STATUS mandatory
    DESCRIPTION
        "Number of retries made to install this soft PVP 
        connection. If ciscoAtmVplConfigType is not soft then 
        ciscoAtmVplNumAttempts value should be ignored."
    ::= { ciscoAtmVplEntry 22 }

ciscoAtmVplLastReleaseCause OBJECT-TYPE
    SYNTAX INTEGER(1..127)
    ACCESS read-only
    STATUS mandatory
    DESCRIPTION
        "Value of the Cause field of the Cause
        Information Element in the last Release
        Signalling message received for this SPVP.
        Indicates the reason for the Release.
        ciscoAtmVplConfigType is not soft then 
        ciscoAtmVplLastReleaseCause value should be ignored."
    REFERENCE
        "ATM Forum's UNI3.0/3.1 Speicifcation"
    ::= { ciscoAtmVplEntry 23 }

ciscoAtmVplLogicalPortDef OBJECT-TYPE
    SYNTAX INTEGER {
        notLogicalIf(1),
        isLogicalIf(2)
        }
    ACCESS read-write
    STATUS mandatory
    DESCRIPTION
        "Indicates whether the VPC at this VPL interface
        is an Atm Logical Port interface."
    DEFVAL { notLogicalIf }
    ::= { ciscoAtmVplEntry 24 }

ciscoAtmVplLogicalPortIndex OBJECT-TYPE
    SYNTAX InterfaceIndexOrZero
--    Rsyntax INTEGER(0..2147483647)
    ACCESS read-only
    STATUS mandatory
    DESCRIPTION
        "The ifTable index of the Atm logical port
        interface associated with this VPL. Only valid if
        the value of atmVplLogicalPortDef is isLogicalIf,
        and the VPL row is active."
    ::= { ciscoAtmVplEntry 25 }

ciscoAtmVplUpcViolations OBJECT-TYPE
    SYNTAX Counter
    ACCESS read-only
    STATUS mandatory
    DESCRIPTION
        "The total number of nonconforming cells detected
         by Usage Parameter Control (UPC) for cells received
         on this VPL.
         On LS1010 systems, this counter is valid only if
         equipped with the Feature Card - Per Flow Queueing."
    ::= { ciscoAtmVplEntry 26 }

ciscoAtmVplEpdTpdCellDrops OBJECT-TYPE
    SYNTAX Counter
    ACCESS read-only
    STATUS obsolete
    DESCRIPTION
        "Never implemented."
    ::= { ciscoAtmVplEntry 27 }

ciscoAtmVplEpdTpdPacketDrops OBJECT-TYPE
    SYNTAX Counter
    ACCESS read-only
    STATUS obsolete
    DESCRIPTION
        "Never implemented."
    ::= { ciscoAtmVplEntry 28 }

ciscoAtmVplEpdTpdPacketsIn OBJECT-TYPE
    SYNTAX Counter
    ACCESS read-only
    STATUS obsolete
    DESCRIPTION
        "Never implemented."
    ::= { ciscoAtmVplEntry 29 }

ciscoAtmVplClp1Drops OBJECT-TYPE
    SYNTAX Counter
    ACCESS read-only
    STATUS obsolete
    DESCRIPTION
        "Never implemented."
    ::= { ciscoAtmVplEntry 30 }

ciscoAtmVplDefaultRxUpcTolerance OBJECT-TYPE
    SYNTAX INTEGER
    ACCESS read-only
    STATUS mandatory
    DESCRIPTION
        "If the tolerance (CDVT for CBR, ABR, UBR connections, Maximum 
         Burst Size for VBR connectons)  requested for Usage 
         Parameter Control is not explicitly specified in VPL creation, 
         this object contains the default that is used. If tolerance
         is explicitly specified in VPL creation, it can be found in
         the Traffic Table row specified by atmVplReceiveTrafficDescrIndex,
         and the value of this object is -1."
    ::= { ciscoAtmVplEntry 31 }

ciscoAtmVplDefaultRxUpcVbrCdvt OBJECT-TYPE
    SYNTAX INTEGER
    ACCESS read-only
    STATUS mandatory
    DESCRIPTION
        "If the Cell Delay Variation Tolerance (CDVT) requested for 
         Usage Parameter Control for a VBR connection is not explicitly 
         specified in VPL creation, this object contains the default 
         that is used. If CDVT is explicitly specified in VPL creation, 
         it can be found in the Traffic Table row specified by 
         atmVplReceiveTrafficDescrIndex, and the value of this object 
         is -1."
    ::= { ciscoAtmVplEntry 32 }

ciscoAtmVplLsPerVcqWrrWeight OBJECT-TYPE
    SYNTAX INTEGER(1..15)
    ACCESS read-write
    STATUS mandatory
    DESCRIPTION
        "Configure the weighting specified for a VP half-leg
         within a service class to make the scheduling decision
         among other active VPLs in the service class. This
         is for transmit on the VPL on the interface. This
         parameter only applies to transit VPs. This object
         is defined only when the switch is equipped with 
         the Lightstream per-VC queueing chipset."
    ::= { ciscoAtmVplEntry 33 }

ciscoAtmVplLsPerVcqTunnelIsShaped OBJECT-TYPE
    SYNTAX TruthValue
--    Rsyntax INTEGER {
--        true(1),
--        false(2)
--        }
    ACCESS read-write
    STATUS mandatory
    DESCRIPTION
        "Determines whether this is to be a -shaped- VP, per
         the Lightstream per-VC queueing chipset. If the value 
         specified is TRUE, the VP is to be a shaped VP Tunnel. 
         Such a VP cannot be cross-connected. This object
         is defined only when the switch is equipped with 
         the Lightstream per-VC queueing chipset."
    ::= { ciscoAtmVplEntry 34 }

ciscoAtmVplLsPerVcqXmtQueuedCells OBJECT-TYPE
    SYNTAX Gauge
    ACCESS read-only
    STATUS mandatory
    DESCRIPTION
        "Number of cells received on this VPL and
         residing on the per-connection queue. Note that 
         this value is not valid until the VPL is in an 
         active cross-connect. This object
         is defined only when the switch is equipped with 
         the Lightstream per-VC queueing chipset."
    ::= { ciscoAtmVplEntry 35 }

ciscoAtmVplLsPerVcQThreshGrp OBJECT-TYPE
    SYNTAX LsPerVcqThresholdGroup
--    Rsyntax INTEGER {
--        tg1(1),
--        tg2(2),
--        tg3(3),
--        tg4(4),
--        tg5(5),
--        tg6(6),
--        tg7(7),
--        tg8(8),
--        tg9(9),
--        tg10(10),
--        tg11(11),
--        tg12(12),
--        tg13(13),
--        tg14(14),
--        tg15(15),
--        tg16(16)
--        }
    ACCESS read-only
    STATUS mandatory
    DESCRIPTION
        "The Threshold Group to which the cell-queue for 
         cells received by this VP are queued. This object
         is defined only when the switch is equipped with 
         the Lightstream per-VC queueing chipset."
    ::= { ciscoAtmVplEntry 36 }

ciscoAtmVplInClp0Cells OBJECT-TYPE
    SYNTAX Counter
    ACCESS read-only
    STATUS mandatory
    DESCRIPTION
        "The total number of cells with the CLP bit clear
         received on this VPL. Note that these cells may
         subsequently be discarded.
         This counter is valid only:
          - if the VPL is not a Logical Interface (tunnel).
          - on LS1010 systems, only those equipped with 
            Feature Card - Per Flow Queueing."
    ::= { ciscoAtmVplEntry 37 }

ciscoAtmVplInClp1Cells OBJECT-TYPE
    SYNTAX Counter
    ACCESS read-only
    STATUS mandatory
    DESCRIPTION
        "The total number of cells with the CLP bit set
         received on this VPL. Note that these cells may
         subsequently be discarded.
         This counter is valid only:
          - if the VPL is not a Logical Interface (tunnel).
          - on LS1010 systems, only those equipped with 
            Feature Card - Per Flow Queueing."
    ::= { ciscoAtmVplEntry 38 }

ciscoAtmVplOutClp0Cells OBJECT-TYPE
    SYNTAX Counter
    ACCESS read-only
    STATUS mandatory
    DESCRIPTION
        "The total number of cells with the CLP bit clear
         transmitted on this VPL.
         This counter is valid only:
          - if the VPL is not a Logical Interface (tunnel).
          - on LS1010 systems, only those equipped with 
            the Feature Card - Per Flow Queueing."
    ::= { ciscoAtmVplEntry 39 }

ciscoAtmVplOutClp1Cells OBJECT-TYPE
    SYNTAX Counter
    ACCESS read-only
    STATUS mandatory
    DESCRIPTION
        "The total number of cells with the CLP bit set
         transmitted on this VPL.
         This counter is valid only:
          - if the VPL is not a Logical Interface (tunnel).
          - on LS1010 systems, only those equipped with 
            the Feature Card - Per Flow Queueing."
    ::= { ciscoAtmVplEntry 40 }

ciscoAtmVplCellDrops OBJECT-TYPE
    SYNTAX Counter
    ACCESS read-only
    STATUS mandatory
    DESCRIPTION
        "The total number of cells received on this
         VPL, but discarded.
         This counter is valid only:
          - if the VPL is not a Logical Interface (tunnel).
          - on LS1010 systems, only those equipped with 
            Feature Card - Per Flow Queueing."
    ::= { ciscoAtmVplEntry 41 }

ciscoAtmVplClp0VcqFullCellDrops OBJECT-TYPE
    SYNTAX Counter
    ACCESS read-only
    STATUS mandatory
    DESCRIPTION
        "The total number of cells received on this
         VPL with the CLP bit clear, discarded because
         the per-VC queue limit is exceeded.
         This counter is valid only:
          - if the VPL is not a Logical Interface (tunnel).
          - on LS1010 systems, only those equipped with 
            Feature Card - Per Flow Queueing."
    ::= { ciscoAtmVplEntry 43 }

ciscoAtmVplVcqClpThreshCellDrops OBJECT-TYPE
    SYNTAX Counter
    ACCESS read-only
    STATUS mandatory
    DESCRIPTION
        "The total number of cells received on this
         VPL, discarded because the discard threshold
         (as opposed to the queue-limit) is exceeded
         on the per-VC queue, and the CLP bit is set.
         This counter is valid only:
          - if the VPL is not a Logical Interface (tunnel).
          - on LS1010 systems, only those equipped with 
            Feature Card - Per Flow Queueing."
    ::= { ciscoAtmVplEntry 44 }

ciscoAtmVplLsPerVcqTunnelIsHierarchical OBJECT-TYPE
    SYNTAX TruthValue
--    Rsyntax INTEGER {
--        true(1),
--        false(2)
--        }
    ACCESS read-write
    STATUS mandatory
    DESCRIPTION
        "Determines whether this is to be a -Hierarchical- VP, per
         the Lightstream per-VC queueing chipset. If the value
         specified is TRUE, the VP is to be a Hierarchical VP Tunnel.
         Such a VP cannot be cross-connected. This object
         is defined on a LS1010 only when the switch is equipped with
         the Lightstream per-VC queueing chipset."
    ::= { ciscoAtmVplEntry 45 }

ciscoAtmVplRxNegTraffDescrIndex OBJECT-TYPE
    SYNTAX AtmTrafficDescrParamIndex
--    Rsyntax INTEGER
    ACCESS read-only
    STATUS mandatory
    DESCRIPTION
        "Identifies the entry in the atmTrafficDescrParamTable which
        contains negotiated traffic parameters applied to the receive
        direction of this VPL.
        
        This object is not instantiated if this VPL is not the calling
        side of a soft VP, or if there was no traffic negotiation."
    ::= { ciscoAtmVplEntry 46 }

ciscoAtmVplTxNegTraffDescrIndex OBJECT-TYPE
    SYNTAX AtmTrafficDescrParamIndex
--    Rsyntax INTEGER
    ACCESS read-only
    STATUS mandatory
    DESCRIPTION
        "Identifies the entry in the atmTrafficDescrParamTable which
        contains negotiated traffic parameters applied to the transmit
        direction of this VPL.
        
        This object is not instantiated if this VPL is not the calling
        side of a soft VP, or if there was no traffic negotiation."
    ::= { ciscoAtmVplEntry 47 }

ciscoAtmVplSwFabOutCells OBJECT-TYPE
    SYNTAX Counter
    ACCESS read-only
    STATUS mandatory
    DESCRIPTION
        "The total number of cells transmitted on
        this VPL by the Switch Fabric. This object is not 
        instantiated on systems that do not have support for 
        collecting such statistics."
    ::= { ciscoAtmVplEntry 48 }

ciscoAtmVplSwFabOutClp0Cells OBJECT-TYPE
    SYNTAX Counter
    ACCESS read-only
    STATUS mandatory
    DESCRIPTION
        "The total number of cells with the CLP bit clear
         transmitted on this VPL by the Switch Fabric.  This object
         is not instantiated for a VPL that is a logical interface
         (VP Tunnel).  This object is not instantiated on systems 
         that do not have support for collecting such statistics."
    ::= { ciscoAtmVplEntry 49 }

ciscoAtmVplSwFabOutClp1Cells OBJECT-TYPE
    SYNTAX Counter
    ACCESS read-only
    STATUS mandatory
    DESCRIPTION
        "The total number of cells with the CLP bit set transmitted
         on this VPL by the Switch Fabric. This object is not 
         instantiated for a VPL that is a logical interface
         (VP Tunnel).  This object is not instantiated on systems 
         that do not have support for collecting such statistics."
    ::= { ciscoAtmVplEntry 50 }

ciscoAtmVplConnName OBJECT-TYPE
    SYNTAX SnmpAdminString
--    Rsyntax OCTET STRING(SIZE(0..255))
    ACCESS read-write
    STATUS mandatory
    DESCRIPTION
        "A human readable string that identifies this connection.
         This object will return a zero-length string if value is
         not set."
    ::= { ciscoAtmVplEntry 51 }

ciscoAtmVplConnType OBJECT-TYPE
    SYNTAX INTEGER {
        local(1),
        endToEnd(2)
        }
    ACCESS read-write
    STATUS mandatory
    DESCRIPTION
        "This object represent the PVP Type for this connection.
         - local       connection within the node
         - endToEnd    across several nodes
         This object serves as an information object for a
         management system and has no functional meaning to
         the switch."
    ::= { ciscoAtmVplEntry 52 }

ciscoAtmVclTable OBJECT-TYPE
    SYNTAX SEQUENCE OF CiscoAtmVclEntry
    ACCESS not-accessible
    STATUS mandatory
    DESCRIPTION
        "The Virtual Channel Link extension Table."
    ::= { ciscoAtmVcl 1 }

ciscoAtmVclEntry OBJECT-TYPE
    SYNTAX CiscoAtmVclEntry
    ACCESS not-accessible
    STATUS mandatory
    DESCRIPTION
        " An entry in the Vcl table.This entry is used to model
        a bi-directional Vcl. This table augments the atmVclTable 
        defined in RFC 1695. However it uses ifIndex, atmVclVpi 
        and atmVclVci as an Index for historical reasons.
        The entries are created/deleted as a by-product of 
        creating and deleting entries in the atmVclTable."
    INDEX { ifIndex, atmVclVpi, atmVclVci }
    ::= { ciscoAtmVclTable 1 }

CiscoAtmVclEntry ::= SEQUENCE {
    ciscoAtmVclCastType CastType,
    ciscoAtmVclSpanType SpanType,
    ciscoAtmVclConfigType ConfigType,
    ciscoAtmVclRxUpcMode UpcStatus,
    ciscoAtmVclEpdEnable INTEGER,
    ciscoAtmVclConnState ConnState,
    ciscoAtmVclOamLoopbkTxInterval INTEGER,
    ciscoAtmVclOamSegmentLoopback EnableStatus,
    ciscoAtmVclOamEndLoopback EnableStatus,
    ciscoAtmVclOamAisEnable EnableStatus,
    ciscoAtmVclOamRdiEnable EnableStatus,
    ciscoAtmVclInstallTime TimeStamp,
    ciscoAtmVclInCells Counter,
    ciscoAtmVclOutCells Counter,
    ciscoAtmVclCrossIfIndex InterfaceIndexOrZero,
    ciscoAtmVclCrossVpi INTEGER,
    ciscoAtmVclCrossVci INTEGER,
    ciscoAtmVclNextLeafIfIndex InterfaceIndexOrZero,
    ciscoAtmVclNextLeafVpi INTEGER,
    ciscoAtmVclNextLeafVci INTEGER,
    ciscoAtmVclAalEncapFlag INTEGER,
    ciscoAtmVclAalEncapProtocol INTEGER,
    ciscoAtmVclAalUserVcType INTEGER,
    ciscoAtmVclAtmInArpInterval INTEGER,
    ciscoAtmVclRemoteAddr NsapAtmAddr,
    ciscoAtmVclRemoteVpi INTEGER,
    ciscoAtmVclRemoteVci INTEGER,
    ciscoAtmVclLocation Location,
    ciscoAtmVclSlowRetryIntv INTEGER,
    ciscoAtmVclNumAttempts Counter,
    ciscoAtmVclLastReleaseCause INTEGER,
    ciscoAtmVclUpcViolations Counter,
    ciscoAtmVclEpdTpdCellDrops Counter,
    ciscoAtmVclEpdTpdPacketDrops Counter,
    ciscoAtmVclEpdTpdPacketsIn Counter,
    ciscoAtmVclClp1Drops Counter,
    ciscoAtmVclDefaultRxUpcTolerance INTEGER,
    ciscoAtmVclDefaultRxUpcVbrCdvt INTEGER,
    ciscoAtmVclLsPerVcqWrrWeight INTEGER,
    ciscoAtmVclLsPerVcqXmtQueuedCells Gauge,
    ciscoAtmVclLsPerVcQThreshGrp LsPerVcqThresholdGroup,
    ciscoAtmVclInClp0Cells Counter,
    ciscoAtmVclInClp1Cells Counter,
    ciscoAtmVclOutClp0Cells Counter,
    ciscoAtmVclOutClp1Cells Counter,
    ciscoAtmVclCellDrops Counter,
    ciscoAtmVclClp0VcqFullCellDrops Counter,
    ciscoAtmVclVcqClpThreshCellDrops Counter,
    ciscoAtmVclRxNegTraffDescrIndex AtmTrafficDescrParamIndex,
    ciscoAtmVclTxNegTraffDescrIndex AtmTrafficDescrParamIndex,
    ciscoAtmVclSwFabOutCells Counter,
    ciscoAtmVclSwFabOutClp0Cells Counter,
    ciscoAtmVclSwFabOutClp1Cells Counter,
    ciscoAtmVclConnName SnmpAdminString,
    ciscoAtmVclConnType INTEGER
    }

ciscoAtmVclCastType OBJECT-TYPE
    SYNTAX CastType
--    Rsyntax INTEGER {
--        pointToPoint(1),
--        pointToMultiPointRoot(2),
--        pointToMultiPointLeaf(3)
--        }
    ACCESS read-write
    STATUS mandatory
    DESCRIPTION
        " Vcl type is either a point to point connection or point 
        to multipoint root or leaf."
    DEFVAL { pointToPoint }
    ::= { ciscoAtmVclEntry 1 }

ciscoAtmVclSpanType OBJECT-TYPE
    SYNTAX SpanType
--    Rsyntax INTEGER {
--        unknown(1),
--        transit(2),
--        terminate(3),
--        both(4)
--        }
    ACCESS read-only
    STATUS mandatory
    DESCRIPTION
        " Vcl span is either a transit one or a terminating one."
    DEFVAL { transit }
    ::= { ciscoAtmVclEntry 2 }

ciscoAtmVclConfigType OBJECT-TYPE
    SYNTAX ConfigType
--    Rsyntax INTEGER {
--        other(1),
--        permanent(2),
--        switch(3),
--        soft(4),
--        softPassive(5)
--        }
    ACCESS read-write
    STATUS mandatory
    DESCRIPTION
        " Vcl type is either a PVC, SVC, Soft PVC or Soft Passive half leg.
          The half leg can be set to Passive through user configuration only."
    DEFVAL { permanent }
    ::= { ciscoAtmVclEntry 3 }

ciscoAtmVclRxUpcMode OBJECT-TYPE
    SYNTAX UpcStatus
--    Rsyntax INTEGER {
--        passing(1),
--        tagging(2),
--        dropping(3),
--        localShaping(4)
--        }
    ACCESS read-write
    STATUS mandatory
    DESCRIPTION
        " Usage Parameter Control opeartion is pass,tag,drop or 
        local shaping at this connection."
    DEFVAL { passing }
    ::= { ciscoAtmVclEntry 4 }

ciscoAtmVclEpdEnable OBJECT-TYPE
    SYNTAX INTEGER {
        enable(1),
        disable(2),
        useTrafficDescr(3)
        }
    ACCESS read-write
    STATUS mandatory
    DESCRIPTION
        " Early Packet Discard option used for this VCL.
          The use is as follows:
          enable(1)
             Packet-discard is enabled.
          disable(2)
             Packet-discard is disabled.
          useTrafficDescr(3)
             Packet-discard in the receive direction is as specified by
             the atmTrafficFrameDiscard value in row corresponding to
             atmVclReceiveTrafficDescrIndex.  For VCLs of type
             spvcInitiator, the packet-discard in the reverse direction
             is as specified by the atmTrafficFrameDiscard value in row
             corresponding to atmVclTransmitTrafficDescrIndex. "
    DEFVAL { useTrafficDescr }
    ::= { ciscoAtmVclEntry 5 }

ciscoAtmVclConnState OBJECT-TYPE
    SYNTAX ConnState
--    Rsyntax INTEGER {
--        setup(1),
--        release(2),
--        notInstalled(3),
--        down(4),
--        up(5)
--        }
    ACCESS read-write
    STATUS mandatory
    DESCRIPTION
        "The connection state of this VCL."
    ::= { ciscoAtmVclEntry 6 }

ciscoAtmVclOamLoopbkTxInterval OBJECT-TYPE
    SYNTAX INTEGER(5..60)
--  Units
--    seconds
    ACCESS read-write
    STATUS mandatory
    DESCRIPTION
        "Frequency of OAM loopback cell are generated on this 
        virtual channel."
    DEFVAL { 5 }
    ::= { ciscoAtmVclEntry 7 }

ciscoAtmVclOamSegmentLoopback OBJECT-TYPE
    SYNTAX EnableStatus
--    Rsyntax INTEGER {
--        enable(1),
--        disable(2)
--        }
    ACCESS read-write
    STATUS mandatory
    DESCRIPTION
        "Enable segment loopback on this virtual channel."
    DEFVAL { disable }
    ::= { ciscoAtmVclEntry 8 }

ciscoAtmVclOamEndLoopback OBJECT-TYPE
    SYNTAX EnableStatus
--    Rsyntax INTEGER {
--        enable(1),
--        disable(2)
--        }
    ACCESS read-write
    STATUS mandatory
    DESCRIPTION
        "Enable end to end loopback on this virtual channel."
    DEFVAL { disable }
    ::= { ciscoAtmVclEntry 9 }

ciscoAtmVclOamAisEnable OBJECT-TYPE
    SYNTAX EnableStatus
--    Rsyntax INTEGER {
--        enable(1),
--        disable(2)
--        }
    ACCESS read-write
    STATUS mandatory
    DESCRIPTION
        "Enable Alarm Indication Signal OAM cell generation
         if the interafce goes down on a crossconnect virtual 
         channel."
    DEFVAL { disable }
    ::= { ciscoAtmVclEntry 10 }

ciscoAtmVclOamRdiEnable OBJECT-TYPE
    SYNTAX EnableStatus
--    Rsyntax INTEGER {
--        enable(1),
--        disable(2)
--        }
    ACCESS read-write
    STATUS mandatory
    DESCRIPTION
        "Enable Remote Defect Indication OAM cell generation
         if an Alarm Indication Signal OAM cell is received."
    DEFVAL { disable }
    ::= { ciscoAtmVclEntry 11 }

ciscoAtmVclInstallTime OBJECT-TYPE
    SYNTAX TimeStamp
--    Rsyntax TimeTicks
    ACCESS read-only
    STATUS mandatory
    DESCRIPTION
        "The time stamp derived from sysUpTime when this VCL gets 
         created. The VCL entries are created/deleted as a by-product 
         of creating and deleting entries in the atmVclTable defined 
         in RFC1695."
    ::= { ciscoAtmVclEntry 12 }

ciscoAtmVclInCells OBJECT-TYPE
    SYNTAX Counter
    ACCESS read-only
    STATUS mandatory
    DESCRIPTION
        "The total number of cells received on 
        this VCL."
    ::= { ciscoAtmVclEntry 13 }

ciscoAtmVclOutCells OBJECT-TYPE
    SYNTAX Counter
    ACCESS read-only
    STATUS mandatory
    DESCRIPTION
        "The total number of cells transmitted on 
        this VCL."
    ::= { ciscoAtmVclEntry 14 }

ciscoAtmVclCrossIfIndex OBJECT-TYPE
    SYNTAX InterfaceIndexOrZero
--    Rsyntax INTEGER(0..2147483647)
    ACCESS read-write
    STATUS mandatory
    DESCRIPTION
        "For point to point, this is the cross-connected VCL's 
        ifIndex of this VCL. For point to multi-point connection, 
        this will be the root VCL's ifIndex for a leaf VCL entry in 
        the multicast chain, or it's the 1st leaf VCL for a root 
        VCL entry. If it's zero, it means it's not cross-connected 
        yet. Atomically set ciscoAtmVclConnState, 
        ciscoAtmVclCrossIfindex, ciscoAtmVclCrossVpi and 
        ciscoAtmVclCrossVci will create or delete a cross 
        connection to crossed half leg of this 
        ciscoAtmVclCrossIfindex, ciscoAtmVclCrossVpi and 
        ciscoAtmVclCrossVci for p2p PVC, or add or drop a multicast 
        connection to/from the root of this ciscoAtmVclCrossIfindex, 
        ciscoAtmVclCrossVpi and ciscoAtmVclCrossVci on the multicast 
        chain for p2mp PVC."
    DEFVAL { 0 }
    ::= { ciscoAtmVclEntry 15 }

ciscoAtmVclCrossVpi OBJECT-TYPE
    SYNTAX INTEGER(0..4095)
    ACCESS read-write
    STATUS mandatory
    DESCRIPTION
        "This specifies the VPI value of the VCL to which this 
        VCL is cross-connected. For point to multi-point 
        connection, this is the root VCL's VPI for the leaf entry. 
        Similarly it is the 1st leaf's VPI value for the root entry."
    DEFVAL { 0 }
    ::= { ciscoAtmVclEntry 16 }

ciscoAtmVclCrossVci OBJECT-TYPE
    SYNTAX INTEGER(0..65535)
    ACCESS read-write
    STATUS mandatory
    DESCRIPTION
        "This specifies the VCI value of the VCL to which this 
        VCL is cross-connected. For point to multi-point 
        connection, this is the root VCL's VCI for the leaf 
        entry. Similarly it is the 1st leaf's VCI value for 
        the root entry."
    DEFVAL { 0 }
    ::= { ciscoAtmVclEntry 17 }

ciscoAtmVclNextLeafIfIndex OBJECT-TYPE
    SYNTAX InterfaceIndexOrZero
--    Rsyntax INTEGER(0..2147483647)
    ACCESS read-only
    STATUS mandatory
    DESCRIPTION
        "For point to point, this is zero i.e. not used. 
        For point to multi-point connection, this will be 
        the next leaf VCL's ifIndex on the multicast chain. 
        This will be 0 if this is the root VCL entry. 
        If it's zero for a leaf VCL, it means this is the 
        last leaf."
    DEFVAL { 0 }
    ::= { ciscoAtmVclEntry 18 }

ciscoAtmVclNextLeafVpi OBJECT-TYPE
    SYNTAX INTEGER(0..4095)
    ACCESS read-only
    STATUS mandatory
    DESCRIPTION
        "For point to point, this is zero i.e. not used. 
        This apply only to point to multi-point connection, 
        this will be the next leaf VCL's VPI on the multicast 
        chain."
    DEFVAL { 0 }
    ::= { ciscoAtmVclEntry 19 }

ciscoAtmVclNextLeafVci OBJECT-TYPE
    SYNTAX INTEGER(0..65535)
    ACCESS read-only
    STATUS mandatory
    DESCRIPTION
        "For point to point, this is zero i.e. not used. 
        This apply only to point to multi-point connection, 
        this will be the next leaf VCL's VCI on the multicast 
        chain."
    DEFVAL { 0 }
    ::= { ciscoAtmVclEntry 20 }

ciscoAtmVclAalEncapFlag OBJECT-TYPE
    SYNTAX INTEGER {
        other(1),
        aal5Snap(2),
        aal5Nlpid(3),
        aal5FrNlpid(4),
        aal5Mux(5),
        aal34Smds(6),
        aalQsAal(7),
        aal5Ilmi(8),
        aal5Lane(9),
        aal5Pnni(10)
        }
    ACCESS read-write
    STATUS mandatory
    DESCRIPTION
        "Encapsulation type for terminating VC."
    ::= { ciscoAtmVclEntry 21 }

ciscoAtmVclAalEncapProtocol OBJECT-TYPE
    SYNTAX INTEGER {
        other(1),
        ip(2),
        xns(3),
        appletalk(4),
        clns(5),
        decnet(6),
        novell(7),
        apollo(8),
        vines(9)
        }
    ACCESS read-write
    STATUS mandatory
    DESCRIPTION
        "Protocol for terminating VC if EncapFlag is aal5Mux."
    ::= { ciscoAtmVclEntry 22 }

ciscoAtmVclAalUserVcType OBJECT-TYPE
    SYNTAX INTEGER {
        other(1),
        boxConfigure(2),
        busForward(3),
        busSend(4),
        clientConfigure(5),
        clientData(6),
        clientDirect(7),
        clientDistribute(8),
        clientForward(9),
        clientSend(10),
        configure(11),
        serverConfigure(12),
        serverDirect(13),
        serverDistribute(14)
        }
    ACCESS read-write
    STATUS mandatory
    DESCRIPTION
        "Following is the list of user virtual circuit types in 
         case aal5Lane encapusation on this virtual channel.
         boxConfigure -- The shared Server/Client end of a 
                         Configure VCC
         busForward -- The BUS end of the Data Forward VCC
         busSend -- The BUS end of the Data Send VCC
         clientConfigure -- The LE Client end of the Configure 
                            Direct VCC
         clientData -- One end of the Data Direct VCC
         clientDirect -- The LE Client end of the Control 
                         Direct VCC
         clientDistribute -- The LE Client end of the Control 
                             Distribute VCC
         clientForward -- The LE Client end of the Multicast 
                          Forward VCC
         clientSend -- The LE Client end of the Multicast 
                       Send VCC
         configure -- The Config Server end of any Configure VCC
         serverConfigure -- The LE Server end of the Configure VCC
         serverDirect -- The LE Server end of the Control 
                         Direct VCC."
    ::= { ciscoAtmVclEntry 23 }

ciscoAtmVclAtmInArpInterval OBJECT-TYPE
    SYNTAX INTEGER(0..60)
--  Units
--    minutes
    ACCESS read-write
    STATUS mandatory
    DESCRIPTION
        "Time interval in minutes to send InArp on a PVC for 
        IP over ATM.  0 will disable the InArp for this pvc."
    ::= { ciscoAtmVclEntry 24 }

ciscoAtmVclRemoteAddr OBJECT-TYPE
    SYNTAX NsapAtmAddr
--    Rsyntax OCTET STRING(SIZE(20))
    ACCESS read-write
    STATUS mandatory
    DESCRIPTION
        "Soft PVC target address if this is the calling side
        Soft PVC source address if this is called side. 
        Atomically set ConnState, RemoteAddr, RemoteVpi
        and RemoteVci will create or delete a soft PVC. 
        Atomically set ConnState, RemoteAddr without RemoteVpi,
        Remote Vci  will also create or delete a soft PVC but let 
        target switch assign the vpi and vci."
    ::= { ciscoAtmVclEntry 25 }

ciscoAtmVclRemoteVpi OBJECT-TYPE
    SYNTAX INTEGER(0..4095)
    ACCESS read-write
    STATUS mandatory
    DESCRIPTION
        "Soft PVC target VPI in calling side. 0 in called side."
    ::= { ciscoAtmVclEntry 26 }

ciscoAtmVclRemoteVci OBJECT-TYPE
    SYNTAX INTEGER(0..65535)
    ACCESS read-write
    STATUS mandatory
    DESCRIPTION
        "Soft PVC target VCI in calling side. 0 in called side."
    ::= { ciscoAtmVclEntry 27 }

ciscoAtmVclLocation OBJECT-TYPE
    SYNTAX Location
--    Rsyntax INTEGER {
--        unknown(1),
--        calling(2),
--        called(3)
--        }
    ACCESS read-only
    STATUS mandatory
    DESCRIPTION
        "Indicate calling or called side of a soft PVC.
         If ciscoAtmVclConfigType is not soft then 
         ciscoAtmVclLocation value should be ignored."
    ::= { ciscoAtmVclEntry 28 }

ciscoAtmVclSlowRetryIntv OBJECT-TYPE
    SYNTAX INTEGER(0..65535)
--  Units
--    seconds
    ACCESS read-write
    STATUS mandatory
    DESCRIPTION
        "Soft PVC slow retry interval in seconds."
    ::= { ciscoAtmVclEntry 29 }

ciscoAtmVclNumAttempts OBJECT-TYPE
    SYNTAX Counter
    ACCESS read-only
    STATUS mandatory
    DESCRIPTION
        "Number of retries made to install this soft PVC 
        connection.  If ciscoAtmVclConfigType is not soft then 
        ciscoAtmVclNumAttempts value should be ignored."
    ::= { ciscoAtmVclEntry 30 }

ciscoAtmVclLastReleaseCause OBJECT-TYPE
    SYNTAX INTEGER(1..127)
    ACCESS read-only
    STATUS mandatory
    DESCRIPTION
        "Value of the Cause field of the Cause
        Information Element in the last Release
        Signalling message received for this SPVC.
        Indicates the reason for the Release.
        ciscoAtmVclConfigType is not soft then 
        ciscoAtmVclLastReleaseCause value should be 
        ignored."
    ::= { ciscoAtmVclEntry 31 }

ciscoAtmVclUpcViolations OBJECT-TYPE
    SYNTAX Counter
    ACCESS read-only
    STATUS mandatory
    DESCRIPTION
        "The total number of nonconforming cells detected
         by Usage Parameter Control (UPC) for cells received
         on this VCL.
         On LS1010 systems, this counter is valid only on those
         equipped with the Feature Card - Per Flow Queueing."
    ::= { ciscoAtmVclEntry 32 }

ciscoAtmVclEpdTpdCellDrops OBJECT-TYPE
    SYNTAX Counter
    ACCESS read-only
    STATUS obsolete
    DESCRIPTION
        "Never implemented."
    ::= { ciscoAtmVclEntry 33 }

ciscoAtmVclEpdTpdPacketDrops OBJECT-TYPE
    SYNTAX Counter
    ACCESS read-only
    STATUS mandatory
    DESCRIPTION
        "The total number of EPD/TPD packet drops of
         packets received on this VCL.
         This counter is valid only:
          - if EPD is enabled on this VCL.
          - on LS1010 systems, only those equipped with 
            the Feature Card - Per Flow Queueing."
    ::= { ciscoAtmVclEntry 34 }

ciscoAtmVclEpdTpdPacketsIn OBJECT-TYPE
    SYNTAX Counter
    ACCESS read-only
    STATUS mandatory
    DESCRIPTION
        "The total number of packets received in their
         entirety on this VPL.
         This counter is valid only:
          - if EPD is enabled on this VCL.
          - on LS1010 systems, only those equipped with 
            the Feature Card - Per Flow Queueing."
    ::= { ciscoAtmVclEntry 35 }

ciscoAtmVclClp1Drops OBJECT-TYPE
    SYNTAX Counter
    ACCESS read-only
    STATUS obsolete
    DESCRIPTION
        "Never implemented."
    ::= { ciscoAtmVclEntry 37 }

ciscoAtmVclDefaultRxUpcTolerance OBJECT-TYPE
    SYNTAX INTEGER
    ACCESS read-only
    STATUS mandatory
    DESCRIPTION
        "If the tolerance (CDVT for CBR, ABR, UBR connections, Maximum 
         Burst Size for VBR connectons) requested for Usage 
         Parameter Control is not explicitly specified in VCL creation, 
         this object contains the default that is used.If tolerance
         is explicitly specified in VCL creation, it can be found in
         the Traffic Table row specified by atmVclReceiveTrafficDescrIndex,
         and the value of this object is -1."
    ::= { ciscoAtmVclEntry 38 }

ciscoAtmVclDefaultRxUpcVbrCdvt OBJECT-TYPE
    SYNTAX INTEGER
    ACCESS read-only
    STATUS mandatory
    DESCRIPTION
        "If the Cell Delay Variation Tolerance (CDVT) requested for 
         Usage Parameter Control for a VBR connection is not explicitly 
         specified in VCL creation, this object contains the default 
         that is used. If CDVT is explicitly specified in VCL creation, 
         it can be found in the Traffic Table row specified by 
         atmVclReceiveTrafficDescrIndex, and the value of this object 
         is -1."
    ::= { ciscoAtmVclEntry 39 }

ciscoAtmVclLsPerVcqWrrWeight OBJECT-TYPE
    SYNTAX INTEGER(1..15)
    ACCESS read-write
    STATUS mandatory
    DESCRIPTION
        "Configure the weighting specified for a VC half-leg
         within a service class to make the scheduling decision
         among other active VCLs in the service class. This
         is for transmit on the VCL on the interface. This object
         is defined only when the switch is equipped with 
         the Lightstream per-VC queueing chipset."
    ::= { ciscoAtmVclEntry 40 }

ciscoAtmVclLsPerVcqXmtQueuedCells OBJECT-TYPE
    SYNTAX Gauge
    ACCESS read-only
    STATUS mandatory
    DESCRIPTION
        "Number of cells received on this VCL and
         residing on the per-connection queue. Note that 
         this value is not valid until the VCL is in an 
         active cross-connect. This object
         is defined only when the switch is equipped with 
         the Lightstream per-VC queueing chipset."
    ::= { ciscoAtmVclEntry 41 }

ciscoAtmVclLsPerVcQThreshGrp OBJECT-TYPE
    SYNTAX LsPerVcqThresholdGroup
--    Rsyntax INTEGER {
--        tg1(1),
--        tg2(2),
--        tg3(3),
--        tg4(4),
--        tg5(5),
--        tg6(6),
--        tg7(7),
--        tg8(8),
--        tg9(9),
--        tg10(10),
--        tg11(11),
--        tg12(12),
--        tg13(13),
--        tg14(14),
--        tg15(15),
--        tg16(16)
--        }
    ACCESS read-only
    STATUS mandatory
    DESCRIPTION
        "The Threshold Group to which the cell-queue 
         for cells received by this VC are queued. 
         Note that this value is not valid until the 
         VCL is in an active cross-connect. This object
         is defined only when the switch is equipped with 
         the Lightstream per-VC queueing chipset."
    ::= { ciscoAtmVclEntry 42 }

ciscoAtmVclInClp0Cells OBJECT-TYPE
    SYNTAX Counter
    ACCESS read-only
    STATUS mandatory
    DESCRIPTION
        "The total number of cells with the CLP bit clear
         received on this VCL. Note that these cells may
         subsequently be discarded.
         This counter is valid only:
          - on LS1010 systems, only those equipped with 
            Feature Card - Per Flow Queueing."
    ::= { ciscoAtmVclEntry 43 }

ciscoAtmVclInClp1Cells OBJECT-TYPE
    SYNTAX Counter
    ACCESS read-only
    STATUS mandatory
    DESCRIPTION
        "The total number of cells with the CLP bit set
         received on this VCL. Note that these cells may
         subsequently be discarded.
         This counter is valid only:
          - on LS1010 systems, only those equipped with 
            Feature Card - Per Flow Queueing."
    ::= { ciscoAtmVclEntry 44 }

ciscoAtmVclOutClp0Cells OBJECT-TYPE
    SYNTAX Counter
    ACCESS read-only
    STATUS mandatory
    DESCRIPTION
        "The total number of cells with the CLP bit clear
         transmitted on this VCL.
         This counter is valid only:
          - on LS1010 systems, only those equipped with 
            Feature Card - Per Flow Queueing."
    ::= { ciscoAtmVclEntry 45 }

ciscoAtmVclOutClp1Cells OBJECT-TYPE
    SYNTAX Counter
    ACCESS read-only
    STATUS mandatory
    DESCRIPTION
        "The total number of cells with the CLP bit set
         transmitted on this VCL.
         This counter is valid only:
          - on LS1010 systems, only those equipped with 
            Feature Card - Per Flow Queueing."
    ::= { ciscoAtmVclEntry 46 }

ciscoAtmVclCellDrops OBJECT-TYPE
    SYNTAX Counter
    ACCESS read-only
    STATUS mandatory
    DESCRIPTION
        "The total number of cells received on this
         VCL, but discarded.
         This counter is valid only:
          - on LS1010 systems, only those equipped with 
            Feature Card - Per Flow Queueing."
    ::= { ciscoAtmVclEntry 47 }

ciscoAtmVclClp0VcqFullCellDrops OBJECT-TYPE
    SYNTAX Counter
    ACCESS read-only
    STATUS mandatory
    DESCRIPTION
        "The total number of cells received on this
         VCL with the CLP bit clear, discarded because
         the per-VC queue limit is exceeded.
         This counter is valid only:
          - if EPD is disabled on the VCL.
          - on LS1010 systems, only those equipped with 
            Feature Card - Per Flow Queueing."
    ::= { ciscoAtmVclEntry 48 }

ciscoAtmVclVcqClpThreshCellDrops OBJECT-TYPE
    SYNTAX Counter
    ACCESS read-only
    STATUS mandatory
    DESCRIPTION
        "The total number of cells received on this
         VCL, discarded because the discard threshold
         (as opposed to the queue-limit) is exceeded
         on the per-VC queue, and the CLP bit is set.
         This counter is valid only:
          - if EPD is disabled on the VCL.
          - on LS1010 systems, only those equipped with 
            Feature Card - Per Flow Queueing."
    ::= { ciscoAtmVclEntry 49 }

ciscoAtmVclRxNegTraffDescrIndex OBJECT-TYPE
    SYNTAX AtmTrafficDescrParamIndex
--    Rsyntax INTEGER
    ACCESS read-only
    STATUS mandatory
    DESCRIPTION
        "Identifies the entry in the atmTrafficDescrParamTable which
        contains negotiated traffic parameters applied to the receive
        direction of this VCL.
        
        This object is not instantiated if this VCL is not the calling
        side of a soft VC, or if there was no traffic negotiation."
    ::= { ciscoAtmVclEntry 50 }

ciscoAtmVclTxNegTraffDescrIndex OBJECT-TYPE
    SYNTAX AtmTrafficDescrParamIndex
--    Rsyntax INTEGER
    ACCESS read-only
    STATUS mandatory
    DESCRIPTION
        "Identifies the entry in the atmTrafficDescrParamTable which
        contains negotiated traffic parameters applied to the transmit
        direction of this VCL.
        
        This object is not instantiated if this VCL is not the calling
        side of a soft VC, or if there was no traffic negotiation."
    ::= { ciscoAtmVclEntry 51 }

ciscoAtmVclSwFabOutCells OBJECT-TYPE
    SYNTAX Counter
    ACCESS read-only
    STATUS mandatory
    DESCRIPTION
        "The total number of cells transmitted on 
        this VCL by the Switch Fabric.  This object is not 
        instantiated on systems that do not have support for 
        collecting such statistics."
    ::= { ciscoAtmVclEntry 52 }

ciscoAtmVclSwFabOutClp0Cells OBJECT-TYPE
    SYNTAX Counter
    ACCESS read-only
    STATUS mandatory
    DESCRIPTION
        "The total number of cells with the CLP bit clear
         transmitted on this VCL by the Switch Fabric.
         This object is not instantiated on systems 
         that do not have support for collecting such 
         statistics."
    ::= { ciscoAtmVclEntry 53 }

ciscoAtmVclSwFabOutClp1Cells OBJECT-TYPE
    SYNTAX Counter
    ACCESS read-only
    STATUS mandatory
    DESCRIPTION
        "The total number of cells with the CLP bit set
         transmitted on this VCL by the Switch Fabric.
         This object is not instantiated on systems that 
         do not have support for collecting such statistics."
    ::= { ciscoAtmVclEntry 54 }

ciscoAtmVclConnName OBJECT-TYPE
    SYNTAX SnmpAdminString
--    Rsyntax OCTET STRING(SIZE(0..255))
    ACCESS read-write
    STATUS mandatory
    DESCRIPTION
        "A human readable string that identifies this connection.
         This object will return a zero-length string if value is
         not set."
    ::= { ciscoAtmVclEntry 55 }

ciscoAtmVclConnType OBJECT-TYPE
    SYNTAX INTEGER {
        local(1),
        endToEnd(2)
        }
    ACCESS read-write
    STATUS mandatory
    DESCRIPTION
        "This object represent the PVC Type for this connection.
         - local     connection within the node
         - endToEnd  across several nodes.
         This object serves as an information object for a
         management system and has no functional meaning to
         the switch."
    ::= { ciscoAtmVclEntry 56 }

ciscoAtmSvpAddrTable OBJECT-TYPE
    SYNTAX SEQUENCE OF CiscoAtmSvpAddrEntry
    ACCESS not-accessible
    STATUS mandatory
    DESCRIPTION
        "Switched virtual path link address table."
    ::= { ciscoAtmSvp 1 }

ciscoAtmSvpAddrEntry OBJECT-TYPE
    SYNTAX CiscoAtmSvpAddrEntry
    ACCESS not-accessible
    STATUS mandatory
    DESCRIPTION
        " An entry in the Switched Vrtual Path address table."
    INDEX { ifIndex, ciscoAtmSvpAddr, ciscoAtmSvpVpi }
    ::= { ciscoAtmSvpAddrTable 1 }

CiscoAtmSvpAddrEntry ::= SEQUENCE {
    ciscoAtmSvpAddr OCTET STRING,
    ciscoAtmSvpVpi INTEGER,
    ciscoAtmSvpDirection Direction
    }

ciscoAtmSvpAddr OBJECT-TYPE
    SYNTAX OCTET STRING(SIZE(20))
    ACCESS not-accessible
    STATUS mandatory
    DESCRIPTION
        "It depends on the direction.This could be p2pCallingSide 
        address on a called side VPL, or p2pCalledSide address on a 
        calling side VPL or p2mpRoot address on a p2mp leaf side 
        VPL or p2mpLeaf address on a p2mp root side VPL."
    ::= { ciscoAtmSvpAddrEntry 1 }

ciscoAtmSvpVpi OBJECT-TYPE
    SYNTAX INTEGER(1..4095)
    ACCESS not-accessible
    STATUS mandatory
    DESCRIPTION
        "This SVP's VPI value on this interface."
    ::= { ciscoAtmSvpAddrEntry 2 }

ciscoAtmSvpDirection OBJECT-TYPE
    SYNTAX Direction
--    Rsyntax INTEGER {
--        unknown(1),
--        p2pCallingSide(2),
--        p2pCalledSide(3),
--        p2mpRoot(4),
--        p2mpLeaf(5)
--        }
    ACCESS read-only
    STATUS mandatory
    DESCRIPTION
        "Indicate whether this VPL is calling side, called side, 
        root or leaf for this address."
    ::= { ciscoAtmSvpAddrEntry 3 }

ciscoAtmSvcAddrTable OBJECT-TYPE
    SYNTAX SEQUENCE OF CiscoAtmSvcAddrEntry
    ACCESS not-accessible
    STATUS mandatory
    DESCRIPTION
        "Switched virtual channel link address table."
    ::= { ciscoAtmSvc 1 }

ciscoAtmSvcAddrEntry OBJECT-TYPE
    SYNTAX CiscoAtmSvcAddrEntry
    ACCESS not-accessible
    STATUS mandatory
    DESCRIPTION
        " An entry in the SVC address table."
    INDEX { ifIndex, ciscoAtmSvcAddr, ciscoAtmSvcVpi, ciscoAtmSvcVci }
    ::= { ciscoAtmSvcAddrTable 1 }

CiscoAtmSvcAddrEntry ::= SEQUENCE {
    ciscoAtmSvcAddr OCTET STRING,
    ciscoAtmSvcVpi INTEGER,
    ciscoAtmSvcVci INTEGER,
    ciscoAtmSvcDirection Direction
    }

ciscoAtmSvcAddr OBJECT-TYPE
    SYNTAX OCTET STRING(SIZE(20))
    ACCESS not-accessible
    STATUS mandatory
    DESCRIPTION
        "It depends on the direction.This could be p2pCallingSide 
        address on a called side VCL, or p2pCalledSide address on a 
        calling side VCL or p2mpRoot address on a p2mp leaf side VCL 
        or p2mpLeaf address on a p2mp root side VCL."
    ::= { ciscoAtmSvcAddrEntry 1 }

ciscoAtmSvcVpi OBJECT-TYPE
    SYNTAX INTEGER(0..4095)
    ACCESS not-accessible
    STATUS mandatory
    DESCRIPTION
        "This SVC's VPI value on this interface."
    ::= { ciscoAtmSvcAddrEntry 2 }

ciscoAtmSvcVci OBJECT-TYPE
    SYNTAX INTEGER(0..65535)
    ACCESS not-accessible
    STATUS mandatory
    DESCRIPTION
        "This SVC's VCI value on this interface."
    ::= { ciscoAtmSvcAddrEntry 3 }

ciscoAtmSvcDirection OBJECT-TYPE
    SYNTAX Direction
--    Rsyntax INTEGER {
--        unknown(1),
--        p2pCallingSide(2),
--        p2pCalledSide(3),
--        p2mpRoot(4),
--        p2mpLeaf(5)
--        }
    ACCESS read-only
    STATUS mandatory
    DESCRIPTION
        "Indicate whether this VCL is calling side, called side, 
        root or leaf for this address."
    ::= { ciscoAtmSvcAddrEntry 4 }

ciscoAtmSnoopVcTable OBJECT-TYPE
    SYNTAX SEQUENCE OF CiscoAtmSnoopVcEntry
    ACCESS not-accessible
    STATUS mandatory
    DESCRIPTION
        "Snooping VC Table."
    ::= { ciscoAtmSnoopVc 1 }

ciscoAtmSnoopVcEntry OBJECT-TYPE
    SYNTAX CiscoAtmSnoopVcEntry
    ACCESS not-accessible
    STATUS mandatory
    DESCRIPTION
        "An entry in the Snoop VC table. This entry models a VC snooping 
         connection. The  ifIndex indicates  the snooping interface, the
         atmVclVpi and atmVclVci  specifies the VPI and VCI value of the 
         snooping connection. To create or destroy a snooping connection 
         at an ATM interface, the following procedures are used:
        
         Configure VC Snooping
        
         A snooping connection is configured in one step by a set-request 
         with all necessary snoop parameter values and set-request to the 
         object ciscoAtmSnoopVcRowStatus to createAndGo(4). This may fail 
         for the following reasons:
              - The selected snooping VPI/VCI values are unavailable,
              - The selected snooping VPI/VCI values are in use.
              - The selected snooping interface is CPU interface. 
              - The selected snooped connection doesn't exist.
              - There is no traffic in the selected snoop direction.
              - Resource failure during configuration of snooping connection.
        
         De-Configure VC Snooping
        
         A snooping connection is deconfigured by a set-request to the 
         object ciscoAtmSnoopVcRowStatus to destroy(6), and the agent 
         releases all associated resources."
    INDEX { ifIndex, atmVclVpi, atmVclVci }
    ::= { ciscoAtmSnoopVcTable 1 }

CiscoAtmSnoopVcEntry ::= SEQUENCE {
    ciscoAtmSnoopVcSnoopedIfIndex InterfaceIndexOrZero,
    ciscoAtmSnoopVcSnoopedVpi INTEGER,
    ciscoAtmSnoopVcSnoopedVci INTEGER,
    ciscoAtmSnoopVcDir SnoopDirType,
    ciscoAtmSnoopVcState ConnState,
    ciscoAtmSnoopVcRowStatus RowStatus
    }

ciscoAtmSnoopVcSnoopedIfIndex OBJECT-TYPE
    SYNTAX InterfaceIndexOrZero
--    Rsyntax INTEGER(0..2147483647)
    ACCESS read-write
    STATUS mandatory
    DESCRIPTION
        "This specifies the ifIndex of the snooped interface."
    DEFVAL { 0 }
    ::= { ciscoAtmSnoopVcEntry 1 }

ciscoAtmSnoopVcSnoopedVpi OBJECT-TYPE
    SYNTAX INTEGER(0..4095)
    ACCESS read-write
    STATUS mandatory
    DESCRIPTION
        "This specifies the VPI value of the snooped connection endpoint."
    DEFVAL { 0 }
    ::= { ciscoAtmSnoopVcEntry 2 }

ciscoAtmSnoopVcSnoopedVci OBJECT-TYPE
    SYNTAX INTEGER(0..65535)
    ACCESS read-write
    STATUS mandatory
    DESCRIPTION
        "This specifies the VCI value of the snooped connection endpoint."
    DEFVAL { 0 }
    ::= { ciscoAtmSnoopVcEntry 3 }

ciscoAtmSnoopVcDir OBJECT-TYPE
    SYNTAX SnoopDirType
--    Rsyntax INTEGER {
--        transmit(1),
--        receive(2)
--        }
    ACCESS read-write
    STATUS mandatory
    DESCRIPTION
        "This specifies the traffic direction at the snooped connection 
         endpoint."
    DEFVAL { receive }
    ::= { ciscoAtmSnoopVcEntry 4 }

ciscoAtmSnoopVcState OBJECT-TYPE
    SYNTAX ConnState
--    Rsyntax INTEGER {
--        setup(1),
--        release(2),
--        notInstalled(3),
--        down(4),
--        up(5)
--        }
    ACCESS read-only
    STATUS mandatory
    DESCRIPTION
        "The connection state of this Snooping connetion."
    ::= { ciscoAtmSnoopVcEntry 5 }

ciscoAtmSnoopVcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an existing row 
         in this table. This gives the way to configure one-shot per-vc
         snooping connection"
    DEFVAL { active }
    ::= { ciscoAtmSnoopVcEntry 6 }

ciscoAtmSnoopVpTable OBJECT-TYPE
    SYNTAX SEQUENCE OF CiscoAtmSnoopVpEntry
    ACCESS not-accessible
    STATUS mandatory
    DESCRIPTION
        "Snooping VP Table."
    ::= { ciscoAtmSnoopVp 1 }

ciscoAtmSnoopVpEntry OBJECT-TYPE
    SYNTAX CiscoAtmSnoopVpEntry
    ACCESS not-accessible
    STATUS mandatory
    DESCRIPTION
        "An entry in the Snoop VP table. This entry models a VP snooping 
         connection. The  ifIndex indicates  the snooping interface, the
         atmVclVpi specifies the VPI value of the snooping connection. To 
         create or destroy a snooping connection at an ATM interface, the 
         following procedures are used:
        
         Configure VP Snooping
        
         A snooping connection is configured in one step by a set-request 
         with all necessary snoop parameter values and set-request to the 
         object ciscoAtmSnoopVpRowStatus to createAndGo(4). This may fail 
         for the following reasons:
              - The selected snooping VPI values are unavailable,
              - The selected snooping VPI values are in use.
              - The selected snooping interface is CPU interface. 
              - The selected snooped connection doesn't exist.
              - There is no traffic in the selected snoop direction.
              - Resource failure during configuration of snooping connection.
        
         De-Configure VP Snooping
        
         A snooping connection is deconfigured by a set-request to the 
         object ciscoAtmSnoopVpRowStatus to destroy(6), and the agent 
         releases all associated resources."
    INDEX { ifIndex, atmVplVpi }
    ::= { ciscoAtmSnoopVpTable 1 }

CiscoAtmSnoopVpEntry ::= SEQUENCE {
    ciscoAtmSnoopVpSnoopedIfIndex InterfaceIndexOrZero,
    ciscoAtmSnoopVpSnoopedVpi INTEGER,
    ciscoAtmSnoopVpDir SnoopDirType,
    ciscoAtmSnoopVpState ConnState,
    ciscoAtmSnoopVpRowStatus RowStatus
    }

ciscoAtmSnoopVpSnoopedIfIndex OBJECT-TYPE
    SYNTAX InterfaceIndexOrZero
--    Rsyntax INTEGER(0..2147483647)
    ACCESS read-write
    STATUS mandatory
    DESCRIPTION
        "This specifies the ifIndex of the snooped interface."
    DEFVAL { 0 }
    ::= { ciscoAtmSnoopVpEntry 1 }

ciscoAtmSnoopVpSnoopedVpi OBJECT-TYPE
    SYNTAX INTEGER(0..4095)
    ACCESS read-write
    STATUS mandatory
    DESCRIPTION
        "This specifies the VPI value of the snooped connection endpoint."
    DEFVAL { 0 }
    ::= { ciscoAtmSnoopVpEntry 2 }

ciscoAtmSnoopVpDir OBJECT-TYPE
    SYNTAX SnoopDirType
--    Rsyntax INTEGER {
--        transmit(1),
--        receive(2)
--        }
    ACCESS read-write
    STATUS mandatory
    DESCRIPTION
        "This specifies the traffic direction at the snooped connection 
         endpoint."
    DEFVAL { receive }
    ::= { ciscoAtmSnoopVpEntry 3 }

ciscoAtmSnoopVpState OBJECT-TYPE
    SYNTAX ConnState
--    Rsyntax INTEGER {
--        setup(1),
--        release(2),
--        notInstalled(3),
--        down(4),
--        up(5)
--        }
    ACCESS read-only
    STATUS mandatory
    DESCRIPTION
        "The connection state of this Snooping connection ."
    ::= { ciscoAtmSnoopVpEntry 4 }

ciscoAtmSnoopVpRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        "This object is used to create a new row or delete an existing row 
         in this table. This gives the way to configure one-shot per-vp
         snooping connection"
    DEFVAL { active }
    ::= { ciscoAtmSnoopVpEntry 5 }

ciscoAtmSvcFrameDiscardUsesAal5Ie OBJECT-TYPE
    SYNTAX TruthValue
--    Rsyntax INTEGER {
--        true(1),
--        false(2)
--        }
    ACCESS read-write
    STATUS mandatory
    DESCRIPTION
        "Determines mechanism to use on interfaces
         to specify frame discard.
        
         Specifying a value of true causes the presence
         of the AAL5 IE to influence whether frame discard
         is used on an SVC. If AAL5 IE is present in a received
         SETUP, frame discard is used.
        
         Specifying a value of false results in no influence on
         presence of the frame discard by the AAL5 IE."
    DEFVAL { true }
    ::= { ciscoAtmSvc 2 }

ciscoAtmConnMIBGroup OBJECT IDENTIFIER ::= { ciscoAtmConnMIBGroups 1 }
-- OBJECT-GROUP
--  Status
--    deprecated
--  objects
--    ciscoAtmVplCastType, ciscoAtmVplSpanType, 
--    ciscoAtmVplConfigType, ciscoAtmVplRxUpcMode, 
--    ciscoAtmVplConnState, ciscoAtmVplOamLoopbkTxInterval, 
--    ciscoAtmVplOamSegmentLoopback, ciscoAtmVplOamEndLoopback, 
--    ciscoAtmVplOamAisEnable, ciscoAtmVplOamRdiEnable, 
--    ciscoAtmVplInstallTime, ciscoAtmVplInCells, 
--    ciscoAtmVplOutCells, ciscoAtmVplCrossIfIndex, 
--    ciscoAtmVplCrossVpi, ciscoAtmVplNextLeafIfIndex, 
--    ciscoAtmVplNextLeafVpi, ciscoAtmVplRemoteAddr, 
--    ciscoAtmVplRemoteVpi, ciscoAtmVplLocation, 
--    ciscoAtmVplSlowRetryIntv, ciscoAtmVplNumAttempts, 
--    ciscoAtmVplLastReleaseCause, ciscoAtmVplLogicalPortDef, 
--    ciscoAtmVplLogicalPortIndex, ciscoAtmVclCastType, 
--    ciscoAtmVclSpanType, ciscoAtmVclConfigType, 
--    ciscoAtmVclRxUpcMode, ciscoAtmVclEpdEnable, 
--    ciscoAtmVclConnState, ciscoAtmVclOamLoopbkTxInterval, 
--    ciscoAtmVclOamSegmentLoopback, ciscoAtmVclOamEndLoopback, 
--    ciscoAtmVclOamAisEnable, ciscoAtmVclOamRdiEnable, 
--    ciscoAtmVclInstallTime, ciscoAtmVclInCells, 
--    ciscoAtmVclOutCells, ciscoAtmVclCrossIfIndex, 
--    ciscoAtmVclCrossVpi, ciscoAtmVclCrossVci, 
--    ciscoAtmVclNextLeafIfIndex, ciscoAtmVclNextLeafVpi, 
--    ciscoAtmVclNextLeafVci, ciscoAtmVclAalEncapFlag, 
--    ciscoAtmVclAalEncapProtocol, ciscoAtmVclAalUserVcType, 
--    ciscoAtmVclAtmInArpInterval, ciscoAtmVclRemoteAddr, 
--    ciscoAtmVclRemoteVpi, ciscoAtmVclRemoteVci, 
--    ciscoAtmVclLocation, ciscoAtmVclSlowRetryIntv, 
--    ciscoAtmVclNumAttempts, ciscoAtmVclLastReleaseCause, 
--    ciscoAtmSvpDirection, ciscoAtmSvcDirection

ciscoAtmConnMIBGroup2 OBJECT IDENTIFIER ::= { ciscoAtmConnMIBGroups 2 }
-- OBJECT-GROUP
--  Status
--    obsolete
--  objects
--    ciscoAtmVplUpcViolations, ciscoAtmVplEpdTpdCellDrops, 
--    ciscoAtmVplEpdTpdPacketDrops, ciscoAtmVplEpdTpdPacketsIn, 
--    ciscoAtmVplClp1Drops, ciscoAtmVplDefaultRxUpcTolerance, 
--    ciscoAtmVclUpcViolations, ciscoAtmVclEpdTpdCellDrops, 
--    ciscoAtmVclEpdTpdPacketDrops, ciscoAtmVclEpdTpdPacketsIn, 
--    ciscoAtmVclClp1Drops, ciscoAtmVclDefaultRxUpcTolerance, 
--    ciscoAtmSvcFrameDiscardUsesAal5Ie

ciscoAtmConnMIBGroup3 OBJECT IDENTIFIER ::= { ciscoAtmConnMIBGroups 3 }
-- OBJECT-GROUP
--  Status
--    mandatory
--  objects
--    ciscoAtmVplDefaultRxUpcTolerance, 
--    ciscoAtmVclDefaultRxUpcTolerance, 
--    ciscoAtmVplDefaultRxUpcVbrCdvt, 
--    ciscoAtmVclDefaultRxUpcVbrCdvt, 
--    ciscoAtmSvcFrameDiscardUsesAal5Ie

ciscoAtmConnMIBlsPerVcqGroup OBJECT IDENTIFIER ::= { ciscoAtmConnMIBGroups 4 }
-- OBJECT-GROUP
--  Status
--    obsolete
--  Descr
--    A collection of objects which are supported on platforms
--     using the Lightstream per-VC queueing chipset.
--  objects
--    ciscoAtmVplLsPerVcqWrrWeight, 
--    ciscoAtmVplLsPerVcqTunnelIsShaped, 
--    ciscoAtmVplLsPerVcqXmtQueuedCells, 
--    ciscoAtmVplLsPerVcQThreshGrp, ciscoAtmVclLsPerVcqWrrWeight, 
--    ciscoAtmVclLsPerVcqXmtQueuedCells, 
--    ciscoAtmVclLsPerVcQThreshGrp, ciscoAtmSnoopVcSnoopedIfIndex, 
--    ciscoAtmSnoopVcSnoopedVpi, ciscoAtmSnoopVcSnoopedVci, 
--    ciscoAtmSnoopVcDir, ciscoAtmSnoopVcState, 
--    ciscoAtmSnoopVcRowStatus, ciscoAtmSnoopVpSnoopedIfIndex, 
--    ciscoAtmSnoopVpSnoopedVpi, ciscoAtmSnoopVpDir, 
--    ciscoAtmSnoopVpState, ciscoAtmSnoopVpRowStatus

ciscoAtmConnMIBlsFcPfqGroup OBJECT IDENTIFIER ::= { ciscoAtmConnMIBGroups 5 }
-- OBJECT-GROUP
--  Status
--    deprecated
--  Descr
--    A collection of objects which are supported on LS1010 systems
--     equipped with the FC-PFQ feature card.
--  objects
--    ciscoAtmVplUpcViolations, ciscoAtmVclUpcViolations, 
--    ciscoAtmVclEpdTpdPacketDrops, ciscoAtmVclEpdTpdPacketsIn, 
--    ciscoAtmVplInClp0Cells, ciscoAtmVplInClp1Cells, 
--    ciscoAtmVplOutClp0Cells, ciscoAtmVplOutClp1Cells, 
--    ciscoAtmVplCellDrops, ciscoAtmVplClp0VcqFullCellDrops, 
--    ciscoAtmVplVcqClpThreshCellDrops, ciscoAtmVclInClp0Cells, 
--    ciscoAtmVclInClp1Cells, ciscoAtmVclOutClp0Cells, 
--    ciscoAtmVclOutClp1Cells, ciscoAtmVclCellDrops, 
--    ciscoAtmVclClp0VcqFullCellDrops, 
--    ciscoAtmVclVcqClpThreshCellDrops

ciscoAtmConnMIBlsPerVcqGroup2 OBJECT IDENTIFIER ::= { ciscoAtmConnMIBGroups 6 }
-- OBJECT-GROUP
--  Status
--    mandatory
--  Descr
--    A collection of objects which are supported on platforms
--     using the Lightstream per-VC queueing chipset.
--  objects
--    ciscoAtmVplLsPerVcqWrrWeight, 
--    ciscoAtmVplLsPerVcqTunnelIsShaped, 
--    ciscoAtmVplLsPerVcqTunnelIsHierarchical, 
--    ciscoAtmVplLsPerVcqXmtQueuedCells, 
--    ciscoAtmVplLsPerVcQThreshGrp, ciscoAtmVclLsPerVcqWrrWeight, 
--    ciscoAtmVclLsPerVcqXmtQueuedCells, 
--    ciscoAtmVclLsPerVcQThreshGrp, ciscoAtmSnoopVcSnoopedIfIndex, 
--    ciscoAtmSnoopVcSnoopedVpi, ciscoAtmSnoopVcSnoopedVci, 
--    ciscoAtmSnoopVcDir, ciscoAtmSnoopVcState, 
--    ciscoAtmSnoopVcRowStatus, ciscoAtmSnoopVpSnoopedIfIndex, 
--    ciscoAtmSnoopVpSnoopedVpi, ciscoAtmSnoopVpDir, 
--    ciscoAtmSnoopVpState, ciscoAtmSnoopVpRowStatus

ciscoAtmConnMIBNegTraffGroup OBJECT IDENTIFIER ::= { ciscoAtmConnMIBGroups 7 }
-- OBJECT-GROUP
--  Status
--    mandatory
--  Descr
--    A collection of objects to report negotiated traffic parameters
--     on a Cisco ATM switch.
--  objects
--    ciscoAtmVplRxNegTraffDescrIndex, 
--    ciscoAtmVplTxNegTraffDescrIndex, 
--    ciscoAtmVclRxNegTraffDescrIndex, 
--    ciscoAtmVclTxNegTraffDescrIndex

ciscoAtmConnMIBlsFcPfqGroup1 OBJECT IDENTIFIER ::= { ciscoAtmConnMIBGroups 8 }
-- OBJECT-GROUP
--  Status
--    mandatory
--  Descr
--    A collection of objects which are supported on LS1010 systems
--     equipped with the FC-PFQ feature card.
--  objects
--    ciscoAtmVplUpcViolations, ciscoAtmVclUpcViolations, 
--    ciscoAtmVclEpdTpdPacketDrops, ciscoAtmVclEpdTpdPacketsIn, 
--    ciscoAtmVplInClp0Cells, ciscoAtmVplInClp1Cells, 
--    ciscoAtmVplOutClp0Cells, ciscoAtmVplOutClp1Cells, 
--    ciscoAtmVplCellDrops, ciscoAtmVplClp0VcqFullCellDrops, 
--    ciscoAtmVplVcqClpThreshCellDrops, ciscoAtmVplSwFabOutCells, 
--    ciscoAtmVplSwFabOutClp0Cells, ciscoAtmVplSwFabOutClp1Cells, 
--    ciscoAtmVclInClp0Cells, ciscoAtmVclInClp1Cells, 
--    ciscoAtmVclOutClp0Cells, ciscoAtmVclOutClp1Cells, 
--    ciscoAtmVclCellDrops, ciscoAtmVclClp0VcqFullCellDrops, 
--    ciscoAtmVclVcqClpThreshCellDrops, ciscoAtmVclSwFabOutCells, 
--    ciscoAtmVclSwFabOutClp0Cells, ciscoAtmVclSwFabOutClp1Cells

ciscoAtmConnMIBGroup1 OBJECT IDENTIFIER ::= { ciscoAtmConnMIBGroups 9 }
-- OBJECT-GROUP
--  Status
--    deprecated
--  objects
--    ciscoAtmVplCastType, ciscoAtmVplSpanType, 
--    ciscoAtmVplConfigType, ciscoAtmVplRxUpcMode, 
--    ciscoAtmVplConnState, ciscoAtmVplOamLoopbkTxInterval, 
--    ciscoAtmVplOamSegmentLoopback, ciscoAtmVplOamEndLoopback, 
--    ciscoAtmVplOamAisEnable, ciscoAtmVplOamRdiEnable, 
--    ciscoAtmVplInstallTime, ciscoAtmVplInCells, 
--    ciscoAtmVplOutCells, ciscoAtmVplCrossIfIndex, 
--    ciscoAtmVplCrossVpi, ciscoAtmVplNextLeafIfIndex, 
--    ciscoAtmVplNextLeafVpi, ciscoAtmVplRemoteAddr, 
--    ciscoAtmVplRemoteVpi, ciscoAtmVplLocation, 
--    ciscoAtmVplSlowRetryIntv, ciscoAtmVplNumAttempts, 
--    ciscoAtmVplLastReleaseCause, ciscoAtmVplLogicalPortDef, 
--    ciscoAtmVplLogicalPortIndex, ciscoAtmVplConnName, 
--    ciscoAtmVclCastType, ciscoAtmVclSpanType, 
--    ciscoAtmVclConfigType, ciscoAtmVclRxUpcMode, 
--    ciscoAtmVclEpdEnable, ciscoAtmVclConnState, 
--    ciscoAtmVclOamLoopbkTxInterval, ciscoAtmVclOamSegmentLoopback, 
--    ciscoAtmVclOamEndLoopback, ciscoAtmVclOamAisEnable, 
--    ciscoAtmVclOamRdiEnable, ciscoAtmVclInstallTime, 
--    ciscoAtmVclInCells, ciscoAtmVclOutCells, 
--    ciscoAtmVclCrossIfIndex, ciscoAtmVclCrossVpi, 
--    ciscoAtmVclCrossVci, ciscoAtmVclNextLeafIfIndex, 
--    ciscoAtmVclNextLeafVpi, ciscoAtmVclNextLeafVci, 
--    ciscoAtmVclAalEncapFlag, ciscoAtmVclAalEncapProtocol, 
--    ciscoAtmVclAalUserVcType, ciscoAtmVclAtmInArpInterval, 
--    ciscoAtmVclRemoteAddr, ciscoAtmVclRemoteVpi, 
--    ciscoAtmVclRemoteVci, ciscoAtmVclLocation, 
--    ciscoAtmVclSlowRetryIntv, ciscoAtmVclNumAttempts, 
--    ciscoAtmVclLastReleaseCause, ciscoAtmVclConnName, 
--    ciscoAtmSvpDirection, ciscoAtmSvcDirection

ciscoAtmConnMIBGroup4 OBJECT IDENTIFIER ::= { ciscoAtmConnMIBGroups 10 }
-- OBJECT-GROUP
--  Status
--    mandatory
--  objects
--    ciscoAtmVplCastType, ciscoAtmVplSpanType, 
--    ciscoAtmVplConfigType, ciscoAtmVplRxUpcMode, 
--    ciscoAtmVplConnState, ciscoAtmVplOamLoopbkTxInterval, 
--    ciscoAtmVplOamSegmentLoopback, ciscoAtmVplOamEndLoopback, 
--    ciscoAtmVplOamAisEnable, ciscoAtmVplOamRdiEnable, 
--    ciscoAtmVplInstallTime, ciscoAtmVplInCells, 
--    ciscoAtmVplOutCells, ciscoAtmVplCrossIfIndex, 
--    ciscoAtmVplCrossVpi, ciscoAtmVplNextLeafIfIndex, 
--    ciscoAtmVplNextLeafVpi, ciscoAtmVplRemoteAddr, 
--    ciscoAtmVplRemoteVpi, ciscoAtmVplLocation, 
--    ciscoAtmVplSlowRetryIntv, ciscoAtmVplNumAttempts, 
--    ciscoAtmVplLastReleaseCause, ciscoAtmVplLogicalPortDef, 
--    ciscoAtmVplLogicalPortIndex, ciscoAtmVclCastType, 
--    ciscoAtmVclSpanType, ciscoAtmVclConfigType, 
--    ciscoAtmVclRxUpcMode, ciscoAtmVclEpdEnable, 
--    ciscoAtmVclConnState, ciscoAtmVclOamLoopbkTxInterval, 
--    ciscoAtmVclOamSegmentLoopback, ciscoAtmVclOamEndLoopback, 
--    ciscoAtmVclOamAisEnable, ciscoAtmVclOamRdiEnable, 
--    ciscoAtmVclInstallTime, ciscoAtmVclInCells, 
--    ciscoAtmVclOutCells, ciscoAtmVclCrossIfIndex, 
--    ciscoAtmVclCrossVpi, ciscoAtmVclCrossVci, 
--    ciscoAtmVclNextLeafIfIndex, ciscoAtmVclNextLeafVpi, 
--    ciscoAtmVclNextLeafVci, ciscoAtmVclAalEncapFlag, 
--    ciscoAtmVclAalEncapProtocol, ciscoAtmVclAalUserVcType, 
--    ciscoAtmVclAtmInArpInterval, ciscoAtmVclRemoteAddr, 
--    ciscoAtmVclRemoteVpi, ciscoAtmVclRemoteVci, 
--    ciscoAtmVclLocation, ciscoAtmVclSlowRetryIntv, 
--    ciscoAtmVclNumAttempts, ciscoAtmVclLastReleaseCause, 
--    ciscoAtmSvpDirection, ciscoAtmSvcDirection

ciscoAtmConnNmsGroup OBJECT IDENTIFIER ::= { ciscoAtmConnMIBGroups 11 }
-- OBJECT-GROUP
--  Status
--    mandatory
--  Descr
--    A group of objects that provides additional information
--     for a management system
--  objects
--    ciscoAtmVplConnName, ciscoAtmVplConnType, ciscoAtmVclConnName, 
--    ciscoAtmVclConnType

ciscoAtmConnMIBCompliance OBJECT IDENTIFIER ::= { ciscoAtmConnMIBCompliances 1 }
-- MODULE-COMPLIANCE
--  Status
--    obsolete
--  Descr
--    The compliance statement for the Cisco ATM connection 
--    management group.
--  Module
--    >>current<<
--   MandGroup
--    ciscoAtmConnMIBGroup

ciscoAtmConnMIBCompliance2 OBJECT IDENTIFIER ::= { ciscoAtmConnMIBCompliances 2 }
-- MODULE-COMPLIANCE
--  Status
--    obsolete
--  Descr
--    The compliance statement for the Cisco ATM connection 
--    management group.
--  Module
--    >>current<<
--   MandGroup
--    ciscoAtmConnMIBGroup
--   MandGroup
--    ciscoAtmConnMIBGroup2

ciscoAtmConnMIBCompliance3 OBJECT IDENTIFIER ::= { ciscoAtmConnMIBCompliances 3 }
-- MODULE-COMPLIANCE
--  Status
--    obsolete
--  Descr
--    The compliance statement for the Cisco ATM connection
--    management group.
--  Module
--    >>current<<
--   MandGroup
--    ciscoAtmConnMIBGroup
--   MandGroup
--    ciscoAtmConnMIBGroup3
--   MandGroup
--    ciscoAtmConnMIBlsPerVcqGroup
--   MandGroup
--    ciscoAtmConnMIBlsFcPfqGroup

ciscoAtmConnMIBCompliance4 OBJECT IDENTIFIER ::= { ciscoAtmConnMIBCompliances 4 }
-- MODULE-COMPLIANCE
--  Status
--    obsolete
--  Descr
--    The compliance statement for the Cisco ATM connection
--    management group.
--  Module
--    >>current<<
--   MandGroup
--    ciscoAtmConnMIBGroup
--   MandGroup
--    ciscoAtmConnMIBGroup3
--   MandGroup
--    ciscoAtmConnMIBlsPerVcqGroup2
--   MandGroup
--    ciscoAtmConnMIBlsFcPfqGroup

ciscoAtmConnMIBCompliance5 OBJECT IDENTIFIER ::= { ciscoAtmConnMIBCompliances 5 }
-- MODULE-COMPLIANCE
--  Status
--    deprecated
--  Descr
--    The compliance statement for the Cisco ATM connection
--    management group.
--  Module
--    >>current<<
--   MandGroup
--    ciscoAtmConnMIBGroup
--   MandGroup
--    ciscoAtmConnMIBGroup3
--   MandGroup
--    ciscoAtmConnMIBlsPerVcqGroup2
--   MandGroup
--    ciscoAtmConnMIBlsFcPfqGroup
--   MandGroup
--    ciscoAtmConnMIBNegTraffGroup

ciscoAtmConnMIBCompliance6 OBJECT IDENTIFIER ::= { ciscoAtmConnMIBCompliances 6 }
-- MODULE-COMPLIANCE
--  Status
--    deprecated
--  Descr
--    The compliance statement for the Cisco ATM connection
--    management group.
--  Module
--    >>current<<
--   MandGroup
--    ciscoAtmConnMIBGroup
--   MandGroup
--    ciscoAtmConnMIBGroup3
--   MandGroup
--    ciscoAtmConnMIBlsPerVcqGroup2
--   MandGroup
--    ciscoAtmConnMIBlsFcPfqGroup1
--   MandGroup
--    ciscoAtmConnMIBNegTraffGroup

ciscoAtmConnMIBCompliance7 OBJECT IDENTIFIER ::= { ciscoAtmConnMIBCompliances 7 }
-- MODULE-COMPLIANCE
--  Status
--    deprecated
--  Descr
--    The compliance statement for the Cisco ATM connection
--    management group.
--  Module
--    >>current<<
--   MandGroup
--    ciscoAtmConnMIBGroup1
--   MandGroup
--    ciscoAtmConnMIBGroup3
--   MandGroup
--    ciscoAtmConnMIBlsPerVcqGroup2
--   MandGroup
--    ciscoAtmConnMIBlsFcPfqGroup1
--   MandGroup
--    ciscoAtmConnMIBNegTraffGroup

ciscoAtmConnMIBCompliance8 OBJECT IDENTIFIER ::= { ciscoAtmConnMIBCompliances 8 }
-- MODULE-COMPLIANCE
--  Status
--    mandatory
--  Descr
--    The compliance statement for the Cisco ATM connection
--    management group.
--  Module
--    >>current<<
--   MandGroup
--    ciscoAtmConnMIBGroup4
--   MandGroup
--    ciscoAtmConnMIBGroup3
--   MandGroup
--    ciscoAtmConnMIBlsPerVcqGroup2
--   MandGroup
--    ciscoAtmConnMIBlsFcPfqGroup1
--   MandGroup
--    ciscoAtmConnMIBNegTraffGroup
--   OptGroup
--    ciscoAtmConnNmsGroup


END
