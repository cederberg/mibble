-- MIB created 6/25/99 12:57:49, by
--   SMIC (the next generation) version 1.6.29, November 22, 1994.

CISCO-VOICE-IF-MIB DEFINITIONS ::= BEGIN

-- From file: "CISCO-VOICE-IF-MIB.my"

IMPORTS
    Integer32
            FROM SNMPv2-SMI-v1
    OBJECT-TYPE
            FROM RFC-1212
    TruthValue, DisplayString
            FROM SNMPv2-TC-v1
    ifIndex
            FROM IF-MIB
    CountryCode
            FROM CISCO-TC
    ciscoMgmt
            FROM CISCO-SMI;

ciscoVoiceInterfaceMIB OBJECT IDENTIFIER ::= { ciscoMgmt 64 }
-- MODULE-IDENTITY
--  LastUpdated
--    9803060000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-voice@cisco.com
--  Descr
--    Common Voice Interface MIB module.
--     The MIB module manages the common voice related parameters
--     for both voice analog and ISDN interfaces.

cvIfObjects     OBJECT IDENTIFIER ::= { ciscoVoiceInterfaceMIB 1 }
cvIfCfgObjects  OBJECT IDENTIFIER ::= { cvIfObjects 1 }
cvIfConformance OBJECT IDENTIFIER ::= { ciscoVoiceInterfaceMIB 2 }
cvIfCompliances OBJECT IDENTIFIER ::= { cvIfConformance 1 }
cvIfGroups      OBJECT IDENTIFIER ::= { cvIfConformance 2 }

cvIfCfgTable OBJECT-TYPE
    SYNTAX SEQUENCE OF CvIfCfgEntry
    ACCESS not-accessible
    STATUS mandatory
    DESCRIPTION
        "The Voice Common Configuration Table. It contains information
         about the voice related configuration parameters for
         both analog and digital telephony interfaces. "
    ::= { cvIfCfgObjects 1 }

cvIfCfgEntry OBJECT-TYPE
    SYNTAX CvIfCfgEntry
    ACCESS not-accessible
    STATUS mandatory
    DESCRIPTION
        "An entry in the configuration table for each voice analog
         interface or voice feature associated ISDN signalling channel.
         The entry is automatically created when a voice analog interface
         hardware is found or ISDN signalling channel is configured
         and the ISDN associated voice support hardware is detected 
         by the managed system.
         For the ISDN signalling channel associated entry, the entry
         is deleted after ISDN signalling channel is removed. "
    INDEX { ifIndex }
    ::= { cvIfCfgTable 1 }

CvIfCfgEntry ::= SEQUENCE {
    cvIfCfgNoiseRegEnable TruthValue,
    cvIfCfgNonLinearProcEnable TruthValue,
    cvIfCfgMusicOnHoldThreshold Integer32,
    cvIfCfgInGain Integer32,
    cvIfCfgOutAttn Integer32,
    cvIfCfgEchoCancelEnable TruthValue,
    cvIfCfgEchoCancelCoverage INTEGER,
    cvIfCfgConnectionMode INTEGER,
    cvIfCfgConnectionNumber DisplayString,
    cvIfCfgInitialDigitTimeOut Integer32,
    cvIfCfgInterDigitTimeOut Integer32,
    cvIfCfgRegionalTone CountryCode
    }

cvIfCfgNoiseRegEnable OBJECT-TYPE
    SYNTAX TruthValue
--    Rsyntax INTEGER {
--        true(1),
--        false(2)
--        }
    ACCESS read-write
    STATUS mandatory
    DESCRIPTION
        "The object indicates whether or not the background noise should
         be played to fill silence gaps if VAD is activated.
         The default value of this object is enabled."
    ::= { cvIfCfgEntry 1 }

cvIfCfgNonLinearProcEnable OBJECT-TYPE
    SYNTAX TruthValue
--    Rsyntax INTEGER {
--        true(1),
--        false(2)
--        }
    ACCESS read-write
    STATUS mandatory
    DESCRIPTION
        "The object indicates whether or not the Nonlinear Processing
         is enabled for the interface.
         The default value of this object is enabled."
    ::= { cvIfCfgEntry 2 }

cvIfCfgMusicOnHoldThreshold OBJECT-TYPE
    SYNTAX Integer32(-70..-30)
--  Units
--    dBm
    ACCESS read-write
    STATUS mandatory
    DESCRIPTION
        "The object specifies the Music On Hold Threshold for
         the interface.
         The default value of this object is -38 dBm."
    ::= { cvIfCfgEntry 3 }

cvIfCfgInGain OBJECT-TYPE
    SYNTAX Integer32(-6..14)
--  Units
--    dB
    ACCESS read-write
    STATUS mandatory
    DESCRIPTION
        "This object contains the amount of gain inserted at the
         receiver side of the interface. The input gain settings
         only define a gain/loss relative to the 0 dB setting.
         The absolute loss at the 0 dB setting could be implementation
         dependent based on the desired network loss plan.
         The default value of this object is 0 dB (decibel)."
    ::= { cvIfCfgEntry 4 }

cvIfCfgOutAttn OBJECT-TYPE
    SYNTAX Integer32(0..14)
--  Units
--    dB
    ACCESS read-write
    STATUS mandatory
    DESCRIPTION
        "This object contains the amount of attenuation inserted at the
         transmit side of the interface. 
         The output attenuation settings only define a loss 
         relative to the 0 dB setting.
         The absolute loss at the 0 dB setting could be implementation
         dependent based on the desired network loss plan.
         The default value of this object is 0 dB (decibel)."
    ::= { cvIfCfgEntry 5 }

cvIfCfgEchoCancelEnable OBJECT-TYPE
    SYNTAX TruthValue
--    Rsyntax INTEGER {
--        true(1),
--        false(2)
--        }
    ACCESS read-write
    STATUS mandatory
    DESCRIPTION
        "The object specifies whether or not the Echo Cancellation 
         is enabled for the interface.
         The default value of this object is enabled."
    ::= { cvIfCfgEntry 6 }

cvIfCfgEchoCancelCoverage OBJECT-TYPE
    SYNTAX INTEGER {
        echoCanceller16ms(1),
        echoCanceller24ms(2),
        echoCanceller32ms(3)
        }
    ACCESS read-write
    STATUS mandatory
    DESCRIPTION
        "The object specifies the Echo Canceller coverage for
         the interface. This object is valid if the
         cvIfCfgEchoCancelEnable object is 'true'.
         echoCanceller16ms - 16 milliseconds echo canceller coverage.
         echoCanceller24ms - 24 milliseconds echo canceller coverage.
         echoCanceller32ms - 32 milliseconds echo canceller coverage.
         The default value of this object is echoCanceller16ms."
    ::= { cvIfCfgEntry 7 }

cvIfCfgConnectionMode OBJECT-TYPE
    SYNTAX INTEGER {
        normal(1),
        trunk(2),
        plar(3)
        }
    ACCESS read-write
    STATUS mandatory
    DESCRIPTION
        "The object indicates the connection mode of the interface.
         normal - the interface acts normally to handle incoming
                  and outgoing call.
         trunk  - the interface acts in trunking mode. trunking mode
                  causes two interfaces (on either the same or different
                  routers) to be always conferenced together, and for
                  telephony signaling to be passed transparently through
                  the VoIP system rather than trapped and interpreted by
                  the session application on the router(s).
         plar   - the interface acts in PLAR (private line automatic
                  ringdown) mode. PLAR is handled by associating a
                  peer directly with an interface such that when the
                  interface goes off-hook, that peer is used to setup
                  the second call leg and conference them together
                  without the caller having to dial any digits."
    ::= { cvIfCfgEntry 8 }

cvIfCfgConnectionNumber OBJECT-TYPE
    SYNTAX DisplayString(SIZE(0..32))
--    Rsyntax OCTET STRING(SIZE(0..32))
    ACCESS read-write
    STATUS mandatory
    DESCRIPTION
        "This is the E.164 phone number that is used to 
         establish connection with trunking mode or PLAR mode.
         If the cvIfCfgConnectionMode is 'normal', then  this
         object will be a zero length string."
    ::= { cvIfCfgEntry 9 }

cvIfCfgInitialDigitTimeOut OBJECT-TYPE
    SYNTAX Integer32(0..120)
--  Units
--    seconds
    ACCESS read-write
    STATUS mandatory
    DESCRIPTION
        "This is the initial digit timeout that indicates the amount of
         time the managed system waits for an initial input digit from the
         caller. The timer is activated when the call is accepted and is
         deactivated upon digit input. If the timer expires, the caller
         is signaled through the appropriate tone and the call is abandoned.
         The value of zero disables the timer.
         The default value of this object is 10 seconds."
    ::= { cvIfCfgEntry 10 }

cvIfCfgInterDigitTimeOut OBJECT-TYPE
    SYNTAX Integer32(0..120)
--  Units
--    seconds
    ACCESS read-write
    STATUS mandatory
    DESCRIPTION
        "This is the inter-digit timeout that indicates the amount of time
         the managed system waits for a subsequent input digit from the
         caller. The timer is started upon receipt of an input digit and
         restarted as each digit is received until the destination address
         is identified. If the timer expires and no destination address is
         identified, the caller is signaled through the appropriate tone
         and the call is abandoned. The value of zero disables the timer.
         The default value of this object is 10 seconds."
    ::= { cvIfCfgEntry 11 }

cvIfCfgRegionalTone OBJECT-TYPE
    SYNTAX CountryCode
--    Rsyntax OCTET STRING(SIZE(0 | 2))
    ACCESS read-write
    STATUS mandatory
    DESCRIPTION
        "This object contains the country specific setting
         for the tone, ring, cadence parameters to be used by
         this interface."
    ::= { cvIfCfgEntry 12 }

cvIfGroup OBJECT IDENTIFIER ::= { cvIfGroups 1 }
-- OBJECT-GROUP
--  Status
--    mandatory
--  Descr
--    A collection of objects providing the Common Voice parameter
--     related configuration for both analog and digital voice
--     interfaces.
--  objects
--    cvIfCfgNoiseRegEnable, cvIfCfgNonLinearProcEnable, 
--    cvIfCfgMusicOnHoldThreshold, cvIfCfgInGain, cvIfCfgOutAttn, 
--    cvIfCfgEchoCancelEnable, cvIfCfgEchoCancelCoverage, 
--    cvIfCfgInitialDigitTimeOut, cvIfCfgInterDigitTimeOut, 
--    cvIfCfgRegionalTone

cvIfConnectionGroup OBJECT IDENTIFIER ::= { cvIfGroups 2 }
-- OBJECT-GROUP
--  Status
--    mandatory
--  Descr
--    A collection of objects providing trunking or PLAR
--     (private line automatic ringdown) related configuration
--     for voice analog interfaces.
--  objects
--    cvIfCfgConnectionMode, cvIfCfgConnectionNumber

cvIfCompliance OBJECT IDENTIFIER ::= { cvIfCompliances 1 }
-- MODULE-COMPLIANCE
--  Status
--    mandatory
--  Descr
--    The compliance statement for entities which
--     implement the Cisco Voice Interface MIB
--  Module
--    >>current<<
--   MandGroup
--    cvIfGroup
--   OptGroup
--    cvIfConnectionGroup
--   ObjVar
--    cvIfCfgNoiseRegEnable
--   ObjVar
--    cvIfCfgNonLinearProcEnable
--   ObjVar
--    cvIfCfgMusicOnHoldThreshold
--   ObjVar
--    cvIfCfgInGain
--   ObjVar
--    cvIfCfgOutAttn
--   ObjVar
--    cvIfCfgEchoCancelEnable
--   ObjVar
--    cvIfCfgEchoCancelCoverage
--   ObjVar
--    cvIfCfgConnectionMode
--   ObjVar
--    cvIfCfgConnectionNumber
--   ObjVar
--    cvIfCfgInitialDigitTimeOut
--   ObjVar
--    cvIfCfgInterDigitTimeOut
--   ObjVar
--    cvIfCfgRegionalTone


END
