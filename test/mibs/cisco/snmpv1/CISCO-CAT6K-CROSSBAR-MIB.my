-- MIB file created 31-Oct-2005 15:29:13, by
--   SMICng version 2.2.11-beta(PRO)(Solaris), January 20, 2001. Enterprise key cisco.com

CISCO-CAT6K-CROSSBAR-MIB DEFINITIONS ::= BEGIN

-- From file: "CISCO-CAT6K-CROSSBAR-MIB.my"
-- Compile options "4 7 F H N O W 03 06 0B 0G 0N 0T"

IMPORTS
    ciscoMgmt
            FROM CISCO-SMI
    Percent
            FROM CISCO-QOS-PIB-MIB
    TruthValue, DisplayString
            FROM SNMPv2-TC-v1
    entPhysicalName, entPhysicalVendorType
            FROM ENTITY-MIB
    Counter, Gauge
            FROM RFC1155-SMI
    OBJECT-TYPE
            FROM RFC-1212
    TRAP-TYPE
            FROM RFC-1215;

ciscoCat6kCrossbarMIB OBJECT IDENTIFIER ::= { ciscoMgmt 217 }
-- MODULE-IDENTITY
--  LastUpdated
--    200408110000Z
--  OrgName
--    Cisco Systems, Inc.
--  ContactInfo
--    Cisco Systems
--     Customer Service
--     Postal: 170 W Tasman Drive
--     San Jose, CA  95134
--     USA
--     Tel: +1 800 553-NETS
--    
--     E-mail: cs-cat6000@cisco.com
--  Descr
--    The Catalyst 6000 Crossbar MIB provides instrumentation for
--    configuration and operation of the crossbar switching fabric
--    module, and additional functionalities for switching bus 
--    and internal bus, etc.
--  RevDate
--    200408110000Z
--  RevDescr
--    Added cc6kxbarIntBusNotifControlGroup and
--     cc6kxbarIntBusCRCErrNotifGroup.
--  RevDate
--    200406110000Z
--  RevDescr
--    Added cc6kxbarTruncatedModeOper Object and changed the 
--     description of cc6kxbarTruncatedModeAllowed and 
--     cc6kxbarMinFabricPresent.
--  RevDate
--    200309290000Z
--  RevDescr
--    Changed the description of cc6kxbarTruncatedModeAllowed and
--     cc6kxbarMinFabricPresent. Removed default value for 
--     cc6kxbarTruncatedModeAllowed.
--  RevDate
--    200304020000Z
--  RevDescr
--    Changed the SYNTAX and description of cc6kxbarMinFabricPresent 
--     and  description of cc6kxbarTruncatedModeAllowed.
--  RevDate
--    200212050000Z
--  RevDescr
--    Added cc6kxbarModuleChannelSpeed, cc6kxbarSwBusSwitchingStatus,
--     cc6kxbarSwBusFailureDuration, cc6kxbarSwBusNotifEnable 
--     objects and cc6kxbarSwBusStallNotif notification.
--  RevDate
--    200106250000Z
--  RevDescr
--    Initial version of this MIB module.

ciscoCat6kXbarMIBObjects OBJECT IDENTIFIER ::= { ciscoCat6kCrossbarMIB 1 }
cc6kxbarConfiguration OBJECT IDENTIFIER ::= { ciscoCat6kXbarMIBObjects 1 }
cc6kxbarStatus  OBJECT IDENTIFIER ::= { ciscoCat6kXbarMIBObjects 2 }
cc6kxbarStatistics OBJECT IDENTIFIER ::= { ciscoCat6kXbarMIBObjects 3 }
cc6kxbarSwBusObjects OBJECT IDENTIFIER ::= { ciscoCat6kXbarMIBObjects 4 }
cc6kxbarIntBusObjects OBJECT IDENTIFIER ::= { ciscoCat6kXbarMIBObjects 5 }
ciscoCat6kXbarMIBNotifs OBJECT IDENTIFIER ::= { ciscoCat6kCrossbarMIB 0 }
cc6kxbarMIBConformance OBJECT IDENTIFIER ::= { ciscoCat6kCrossbarMIB 3 }
cc6kxbarMIBCompliances OBJECT IDENTIFIER ::= { cc6kxbarMIBConformance 1 }
cc6kxbarMIBGroups OBJECT IDENTIFIER ::= { cc6kxbarMIBConformance 2 }

ModuleSlotNumber ::= Gauge
-- TEXTUAL-CONVENTION
--  Status
--    mandatory
--  Descr
--    Slot number of the module.

FabricChannelNumber ::= Gauge
-- TEXTUAL-CONVENTION
--  Status
--    mandatory
--  Descr
--    Fabric channel number.

ChannelStatus ::= INTEGER {
        ok(1),
        syncError(2),
        heartbeatError(3),
        crcError(4),
        bufferError(5),
        timeoutError(6),
        unused(7)
        }
-- TEXTUAL-CONVENTION
--  Status
--    mandatory
--  Descr
--    Status of the Channel.

cc6kxbarFallbackMode OBJECT-TYPE
    SYNTAX TruthValue
--    Rsyntax INTEGER {
--        true(1),
--        false(2)
--        }
    ACCESS read-write
    STATUS mandatory
    DESCRIPTION
        "cc6kxbarFallbackMode controls system fallback to bus-mode
        after loss of switching fabric module.
        'true'  - When the last fabric card is removed
                  system will adjust the supervisor and
                  line cards switching mode automatically without
                  resetting the system. With this feature enabled,
                  the switch might lose traffic while it's
                  changing the switching mode.
        'false'  - All the ports in the system will be
                  disabled when the last fabric card is removed."
    DEFVAL { true }
    ::= { cc6kxbarConfiguration 1 }

cc6kxbarBusOnlyModeAllowed OBJECT-TYPE
    SYNTAX TruthValue
--    Rsyntax INTEGER {
--        true(1),
--        false(2)
--        }
    ACCESS read-write
    STATUS mandatory
    DESCRIPTION
        "This object determines the value of
         cc6kxbarModuleModeSwitchingMode of each module.
         'true' - Each and every module is allowed to run in bus-only 
                  mode.
         'false' - None of the modules are allowed to run in bus-only 
                   mode.i.e., All the non-fabric capable modules will 
                   be powered off.  Absence of fabric module results 
                   in all the fabric capable modules being powered 
                   off."
    DEFVAL { true }
    ::= { cc6kxbarConfiguration 2 }

cc6kxbarTruncatedModeAllowed OBJECT-TYPE
    SYNTAX TruthValue
--    Rsyntax INTEGER {
--        true(1),
--        false(2)
--        }
    ACCESS read-write
    STATUS mandatory
    DESCRIPTION
        "Indicates whether truncated mode is 
         administratively enabled on the device or not."
    ::= { cc6kxbarConfiguration 3 }

cc6kxbarMinFabricPresent OBJECT-TYPE
    SYNTAX Gauge
    ACCESS read-write
    STATUS mandatory
    DESCRIPTION
        "This object indicates the minimum number 
         of switching fabric capable modules to be present in the 
         system, for any switching fabric capable module to be in
         'crossbarmode' indicated by  cc6kxbarModuleModeSwitchingMode,
         when cc6kxbarTruncatedModeOper is 'false'."
    ::= { cc6kxbarConfiguration 4 }

cc6kxbarLcdBannerTable OBJECT-TYPE
    SYNTAX SEQUENCE OF Cc6kxbarLcdBannerEntry
    ACCESS not-accessible
    STATUS mandatory
    DESCRIPTION
        "cc6kxbarLcdBannerTable configures the Lcd banner of the
         fabric module."
    ::= { cc6kxbarConfiguration 5 }

cc6kxbarLcdBannerEntry OBJECT-TYPE
    SYNTAX Cc6kxbarLcdBannerEntry
    ACCESS not-accessible
    STATUS mandatory
    DESCRIPTION
        "An entry in cc6kxbarLcdBannerTable.
         Entries are created by the agent based on the
         size of the lcd banner."
    INDEX { cc6kxbarLcdBannerIndex }
    ::= { cc6kxbarLcdBannerTable 1 }

Cc6kxbarLcdBannerEntry ::= SEQUENCE {
    cc6kxbarLcdBannerIndex Gauge,
    cc6kxbarLcdBannerBanner DisplayString,
    cc6kxbarLcdBannerMaxSize Gauge
    }

cc6kxbarLcdBannerIndex OBJECT-TYPE
    SYNTAX Gauge
    ACCESS not-accessible
    STATUS mandatory
    DESCRIPTION
        "Object which specifies a unique entry in the
         table."
    ::= { cc6kxbarLcdBannerEntry 1 }

cc6kxbarLcdBannerBanner OBJECT-TYPE
    SYNTAX DisplayString
--    Rsyntax OCTET STRING(SIZE(0..255))
    ACCESS read-write
    STATUS mandatory
    DESCRIPTION
        "Message that would be displayed on the fabric card LCD.
         The size of cc6kxbarLcdBannerBanner should be less than 
         or equal to the cc6kxbarLcdBannerMaxSize value."
    ::= { cc6kxbarLcdBannerEntry 2 }

cc6kxbarLcdBannerMaxSize OBJECT-TYPE
    SYNTAX Gauge
    ACCESS read-only
    STATUS mandatory
    DESCRIPTION
        "Maximum size of the associated cc6kxbarLcdBannerBanner
         object."
    ::= { cc6kxbarLcdBannerEntry 3 }

cc6kxbarTruncatedModeOper OBJECT-TYPE
    SYNTAX TruthValue
--    Rsyntax INTEGER {
--        true(1),
--        false(2)
--        }
    ACCESS read-only
    STATUS mandatory
    DESCRIPTION
        "Indicates if the truncated mode is
         operationaly enabled on the device or not.
         'true' - With the fabric module present in the system,
                  cc6kxbarModuleModeSwitchingMode will be
                  'crossbarmode' for all the fabric capable
                   modules.
         'false'- With the cc6kxbarMinFabricPresent fabric capable 
                  modules and the fabric module  present in the system,
                  cc6kxbarModuleModeSwitchingMode
                  will be 'crossbarmode' for fabric capable modules."
    ::= { cc6kxbarConfiguration 6 }

cc6kxbarFabricActiveSlot OBJECT-TYPE
    SYNTAX ModuleSlotNumber
--    Rsyntax Gauge
    ACCESS read-only
    STATUS mandatory
    DESCRIPTION
        "cc6kxbarFabricActiveSlot indicates the slot number of the 
         active switching fabric module. A value of zero indicates 
         that the active switching fabric module is either powered 
         down or not present in the chassis."
    ::= { cc6kxbarStatus 1 }

cc6kxbarFabricBackupSlot OBJECT-TYPE
    SYNTAX ModuleSlotNumber
--    Rsyntax Gauge
    ACCESS read-only
    STATUS mandatory
    DESCRIPTION
        "cc6kxbarFabricBackupSlot indicates the slot number of the 
         backup switching fabric module. A value of zero indicates 
         that the backup switching fabric module is either powered
         down or not present in the chassis."
    ::= { cc6kxbarStatus 2 }

cc6kxbarModuleModeTable OBJECT-TYPE
    SYNTAX SEQUENCE OF Cc6kxbarModuleModeEntry
    ACCESS not-accessible
    STATUS mandatory
    DESCRIPTION
        "cc6kxbarModuleModeTable indicates the switching mode of each 
         module in the system."
    ::= { cc6kxbarStatus 3 }

cc6kxbarModuleModeEntry OBJECT-TYPE
    SYNTAX Cc6kxbarModuleModeEntry
    ACCESS not-accessible
    STATUS mandatory
    DESCRIPTION
        "An entry in cc6kxbarModuleModeTable. The agent creates
        an entry when a non switching fabric module 
        is inserted in the chassis.
        The agent destroys an entry when a non switching fabric
        module is power down or reset or removed from the chassis."
    INDEX { cc6kxbarModuleModeModule }
    ::= { cc6kxbarModuleModeTable 1 }

Cc6kxbarModuleModeEntry ::= SEQUENCE {
    cc6kxbarModuleModeModule ModuleSlotNumber,
    cc6kxbarModuleModeSwitchingMode INTEGER
    }

cc6kxbarModuleModeModule OBJECT-TYPE
    SYNTAX ModuleSlotNumber
--    Rsyntax Gauge
    ACCESS not-accessible
    STATUS mandatory
    DESCRIPTION
        "The module slot number."
    ::= { cc6kxbarModuleModeEntry 1 }

cc6kxbarModuleModeSwitchingMode OBJECT-TYPE
    SYNTAX INTEGER {
        busmode(1),
        crossbarmode(2),
        dcefmode(3)
        }
    ACCESS read-only
    STATUS mandatory
    DESCRIPTION
        "cc6kxbarModuleModeSwitchingMode indicates switching mode 
         of the cc6kxbarModuleModeModule.
         'busmode'     -  Modules  in this mode don't use fabric.
                          Backplane is used for both lookup and data
                          forwarding.
         'crossbarmode' -  Modules in this mode use backplane 
                           for forwarding decision and fabric for data 
                           forwarding
         'dcefmode'    -  Modules in this mode use fabric for data 
                          forwarding and local forwarding is enabled."
    ::= { cc6kxbarModuleModeEntry 2 }

cc6kxbarModuleChannelTable OBJECT-TYPE
    SYNTAX SEQUENCE OF Cc6kxbarModuleChannelEntry
    ACCESS not-accessible
    STATUS mandatory
    DESCRIPTION
        "cc6kxbarModuleChannelTable shows the operational status
        of fabric channels. This table will be instantiated only when 
        cc6kxbarFabricActiveSlot has a valid value other than zero."
    ::= { cc6kxbarStatus 4 }

cc6kxbarModuleChannelEntry OBJECT-TYPE
    SYNTAX Cc6kxbarModuleChannelEntry
    ACCESS not-accessible
    STATUS mandatory
    DESCRIPTION
        "An entry in cc6kxbarModuleChannelTable."
    INDEX { cc6kxbarModuleChannelModule, cc6kxbarModuleChannelChannel }
    ::= { cc6kxbarModuleChannelTable 1 }

Cc6kxbarModuleChannelEntry ::= SEQUENCE {
    cc6kxbarModuleChannelModule ModuleSlotNumber,
    cc6kxbarModuleChannelChannel FabricChannelNumber,
    cc6kxbarModuleChannelModStatus ChannelStatus,
    cc6kxbarModuleChannelFabStatus ChannelStatus,
    cc6kxbarModuleChannelSpeed Gauge
    }

cc6kxbarModuleChannelModule OBJECT-TYPE
    SYNTAX ModuleSlotNumber
--    Rsyntax Gauge
    ACCESS not-accessible
    STATUS mandatory
    DESCRIPTION
        "The module slot number."
    ::= { cc6kxbarModuleChannelEntry 1 }

cc6kxbarModuleChannelChannel OBJECT-TYPE
    SYNTAX FabricChannelNumber
--    Rsyntax Gauge
    ACCESS not-accessible
    STATUS mandatory
    DESCRIPTION
        "Fabric channel number of the  cc6kxbarModuleChannelModule."
    ::= { cc6kxbarModuleChannelEntry 2 }

cc6kxbarModuleChannelModStatus OBJECT-TYPE
    SYNTAX ChannelStatus
--    Rsyntax INTEGER {
--        ok(1),
--        syncError(2),
--        heartbeatError(3),
--        crcError(4),
--        bufferError(5),
--        timeoutError(6),
--        unused(7)
--        }
    ACCESS read-only
    STATUS mandatory
    DESCRIPTION
        "The status of the fabric channel at the 
         cc6kxbarModuleChannelModule."
    ::= { cc6kxbarModuleChannelEntry 3 }

cc6kxbarModuleChannelFabStatus OBJECT-TYPE
    SYNTAX ChannelStatus
--    Rsyntax INTEGER {
--        ok(1),
--        syncError(2),
--        heartbeatError(3),
--        crcError(4),
--        bufferError(5),
--        timeoutError(6),
--        unused(7)
--        }
    ACCESS read-only
    STATUS mandatory
    DESCRIPTION
        "The status of the fabric channel at the 
         cc6kxbarFabricActiveSlot."
    ::= { cc6kxbarModuleChannelEntry 4 }

cc6kxbarModuleChannelSpeed OBJECT-TYPE
    SYNTAX Gauge
    ACCESS read-only
    STATUS mandatory
    DESCRIPTION
        "The speed in mega bits per second of the 
         cc6kxbarModuleChannelChannel for cc6kxbarModuleChannelModule."
    ::= { cc6kxbarModuleChannelEntry 5 }

cc6kxbarStatisticsTable OBJECT-TYPE
    SYNTAX SEQUENCE OF Cc6kxbarStatisticsEntry
    ACCESS not-accessible
    STATUS mandatory
    DESCRIPTION
        "cc6kxbarStatisticsTable gives the 
         fabric channel counters and utilization
         information.  This table will be instantiated when 
         cc6kxbarFabricActiveSlot has a valid value other than
         zero."
    ::= { cc6kxbarStatistics 1 }

cc6kxbarStatisticsEntry OBJECT-TYPE
    SYNTAX Cc6kxbarStatisticsEntry
    ACCESS not-accessible
    STATUS mandatory
    DESCRIPTION
        "An entry in cc6kxbarStatisticsTable."
    INDEX { cc6kxbarStatisticsModule, cc6kxbarStatisticsChannel }
    ::= { cc6kxbarStatisticsTable 1 }

Cc6kxbarStatisticsEntry ::= SEQUENCE {
    cc6kxbarStatisticsModule ModuleSlotNumber,
    cc6kxbarStatisticsChannel FabricChannelNumber,
    cc6kxbarStatisticsInErrors Counter,
    cc6kxbarStatisticsOutErrors Counter,
    cc6kxbarStatisticsOutDropped Counter,
    cc6kxbarStatisticsInUtil Percent,
    cc6kxbarStatisticsOutUtil Percent
    }

cc6kxbarStatisticsModule OBJECT-TYPE
    SYNTAX ModuleSlotNumber
--    Rsyntax Gauge
    ACCESS not-accessible
    STATUS mandatory
    DESCRIPTION
        "The module slot number."
    ::= { cc6kxbarStatisticsEntry 1 }

cc6kxbarStatisticsChannel OBJECT-TYPE
    SYNTAX FabricChannelNumber
--    Rsyntax Gauge
    ACCESS not-accessible
    STATUS mandatory
    DESCRIPTION
        "Fabric channel number associated with the  
         cc6kxbarStatisticsModule."
    ::= { cc6kxbarStatisticsEntry 2 }

cc6kxbarStatisticsInErrors OBJECT-TYPE
    SYNTAX Counter
    ACCESS read-only
    STATUS mandatory
    DESCRIPTION
        "The total number of error packets received on 
         cc6kxbarStatisticsChannel for cc6kxbarStatisticsModule
         since this entry was last initialized."
    ::= { cc6kxbarStatisticsEntry 3 }

cc6kxbarStatisticsOutErrors OBJECT-TYPE
    SYNTAX Counter
    ACCESS read-only
    STATUS mandatory
    DESCRIPTION
        "The total number of error packets transmitted on 
         cc6kxbarStatisticsModule through the 
         cc6kxbarStatisticsChannel since this entry was 
         last initialized."
    ::= { cc6kxbarStatisticsEntry 4 }

cc6kxbarStatisticsOutDropped OBJECT-TYPE
    SYNTAX Counter
    ACCESS read-only
    STATUS mandatory
    DESCRIPTION
        "The total number of  dropped packets transmitted on the
         cc6kxbarStatisticsChannel for cc6kxbarStatisticsModule
         since this entry was last initialized."
    ::= { cc6kxbarStatisticsEntry 5 }

cc6kxbarStatisticsInUtil OBJECT-TYPE
    SYNTAX Percent
--    Rsyntax INTEGER(0..100)
    ACCESS read-only
    STATUS mandatory
    DESCRIPTION
        "Input utilization of the cc6kxbarStatisticsChannel for 
         cc6kxbarStatisticsModule."
    ::= { cc6kxbarStatisticsEntry 6 }

cc6kxbarStatisticsOutUtil OBJECT-TYPE
    SYNTAX Percent
--    Rsyntax INTEGER(0..100)
    ACCESS read-only
    STATUS mandatory
    DESCRIPTION
        "Output utilization of the cc6kxbarStatisticsChannel for
         cc6kxbarStatisticsModule."
    ::= { cc6kxbarStatisticsEntry 7 }

cc6kxbarSwBusSwitchingStatus OBJECT-TYPE
    SYNTAX INTEGER {
        normal(1),
        stalled(2),
        isolated(3)
        }
    ACCESS read-only
    STATUS mandatory
    DESCRIPTION
        "Indicates the current switching status of the 
         switching bus on the system. 
        
         normal -- the switching bus is under normal 
                   packet switching operation.
        
         stalled -- the switching bus has stopped packet 
                    switching but is still attached to
                    the system, i.e., the switching bus
                    is stalled. 
        
         isolated -- the switching bus has stopped packet 
                    switching and is detached from 
                    the system, i.e., the switching bus 
                    is isolated.
        
         The object is only instantiated on systems which 
         support switching bus switching detection feature."
    ::= { cc6kxbarSwBusObjects 1 }

cc6kxbarSwBusFailureDuration OBJECT-TYPE
    SYNTAX Gauge
--  Units
--    seconds
    ACCESS read-only
    STATUS mandatory
    DESCRIPTION
        "Indicates the failure duration of the switching 
         bus since the switching bus has transitioned 
         out of the normal(1) state as monitored by  
         cc6kxbarSwBusSwitchingStatus. If the object 
         value of cc6kxbarSwBusSwitchingStatus is 
         normal(1), then the object value of 
         cc6kxbarSwBusFailureDuration should be zero.
        
         The object is only instantiated on systems which
         support switching bus switching detection feature."
    ::= { cc6kxbarSwBusObjects 2 }

cc6kxbarSwBusNotifEnable OBJECT-TYPE
    SYNTAX TruthValue
--    Rsyntax INTEGER {
--        true(1),
--        false(2)
--        }
    ACCESS read-write
    STATUS mandatory
    DESCRIPTION
        "Indicates whether or not the notification 
         cc6kxbarSwBusStatusChangeNotif should be generated 
         when there is change in the switching status of the 
         switching bus as monitored by 
         cc6kxbarSwBusSwitchingStatus.
        
         The object is only instantiated on systems which
         support switching bus switching detection feature."
    ::= { cc6kxbarSwBusObjects 3 }

cc6kxbarIntBusNotifEnable OBJECT-TYPE
    SYNTAX OCTET STRING(SIZE(1..2))
        -- BITS are:
        --   intBusCRCErrExcd(0)
        --   intBusCRCErrRcvrd(1)
    ACCESS read-write
    STATUS mandatory
    DESCRIPTION
        "Indicates whether the generation of a specified
        notification for internal bus is enabled or not. 
        If a bit corresponding to a notification is set to 
        1, then that notification can be generated.
        
        intBusCRCErrExcd -- the cc6kxbarIntBusCRCErrExcdNotif 
                            notification.
        
        intBusCRCErrRcvrd -- the cc6kxbarIntBusCRCErrRcvrdNotif
                            notification."
    ::= { cc6kxbarIntBusObjects 1 }

cc6kxbarSwBusStatusChangeNotif TRAP-TYPE
-- Reverse mappable trap
    ENTERPRISE ciscoCat6kCrossbarMIB
    VARIABLES {
        cc6kxbarSwBusSwitchingStatus, cc6kxbarSwBusFailureDuration }
--  Status
--    mandatory
    DESCRIPTION
        "A cc6kxbarSwBusStatusChangeNotif notification 
         is sent by the the device when there is change
         in switching status of the switching bus as 
         monited by cc6kxbarSwBusSwitchingStatus."
    ::= 1

cc6kxbarIntBusCRCErrExcdNotif TRAP-TYPE
-- Reverse mappable trap
    ENTERPRISE ciscoCat6kCrossbarMIB
    VARIABLES {
        entPhysicalName, entPhysicalVendorType }
--  Status
--    mandatory
    DESCRIPTION
        "A cc6kxbarIntBusCRCThreshExcdNotif notification 
        is sent by the system when the system has
        detected that the internal bus CRC error on
        a physical entity (such as a module) as specified
        by entPhysicalName has exceeded the fatal threshold."
    ::= 2

cc6kxbarIntBusCRCErrRcvrdNotif TRAP-TYPE
-- Reverse mappable trap
    ENTERPRISE ciscoCat6kCrossbarMIB
    VARIABLES {
        entPhysicalName, entPhysicalVendorType }
--  Status
--    mandatory
    DESCRIPTION
        "A cc6kxbarIntBusCRCErrRcvrdNotif notification 
        is sent by the system when the system has
        recovered as the internal bus CRC error on
        a physical entity (such as a module) as
        specified by entPhysicalName has fallen below
        the normal threshold."
    ::= 3

cc6kxbarModuleStatusGroup OBJECT IDENTIFIER ::= { cc6kxbarMIBGroups 1 }
-- OBJECT-GROUP
--  Status
--    deprecated
--  Descr
--    A collection of objects providing 
--     configuration and operation of the crossbar 
--     switching fabric module and switching capable 
--     module.
--  objects
--    cc6kxbarLcdBannerMaxSize, cc6kxbarLcdBannerBanner, 
--    cc6kxbarTruncatedModeAllowed, cc6kxbarMinFabricPresent, 
--    cc6kxbarFabricActiveSlot, cc6kxbarFabricBackupSlot, 
--    cc6kxbarModuleModeSwitchingMode

cc6kxbarChannelStatusGroup OBJECT IDENTIFIER ::= { cc6kxbarMIBGroups 2 }
-- OBJECT-GROUP
--  Status
--    mandatory
--  Descr
--    A collection of objects providing 
--    status and configuration of the fabric channel.
--  objects
--    cc6kxbarModuleChannelModStatus, 
--    cc6kxbarModuleChannelFabStatus

cc6kxbarChannelStatisticsGroup OBJECT IDENTIFIER ::= { cc6kxbarMIBGroups 3 }
-- OBJECT-GROUP
--  Status
--    deprecated
--  Descr
--    A collection of objects providing statistics for
--     the fabric channel.
--  objects
--    cc6kxbarStatisticsInErrors, cc6kxbarStatisticsOutErrors, 
--    cc6kxbarStatisticsOutDropped, cc6kxbarStatisticsInUtil, 
--    cc6kxbarStatisticsOutUtil

cc6kxbarFallbackGroup OBJECT IDENTIFIER ::= { cc6kxbarMIBGroups 4 }
-- OBJECT-GROUP
--  Status
--    mandatory
--  Descr
--    This object controls system fallback to bus-mode
--     after loss of switching fabric module.
--  objects
--    cc6kxbarFallbackMode

cc6kxbarBusOnlyAllowedGroup OBJECT IDENTIFIER ::= { cc6kxbarMIBGroups 5 }
-- OBJECT-GROUP
--  Status
--    mandatory
--  Descr
--    This object determines the value of
--     cc6kxbarModuleModeSwitchingMode of each module.
--  objects
--    cc6kxbarBusOnlyModeAllowed

cc6kxbarModuleStatusGroupVer1 OBJECT IDENTIFIER ::= { cc6kxbarMIBGroups 6 }
-- OBJECT-GROUP
--  Status
--    mandatory
--  Descr
--    A collection of objects providing 
--     configuration and operation of the crossbar 
--     switching fabric module and switching capable 
--     module.
--  objects
--    cc6kxbarTruncatedModeAllowed, cc6kxbarMinFabricPresent, 
--    cc6kxbarFabricActiveSlot, cc6kxbarFabricBackupSlot, 
--    cc6kxbarModuleModeSwitchingMode

cc6kxbarChannelStatisticsGroupVer1 OBJECT IDENTIFIER ::= { cc6kxbarMIBGroups 7 }
-- OBJECT-GROUP
--  Status
--    mandatory
--  Descr
--    A collection of objects providing statistics for
--     the fabric channel.
--  objects
--    cc6kxbarStatisticsInErrors, cc6kxbarStatisticsOutErrors, 
--    cc6kxbarStatisticsOutDropped

cc6kxbarLcdBannerGroup OBJECT IDENTIFIER ::= { cc6kxbarMIBGroups 8 }
-- OBJECT-GROUP
--  Status
--    mandatory
--  Descr
--    A collection of objects providing configuration of
--     the lcd Banner of the fabric module.
--  objects
--    cc6kxbarLcdBannerMaxSize, cc6kxbarLcdBannerBanner

cc6kxbarChannelUtilGroup OBJECT IDENTIFIER ::= { cc6kxbarMIBGroups 9 }
-- OBJECT-GROUP
--  Status
--    mandatory
--  Descr
--    These object determines Input and Output Utilization of the 
--     fabric channel.
--  objects
--    cc6kxbarStatisticsInUtil, cc6kxbarStatisticsOutUtil

cc6kxbarChannelSpeedGroup OBJECT IDENTIFIER ::= { cc6kxbarMIBGroups 10 }
-- OBJECT-GROUP
--  Status
--    mandatory
--  Descr
--    A collection of objects providing the 
--     speed of the fabric channel.
--  objects
--    cc6kxbarModuleChannelSpeed

cc6kxbarSwBusGroup OBJECT IDENTIFIER ::= { cc6kxbarMIBGroups 11 }
-- OBJECT-GROUP
--  Status
--    mandatory
--  Descr
--    A collection of objects for the switching bus switching 
--     detection feature.
--  objects
--    cc6kxbarSwBusSwitchingStatus, cc6kxbarSwBusFailureDuration, 
--    cc6kxbarSwBusNotifEnable

cc6kxbarTruncatedOperGroup OBJECT IDENTIFIER ::= { cc6kxbarMIBGroups 13 }
-- OBJECT-GROUP
--  Status
--    mandatory
--  Descr
--    A collection of objects providing the 
--     operational truncated mode.
--  objects
--    cc6kxbarTruncatedModeOper

cc6kxbarIntBusNotifControlGroup OBJECT IDENTIFIER ::= { cc6kxbarMIBGroups 14 }
-- OBJECT-GROUP
--  Status
--    mandatory
--  Descr
--    A collection of objects to control the notification 
--    generation for internal bus.
--  objects
--    cc6kxbarIntBusNotifEnable

cc6kxbarSwBusNotifGroup OBJECT IDENTIFIER ::= { cc6kxbarMIBGroups 12 }
-- NOTIFICATION-GROUP
--  Status
--    mandatory
--  Descr
--    A collection of notifications for the switching 
--     bus switching detection feature.
--  notifications
--    cc6kxbarSwBusStatusChangeNotif

cc6kxbarIntBusCRCErrNotifGroup OBJECT IDENTIFIER ::= { cc6kxbarMIBGroups 15 }
-- NOTIFICATION-GROUP
--  Status
--    mandatory
--  Descr
--    A collection of notifications for the 
--    internal bus CRC error.
--  notifications
--    cc6kxbarIntBusCRCErrExcdNotif, cc6kxbarIntBusCRCErrRcvrdNotif

cc6kxbarMIBCompliance OBJECT IDENTIFIER ::= { cc6kxbarMIBCompliances 2 }
-- MODULE-COMPLIANCE
--  Status
--    deprecated
--  Descr
--    The compliance statement for
--     the CISCO-CAT6K-CROSSBAR-MIB.
--  Module
--    >>current<<
--   MandGroup
--    cc6kxbarModuleStatusGroup
--   MandGroup
--    cc6kxbarChannelStatusGroup
--   MandGroup
--    cc6kxbarChannelStatisticsGroup
--   OptGroup
--    cc6kxbarFallbackGroup
--   OptGroup
--    cc6kxbarBusOnlyAllowedGroup

cc6kxbarMIBComplianceVer1 OBJECT IDENTIFIER ::= { cc6kxbarMIBCompliances 3 }
-- MODULE-COMPLIANCE
--  Status
--    deprecated
--  Descr
--    The compliance statement for
--     the CISCO-CAT6K-CROSSBAR-MIB.
--  Module
--    >>current<<
--   MandGroup
--    cc6kxbarModuleStatusGroupVer1
--   MandGroup
--    cc6kxbarChannelStatusGroup
--   MandGroup
--    cc6kxbarChannelStatisticsGroupVer1
--   OptGroup
--    cc6kxbarFallbackGroup
--   OptGroup
--    cc6kxbarBusOnlyAllowedGroup
--   OptGroup
--    cc6kxbarLcdBannerGroup
--   OptGroup
--    cc6kxbarChannelUtilGroup
--   OptGroup
--    cc6kxbarChannelSpeedGroup
--   OptGroup
--    cc6kxbarSwBusGroup
--   OptGroup
--    cc6kxbarSwBusNotifGroup

cc6kxbarMIBComplianceVer2 OBJECT IDENTIFIER ::= { cc6kxbarMIBCompliances 4 }
-- MODULE-COMPLIANCE
--  Status
--    deprecated
--  Descr
--    The compliance statement for
--     the CISCO-CAT6K-CROSSBAR-MIB.
--  Module
--    >>current<<
--   MandGroup
--    cc6kxbarModuleStatusGroupVer1
--   MandGroup
--    cc6kxbarChannelStatusGroup
--   MandGroup
--    cc6kxbarChannelStatisticsGroupVer1
--   OptGroup
--    cc6kxbarFallbackGroup
--   OptGroup
--    cc6kxbarBusOnlyAllowedGroup
--   OptGroup
--    cc6kxbarLcdBannerGroup
--   OptGroup
--    cc6kxbarChannelUtilGroup
--   OptGroup
--    cc6kxbarChannelSpeedGroup
--   OptGroup
--    cc6kxbarSwBusGroup
--   OptGroup
--    cc6kxbarSwBusNotifGroup
--   OptGroup
--    cc6kxbarTruncatedOperGroup

cc6kxbarMIBComplianceVer3 OBJECT IDENTIFIER ::= { cc6kxbarMIBCompliances 5 }
-- MODULE-COMPLIANCE
--  Status
--    mandatory
--  Descr
--    The compliance statement for
--     the CISCO-CAT6K-CROSSBAR-MIB.
--  Module
--    >>current<<
--   MandGroup
--    cc6kxbarModuleStatusGroupVer1
--   MandGroup
--    cc6kxbarChannelStatusGroup
--   MandGroup
--    cc6kxbarChannelStatisticsGroupVer1
--   OptGroup
--    cc6kxbarFallbackGroup
--   OptGroup
--    cc6kxbarBusOnlyAllowedGroup
--   OptGroup
--    cc6kxbarLcdBannerGroup
--   OptGroup
--    cc6kxbarChannelUtilGroup
--   OptGroup
--    cc6kxbarChannelSpeedGroup
--   OptGroup
--    cc6kxbarSwBusGroup
--   OptGroup
--    cc6kxbarSwBusNotifGroup
--   OptGroup
--    cc6kxbarTruncatedOperGroup
--   OptGroup
--    cc6kxbarIntBusNotifControlGroup
--   OptGroup
--    cc6kxbarIntBusCRCErrNotifGroup


END
