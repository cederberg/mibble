-- MIB created 4/07/98 01:48:43, by
--   SMIC (the next generation) version 1.6.29, November 22, 1994.

CISCO-ATM-PVC-MIB DEFINITIONS ::= BEGIN

-- From file: "CISCO-ATM-PVC-MIB.my"

IMPORTS
    OBJECT-TYPE
            FROM RFC-1212
    RowStatus, TruthValue
            FROM SNMPv2-TC-v1
    Unsigned32
            FROM CISCO-TC
    ciscoMgmt
            FROM CISCO-SMI;

ciscoAtmPvcMIB OBJECT IDENTIFIER ::= { ciscoMgmt 94 }
-- MODULE-IDENTITY
--  LastUpdated
--    9711180000Z
--  OrgName
--    Cisco Systems, Inc.
--  ContactInfo
--     Cisco Systems
--      Customer Service
--    
--    Postal: 170 W. Tasman Drive
--     San Jose, CA 95134-1706
--     USA
--    
--       Tel: +1 800 553-NETS
--    
--    E-mail: cs-atm@cisco.com
--  Descr
--     PVC's (Permanent Virtual Channel)
--         can carry bridged PDUs (BPDUs)
--         using the encapsulation method 
--         detailed in RFC1483. This is an 
--         alternative to using LAN Emulation 
--         to transfer BPDUs.
--         This MIB allows users to configure 
--         a PVC on an ATM uplink card of a 
--      Catalyst 5000 device, and then bind 
--      that PVC to a Virtual LAN (VLAN). 
--  RevDate
--    9711180000Z
--  RevDescr
--     Initial version of this MIB module. 

ciscoAtmPvcMIBObjects OBJECT IDENTIFIER ::= { ciscoAtmPvcMIB 1 }
ciscoAtmPvcCreateBindGroup OBJECT IDENTIFIER ::= { ciscoAtmPvcMIBObjects 1 }
ciscoAtmPvcMIBConformance OBJECT IDENTIFIER ::= { ciscoAtmPvcMIB 3 }
ciscoAtmPvcMIBCompliances OBJECT IDENTIFIER ::= { ciscoAtmPvcMIBConformance 1 }
ciscoAtmPvcMIBGroups OBJECT IDENTIFIER ::= { ciscoAtmPvcMIBConformance 2 }

capvcTable OBJECT-TYPE
    SYNTAX SEQUENCE OF CapvcEntry
    ACCESS not-accessible
    STATUS mandatory
    DESCRIPTION
        "A table of all the PVCs configured on an ATM uplink card."
    ::= { ciscoAtmPvcCreateBindGroup 1 }

capvcEntry OBJECT-TYPE
    SYNTAX CapvcEntry
    ACCESS not-accessible
    STATUS mandatory
    DESCRIPTION
        " An entry in the PVC table containing information 
          about a single PVC that has been configured. To 
          create a PVC at an ATM interface and bind it to a
          VLAN, either of the following procedures are used :
        
             Multi step process 
           (1) The management application creates a 
              PVC entry in the capvcTable by setting 
              the capvcRowStatus to createAndWait(5).
                   This may fail for the following reasons:
                   - The selected vpi/vci is already being used.
                   - The selected port is not available.
                 Otherwise, the agent creates a row and 
              reserves the vpi/vci on that port.
           (2) The manager then sets the values for 
              the capvcVlanId, capvcType and optionally, 
              the capvcPCR, capvcOAM and capvcFrequency.
           (3) The manager activates the PVC by setting 
              the capvcRowStatus to active(1). 
        
            One-Shot PVC establishment
           (1) A PVC may also be established in one 
              step by a set-request with all necessary 
              PVC parameter values and the capvcRowStatus
               set to createAndGo(4).
               In contrast to the multi step process which 
              allows for detailed error checking (i.e., 
              set errors are explicitly linked to
                 particular resource acquisition failures), 
              the one-shot PVC establishment performs the 
              setup on one operation but does not have the 
              advantage of step-wise error checking.
        
            PVC Retirement  
             A PVC is released by setting the capvcRowStatus 
          to destroy(6), and the agent may release all 
          associated resources. "
    INDEX { capvcPort, capvcVPI, capvcVCI }
    ::= { capvcTable 1 }

CapvcEntry ::= SEQUENCE {
    capvcPort Unsigned32,
    capvcVPI Unsigned32,
    capvcVCI Unsigned32,
    capvcVCD Unsigned32,
    capvcType INTEGER,
    capvcPCR Unsigned32,
    capvcOAM TruthValue,
    capvcFrequency Unsigned32,
    capvcVlanId Unsigned32,
    capvcRowStatus RowStatus
    }

capvcPort OBJECT-TYPE
    SYNTAX Unsigned32
--    Rsyntax Gauge32
    ACCESS not-accessible
    STATUS mandatory
    DESCRIPTION
        " The port number in the ATM module on 
          which this PVC is being configured. "
    ::= { capvcEntry 1 }

capvcVPI OBJECT-TYPE
    SYNTAX Unsigned32(0..4095)
--    Rsyntax Gauge32(0..4095)
    ACCESS not-accessible
    STATUS mandatory
    DESCRIPTION
        " The Virtual Path Identifier for the PVC. "
    ::= { capvcEntry 2 }

capvcVCI OBJECT-TYPE
    SYNTAX Unsigned32(0..65535)
--    Rsyntax Gauge32(0..65535)
    ACCESS not-accessible
    STATUS mandatory
    DESCRIPTION
        " The Virtual Channel Identifier for the PVC. "
    ::= { capvcEntry 3 }

capvcVCD OBJECT-TYPE
    SYNTAX Unsigned32(0..4095)
--    Rsyntax Gauge32(0..4095)
    ACCESS read-only
    STATUS mandatory
    DESCRIPTION
        " This is the Virtual Channel Descriptor,
          a value which uniquely identifies the PVC. 
          This is a read-only variable and is not
          set by the user. When the PVC is created
          successfully, it is assigned a unique
          VCD number by the system."
    ::= { capvcEntry 4 }

capvcType OBJECT-TYPE
    SYNTAX INTEGER {
        aal5snap(1),
        ilmi(2),
        qsaal(3)
        }
    ACCESS read-write
    STATUS mandatory
    DESCRIPTION
        " The type of traffic that will flow 
          through the PVC. The user can configure 
          the PVC as:
            (1) aal5snap PVC which carries network 
              interconnect traffic over ATM 
              AAL5 (RFC1483).
            (2) ilmi PVC which carries Interim Link
              Management Interface protocol traffic.
            (3) qsaal PVC which carries ATM UNI 3.x 
              signalling traffic. "
    ::= { capvcEntry 5 }

capvcPCR OBJECT-TYPE
    SYNTAX Unsigned32(0..155000)
--    Rsyntax Gauge32(0..155000)
--  Units
--    kbps
    ACCESS read-write
    STATUS mandatory
    DESCRIPTION
        " The Peak Cell Rate for the PVC. This 
          value denotes the bandwidth allocated 
          for this PVC. The default value for 
          this field is the maximum speed of the 
             interface. This is 155000 Kbps for an 
          OC3 Module and 45000 Kbps for a DS3 
          Module. "
    ::= { capvcEntry 6 }

capvcOAM OBJECT-TYPE
    SYNTAX TruthValue
--    Rsyntax INTEGER {
--        true(1),
--        false(2)
--        }
    ACCESS read-write
    STATUS mandatory
    DESCRIPTION
        " A boolean that indicates if a F5 OAM 
          loopback cell will be sent on this 
          PVC or not. The default value for 
          this field is false. "
    DEFVAL { false }
    ::= { capvcEntry 7 }

capvcFrequency OBJECT-TYPE
    SYNTAX Unsigned32
--    Rsyntax Gauge32
--  Units
--    seconds
    ACCESS read-write
    STATUS mandatory
    DESCRIPTION
        " Indicates how often will a F5 OAM 
          loopback cell be transmitted. If the 
             value of capvcOAM is true, then the 
          default value for this variable is 
          10 seconds. If the value of capvcOAM 
          is false, then this variable is ignored. "
    DEFVAL { 10 }
    ::= { capvcEntry 8 }

capvcVlanId OBJECT-TYPE
    SYNTAX Unsigned32(1..1024)
--    Rsyntax Gauge32(1..1024)
    ACCESS read-write
    STATUS mandatory
    DESCRIPTION
        " The VLAN number of the VLAN that the 
          PVC is bound to. 
          Binding a PVC say with VCD number x, 
          to a VLAN with a VlanId y, causes the 
          traffic on VLAN y to pass through PVC x.
            Also a PVC that is bound to a VLAN can 
          be unbound by the user. After the unbind 
          operation the VLAN traffic stops flowing 
          through the PVC. If the user changes the
          value of this variable then the PVC is 
          unbound from the original VLAN and bound 
          to the new VLAN. "
    ::= { capvcEntry 9 }

capvcRowStatus OBJECT-TYPE
    SYNTAX RowStatus
--    Rsyntax INTEGER {
--        active(1),
--        notInService(2),
--        notReady(3),
--        createAndGo(4),
--        createAndWait(5),
--        destroy(6)
--        }
    ACCESS read-write
    STATUS mandatory
    DESCRIPTION
        " This object is used to create, delete 
          or modify a row in this table.  To 
          create a new PVC, this object is 
          initially set to 'createAndWait' or 
          'createAndGo'. This object must not 
          be set to 'active' unless the following 
          columnar objects exist in this row:
                capvcType and capvcVlanId.
             To delete a row, this object is set 
          to 'destroy'(6)."
    ::= { capvcEntry 10 }

ciscoAtmPvcMIBGroup OBJECT IDENTIFIER ::= { ciscoAtmPvcMIBGroups 1 }
-- OBJECT-GROUP
--  Status
--    mandatory
--  Descr
--     A collection of objects providing ATM 
--      PVC configuration and VLAN binding. 
--  objects
--    capvcVCD, capvcType, capvcPCR, capvcOAM, capvcFrequency, 
--    capvcVlanId, capvcRowStatus

ciscoAtmPvcMIBCompliance OBJECT IDENTIFIER ::= { ciscoAtmPvcMIBCompliances 1 }
-- MODULE-COMPLIANCE
--  Status
--    mandatory
--  Descr
--     The compliance statement for entities
--      which implement the Cisco Atm PVC MIB.
--      This MIB is mandatory for all ATM uplink
--      cards on the Catalyst 5000 device.
--  Module
--    >>current<<
--   MandGroup
--    ciscoAtmPvcMIBGroup


END
