-- MIB file created 12-Jun-2006 14:03:03, by
--   SMICng version 2.2.11-beta(PRO)(Solaris), January 20, 2001. Enterprise key cisco.com

CISCO-LWAPP-AP-MIB DEFINITIONS ::= BEGIN

-- From file: "CISCO-LWAPP-AP-MIB.my"
-- Compile options "4 7 F H N O W 03 06 0B 0G 0N 0T"

IMPORTS
    MacAddress
            FROM SNMPv2-TC-v1
    CLApIfType
            FROM CISCO-LWAPP-TC-MIB
    ciscoMgmt
            FROM CISCO-SMI
    Gauge
            FROM RFC1155-SMI
    OBJECT-TYPE
            FROM RFC-1212;

ciscoLwappApMIB OBJECT IDENTIFIER ::= { ciscoMgmt 513 }
-- MODULE-IDENTITY
--  LastUpdated
--    200603300000Z
--  OrgName
--    Cisco Systems Inc.
--  ContactInfo
--            Cisco Systems,
--             Customer Service
--    
--     Postal: 170 West Tasman Drive
--             San Jose, CA  95134
--             USA
--    
--        Tel: +1 800 553-NETS
--    
--      Email: cs-snmp@cisco.com
--  Descr
--    This MIB is intended to be implemented on all those
--    devices operating as Central Controllers (CC) that
--    terminate the Light Weight Access Point Protocol
--    tunnel from Light-weight LWAPP Access Points.
--    
--    This MIB provides configuration and status information
--    about the 802.11 Access Points that have joined the
--    controller.                 
--    
--    The relationship between CC and the LWAPP APs
--    can be depicted as follows:
--    
--    +......+     +......+     +......+           +......+
--    +      +     +      +     +      +           +      +
--    +  CC  +     +  CC  +     +  CC  +           +  CC  +
--    +      +     +      +     +      +           +      +
--    +......+     +......+     +......+           +......+
--    ..            .             .                 .
--    ..            .             .                 .
--    .  .            .             .                 .
--    .    .            .             .                 .
--    .      .            .             .                 .
--    .        .            .             .                 .
--    +......+ +......+     +......+      +......+          +......+
--    +      + +      +     +      +      +      +          +      +
--    +  AP  + +  AP  +     +  AP  +      +  AP  +          +  AP  +
--    +      + +      +     +      +      +      +          +      +
--    +......+ +......+     +......+      +......+          +......+
--    .              .             .                 .
--    .  .              .             .                 .
--    .    .              .             .                 .
--    .      .              .             .                 .
--    .        .              .             .                 .
--    +......+ +......+     +......+      +......+          +......+
--    +      + +      +     +      +      +      +          +      +
--    +  MN  + +  MN  +     +  MN  +      +  MN  +          +  MN  +
--    +      + +      +     +      +      +      +          +      +
--    +......+ +......+     +......+      +......+          +......+
--    
--    
--    The LWAPP tunnel exists between the controller and
--    the APs.  The MNs communicate with the APs through
--    the protocol defined by the 802.11 standard.
--    
--    LWAPP APs, upon bootup, discover and join one of the
--    controllers and the controller pushes the configuration,
--    that includes the WLAN parameters, to the LWAPP APs.
--    The APs then encapsulate all the 802.11 frames from
--    wireless clients inside LWAPP frames and forward
--    the LWAPP frames to the controller.
--    
--                       GLOSSARY
--    
--    Access Point ( AP )
--    
--    An entity that contains an 802.11 medium access
--    control ( MAC ) and physical layer ( PHY ) interface
--    and provides access to the distribution services via
--    the wireless medium for associated clients.  
--    
--    LWAPP APs encapsulate all the 802.11 frames in
--    LWAPP frames and sends it to the controller to which
--    it is logically connected.
--    
--    Basic Service Set Identifier (BSSID)
--    
--    The identifier for the service set comprising of
--    all the 802.11 stations under the control of
--    one coordinating Access Point.  This identifier
--    happens to be the MAC address of the dot11 radio
--    interface of the Access Point.  The wireless
--    clients that associate with the Access Point
--    get the wired uplink through this particular 
--    dot11 interface. 
--    
--    Central Controller ( CC )
--    
--    The central entity that terminates the LWAPP protocol
--    tunnel from the LWAPP APs.  Throughout this MIB,
--    this entity also referred to as 'controller'. 
--    
--    Light Weight Access Point Protocol ( LWAPP ) 
--    
--    This is a generic protocol that defines the 
--    communication between the Access Points and the
--    Central Controller. 
--    
--    Mobile Node ( MN )
--    
--    A roaming 802.11 wireless device in a wireless
--    network associated with an access point. 
--    
--    Station Management (SMT)
--    
--    This term refers to the internal management of the
--    802.11 protocol operations by the AP to work
--    cooperatively with the other APs and 802.11
--    devices in the network.
--    
--    REFERENCE
--    
--    [1] Part 11 Wireless LAN Medium Access Control ( MAC )
--    and Physical Layer ( PHY ) Specifications.
--    
--    [2] Draft-obara-capwap-lwapp-00.txt, IETF Light 
--    Weight Access Point Protocol. 
--  RevDate
--    200603300000Z
--  RevDescr
--    Initial version of this MIB module. 

ciscoLwappApMIBNotifs OBJECT IDENTIFIER ::= { ciscoLwappApMIB 0 }
ciscoLwappApMIBObjects OBJECT IDENTIFIER ::= { ciscoLwappApMIB 1 }
ciscoLwappApMIBConform OBJECT IDENTIFIER ::= { ciscoLwappApMIB 2 }
ciscoLwappAp    OBJECT IDENTIFIER ::= { ciscoLwappApMIBObjects 1 }
ciscoLwappApIf  OBJECT IDENTIFIER ::= { ciscoLwappApMIBObjects 2 }
ciscoLwappApMIBCompliances OBJECT IDENTIFIER ::= { ciscoLwappApMIBConform 1 }
ciscoLwappApMIBGroups OBJECT IDENTIFIER ::= { ciscoLwappApMIBConform 2 }

cLApTable OBJECT-TYPE
    SYNTAX SEQUENCE OF CLApEntry
    ACCESS not-accessible
    STATUS mandatory
    DESCRIPTION
        "This table represents the information about the
        802.11 LWAPP Access Points that have joined the
        controller.
        
        LWAPP APs exchange configuration messages with the
        controller and get the required configuration for
        their 802.11 related operations, after they join the
        controller. "
    ::= { ciscoLwappAp 1 }

cLApEntry OBJECT-TYPE
    SYNTAX CLApEntry
    ACCESS not-accessible
    STATUS mandatory
    DESCRIPTION
        "Each entry in this table provides information about
        one 802.11 LWAPP Access Point that has joined the
        controller.
        
        Entries are removed when the APs lose their
        association with the controller due to loss
        of communication. "
    INDEX { cLApSysMacAddress }
    ::= { cLApTable 1 }

CLApEntry ::= SEQUENCE {
    cLApSysMacAddress MacAddress,
    cLApIfMacAddress MacAddress,
    cLApMaxNumberOfDot11Slots Gauge
    }

cLApSysMacAddress OBJECT-TYPE
    SYNTAX MacAddress
--    Rsyntax OCTET STRING(SIZE(6))
    ACCESS not-accessible
    STATUS mandatory
    DESCRIPTION
        "This object represents the radio MAC address 
        common to the dot11 interfaces of the AP
        and uniquely identifies an entry in this table. "
    ::= { cLApEntry 1 }

cLApIfMacAddress OBJECT-TYPE
    SYNTAX MacAddress
--    Rsyntax OCTET STRING(SIZE(6))
    ACCESS read-only
    STATUS mandatory
    DESCRIPTION
        "This object represents the Ethernet MAC address of
        the AP. "
    ::= { cLApEntry 2 }

cLApMaxNumberOfDot11Slots OBJECT-TYPE
    SYNTAX Gauge
    ACCESS read-only
    STATUS mandatory
    DESCRIPTION
        "This object represents the maximum number of
        802.11 radio interface slots in this AP. "
    ::= { cLApEntry 3 }

cLApDot11IfTable OBJECT-TYPE
    SYNTAX SEQUENCE OF CLApDot11IfEntry
    ACCESS not-accessible
    STATUS mandatory
    DESCRIPTION
        "This table represents the information about the
        basic functional parameters corresponding to
        the dot11 interfaces of the APs that have joined
        the controller. "
    ::= { ciscoLwappApIf 1 }

cLApDot11IfEntry OBJECT-TYPE
    SYNTAX CLApDot11IfEntry
    ACCESS not-accessible
    STATUS mandatory
    DESCRIPTION
        "An entry in this table represents the 802.11
        functional parameters of the dot11 interface of
        an AP that has joined the controller.
        
        Entries are added when the APs associate to this
        controller and deleted when they lose their
        association. "
    INDEX { cLApSysMacAddress, cLApDot11IfSlotId }
    ::= { cLApDot11IfTable 1 }

CLApDot11IfEntry ::= SEQUENCE {
    cLApDot11IfSlotId Gauge,
    cLApDot11IfType CLApIfType
    }

cLApDot11IfSlotId OBJECT-TYPE
    SYNTAX Gauge
    ACCESS not-accessible
    STATUS mandatory
    DESCRIPTION
        "This object represents the slot ID of a dot11
        interface on an AP. 
        
        The slot ID for a particular dot11 interface as
        represented by this object ranges from 0 to 
        cLApMaxNumberOfDot11Slots - 1. "
    ::= { cLApDot11IfEntry 1 }

cLApDot11IfType OBJECT-TYPE
    SYNTAX CLApIfType
--    Rsyntax INTEGER {
--        dot11bg(1),
--        dot11a(2),
--        uwb(3)
--        }
    ACCESS read-only
    STATUS mandatory
    DESCRIPTION
        "This object represents the type of this dot11
        interface. "
    ::= { cLApDot11IfEntry 2 }

cLApIfSmtParamTable OBJECT-TYPE
    SYNTAX SEQUENCE OF CLApIfSmtParamEntry
    ACCESS not-accessible
    STATUS mandatory
    DESCRIPTION
        "This table represents the station management
        information in the APs that have joined the
        controller.  Information populated through the
        entries of this table is used by the AP to
        perform the expected 802.11 operations on
        the respective dot11 interfaces to coordinate with
        other 802.11 devices in the network.
        
        Since this table has the indices defined in the
        tables cLApTable and cLApDot11IfTable, an entry in
        this table is automatically removed when the
        respective entry is removed in either of those
        tables. "
    ::= { ciscoLwappAp 2 }

cLApIfSmtParamEntry OBJECT-TYPE
    SYNTAX CLApIfSmtParamEntry
    ACCESS not-accessible
    STATUS mandatory
    DESCRIPTION
        "An entry in this table represents the information
        pertaining to one particular dot11 interface of
        this AP used to perform the 802.11 protocol
        operations on the respective dot11 interface.
        
        Rows are added or deleted to this table when
        APs join or leave the controller respectively. "
    INDEX { cLApSysMacAddress, cLApDot11IfSlotId }
    ::= { cLApIfSmtParamTable 1 }

CLApIfSmtParamEntry ::= SEQUENCE {
    cLApIfSmtDot11Bssid MacAddress
    }

cLApIfSmtDot11Bssid OBJECT-TYPE
    SYNTAX MacAddress
--    Rsyntax OCTET STRING(SIZE(6))
    ACCESS read-only
    STATUS mandatory
    DESCRIPTION
        "This object defines the base BSSID of this AP, which
        is the MAC address of the radio interface of this
        AP. "
    ::= { cLApIfSmtParamEntry 1 }

ciscoLwappApGroup OBJECT IDENTIFIER ::= { ciscoLwappApMIBGroups 1 }
-- OBJECT-GROUP
--  Status
--    mandatory
--  Descr
--    This collection of objects represents the information
--    about the general attributes and functional 
--    parameters of those APs that have joined the
--    controller. 
--  objects
--    cLApIfMacAddress, cLApMaxNumberOfDot11Slots, 
--    cLApIfSmtDot11Bssid

ciscoLwappApIfGroup OBJECT IDENTIFIER ::= { ciscoLwappApMIBGroups 2 }
-- OBJECT-GROUP
--  Status
--    mandatory
--  Descr
--    This collection of objects represents the information
--    about the dot11 interfaces of those APs that have 
--    joined the controller. 
--  objects
--    cLApDot11IfType

ciscoLwappApMIBCompliance OBJECT IDENTIFIER ::= { ciscoLwappApMIBCompliances 1 }
-- MODULE-COMPLIANCE
--  Status
--    mandatory
--  Descr
--    The compliance statement for the SNMP entities that
--    implement the ciscoLwappApMIB module. 
--  Module
--    >>current<<
--   MandGroup
--    ciscoLwappApGroup
--   MandGroup
--    ciscoLwappApIfGroup


END
