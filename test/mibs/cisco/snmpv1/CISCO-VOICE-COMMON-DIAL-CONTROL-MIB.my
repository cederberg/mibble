-- MIB created 9/05/100 11:41:18, by
--   SMIC (the next generation) version 1.6.29, November 22, 1994.

CISCO-VOICE-COMMON-DIAL-CONTROL-MIB DEFINITIONS ::= BEGIN

-- From file: "CISCO-VOICE-COMMON-DIAL-CONTROL-MIB.my"

IMPORTS
    OBJECT-TYPE
            FROM RFC-1212
    TruthValue
            FROM SNMPv2-TC-v1
    callActiveSetupTime, callActiveIndex
            FROM DIAL-CONTROL-MIB
    cCallHistoryIndex
            FROM CISCO-DIAL-CONTROL-MIB
    ciscoExperiment
            FROM CISCO-SMI;

ciscoVoiceCommonDialControlMIB OBJECT IDENTIFIER ::= { ciscoExperiment 55 }
-- MODULE-IDENTITY
--  LastUpdated
--    9906180000Z
--  OrgName
--    Cisco Systems, Inc.
--  ContactInfo
--           Cisco Systems
--            Customer Service
--    
--    Postal: 170 W. Tasman Drive
--            San Jose, CA  95134
--            USA
--    
--    Tel: +1 800 553-NETS
--    
--    E-mail: cs-voice@cisco.com
--  Descr
--    This MIB module contains voice related objects that
--     are common across more than one network
--     encapsulation i.e VoIP, VoATM and VoFR.

cvCommonDcMIBObjects OBJECT IDENTIFIER ::= { ciscoVoiceCommonDialControlMIB 1 }
cvCommonDcCallActive OBJECT IDENTIFIER ::= { cvCommonDcMIBObjects 1 }
cvCommonDcCallHistory OBJECT IDENTIFIER ::= { cvCommonDcMIBObjects 2 }
cvCommonDcMIBNotificationPrefix OBJECT IDENTIFIER ::= { ciscoVoiceCommonDialControlMIB 2 }
cvCommonDcMIBNotifications OBJECT IDENTIFIER ::= { cvCommonDcMIBNotificationPrefix 0 }
cvCommonDcMIBConformance OBJECT IDENTIFIER ::= { ciscoVoiceCommonDialControlMIB 3 }
cvCommonDcMIBCompliances OBJECT IDENTIFIER ::= { cvCommonDcMIBConformance 1 }
cvCommonDcMIBGroups OBJECT IDENTIFIER ::= { cvCommonDcMIBConformance 2 }

CvcSpeechCoderRate ::= INTEGER {
        g729r8000(1),
        g729Ar8000(2),
        g726r16000(3),
        g726r24000(4),
        g726r32000(5),
        g711ulawr64000(6),
        g711Alawr64000(7),
        g728r16000(8),
        g723r6300(9),
        g723r5300(10),
        gsmr13200(11),
        g729Br8000(12),
        g729ABr8000(13),
        g723Ar6300(14),
        g723Ar5300(15),
        g729IETFr8000(16)
        }
-- TEXTUAL-CONVENTION
--  Status
--    mandatory
--  Descr
--    This object specifies the most desirable codec of speech
--     for the VoIP, VoATM or VoFR peer.
--     g729r8000      - pre-IETF G.729 8000  bps
--     g729Ar8000     - G.729 ANNEX-A 8000  bps
--     g726r16000     - G.726 16000 bps
--     g726r24000     - G.726 24000 bps
--     g726r32000     - G.726 32000 bps
--     g711ulawr64000 - G.711 u-Law 64000 bps
--     g711Alawr64000 - G.711 A-Law 64000 bps
--     g728r16000     - G.728 16000 bps
--     g723r6300      - G.723.1 6300 bps
--     g723r5300      - G.723.1 5300 bps
--     gsmr13200      - GSM Full rate 13200 bps
--     g729Br8000     - G.729 ANNEX-B 8000  bps
--     g729ABr8000    - G.729 ANNEX-A & B 8000 bps
--     g723Ar6300     - G723.1 Annex A 6300 bps
--     g723Ar5300     - G723.1 Annex A 5300 bps
--     g729IETFr8000  - IETF G.729 8000  bps

CvcFaxTransmitRate ::= INTEGER {
        none(1),
        voiceRate(2),
        fax2400(3),
        fax4800(4),
        fax7200(5),
        fax9600(6),
        fax14400(7),
        fax12000(8)
        }
-- TEXTUAL-CONVENTION
--  Status
--    mandatory
--  Descr
--     This object specifies the default transmit rate of FAX
--      for the VoIP, VoATM or VOFR peer. If the value of this
--      object is 'none', then the Fax relay feature is disabled
--      ; otherwise the Fax relay feature is enabled.
--    
--      none      - Fax relay is disabled.
--      voiceRate - the fastest possible fax rate not exceed
--                  the configured voice rate.
--      fax2400   - 2400  bps FAX transmit rate.
--      fax4800   - 4800  bps FAX transmit rate.
--      fax7200   - 7200  bps FAX transmit rate.
--      fax9600   - 9600  bps FAX transmit rate.
--      fax14400  - 14400 bps FAX transmit rate.
--      fax12000  - 12000 bps FAX transmit rate.

CvcCoderTypeRate ::= INTEGER {
        other(1),
        fax2400(2),
        fax4800(3),
        fax7200(4),
        fax9600(5),
        fax14400(6),
        fax12000(7),
        g729r8000(10),
        g729Ar8000(11),
        g726r16000(12),
        g726r24000(13),
        g726r32000(14),
        g711ulawr64000(15),
        g711Alawr64000(16),
        g728r16000(17),
        g723r6300(18),
        g723r5300(19),
        gsmr13200(20),
        g729Br8000(21),
        g729ABr8000(22),
        g723Ar6300(23),
        g723Ar5300(24),
        ietfg729r8000(25)
        }
-- TEXTUAL-CONVENTION
--  Status
--    mandatory
--  Descr
--    Represents the coder type-rate for voice/fax compression
--     used during a call.
--    
--     other          - none of the following.
--     fax2400        - FAX   2400  bps
--     fax4800        - FAX   4800  bps
--     fax7200        - FAX   7200  bps
--     fax9600        - FAX   9600  bps
--     fax14400       - FAX   14400 bps
--     fax12000       - FAX   12000 bps
--     g729r8000      - G.729 8000  bps (pre-IETF bit ordering)
--     g729Ar8000     - G.729 ANNEX-A 8000  bps
--     g726r16000     - G.726 16000 bps
--     g726r24000     - G.726 24000 bps
--     g726r32000     - G.726 32000 bps
--     g711ulawr64000 - G.711 u-Law 64000 bps
--     g711Alawr64000 - G.711 A-Law 64000 bps
--     g728r16000     - G.728 16000 bps
--     g723r6300      - G.723.1 6300 bps
--     g723r5300      - G.723.1 5300 bps
--     gsmr13200      - GSM full rate 13200 bps
--     g729Br8000     - G.729 ANNEX-B 8000  bps
--     g729ABr8000    - G.729 ANNEX-A & B 8000 bps
--     g723Ar6300     - G723.1 Annex A 6300 bps
--     g723Ar5300     - G723.1 Annex A 5300 bps
--     ietfg729r8000  - G.729 8000 bps (IETF bit ordering)

CvcGUid ::= OCTET STRING(SIZE(0..16))
-- TEXTUAL-CONVENTION
--  Status
--    mandatory
--  Descr
--    Represents a Global Call Identifier.
--     The global call identifier is used as an unique identifier
--     for an end-to-end call.
--     A zero length CvcGUid indicates no value for the global call
--     identifier.

CvcInBandSignaling ::= INTEGER {
        cas(1),
        none(2),
        cept(3),
        transparent(4)
        }
-- TEXTUAL-CONVENTION
--  Status
--    mandatory
--  Descr
--    Represents the type of in-band signaling used between the
--     two end points of the call and is used to inform the
--     router how intepret the ABCD signaling data bits passed
--     as part of the voice payload data.
--    
--     cas         - specifies intepret the signaling bits as
--                   North American Channel Associated signaling.
--     none        - specifies no in-band signaling or signaling
--                   is being done via an external method (e.g
--                   CCS).
--     cept        - specifies interpret the signaling bits as
--                   MELCAS
--     transparent - specifies do not interpret or translate the
--                   signaling bits.

cvCommonDcCallActiveTable OBJECT-TYPE
    SYNTAX SEQUENCE OF CvCommonDcCallActiveEntry
    ACCESS not-accessible
    STATUS mandatory
    DESCRIPTION
        "This table is a common extension to the call active table of
         IETF Dial Control MIB. It contains common call leg information
         about a network call leg."
    ::= { cvCommonDcCallActive 1 }

cvCommonDcCallActiveEntry OBJECT-TYPE
    SYNTAX CvCommonDcCallActiveEntry
    ACCESS not-accessible
    STATUS mandatory
    DESCRIPTION
        "The common information regarding a single network call leg.
         The call leg entry is identified by using the same index
        objects
         that are used by Call Active table of IETF Dial Control MIB to
         identify the call.
         An entry of this table is created when its associated call
         active entry in the IETF Dial Control MIB is created and the
         call active entry contains information for the call
         establishment to a network dialpeer.
         The entry is deleted when its associated call active entry in
         the IETF Dial Control MIB is deleted."
    INDEX { callActiveSetupTime, callActiveIndex }
    ::= { cvCommonDcCallActiveTable 1 }

CvCommonDcCallActiveEntry ::= SEQUENCE {
    cvCommonDcCallActiveConnectionId CvcGUid,
    cvCommonDcCallActiveVADEnable TruthValue,
    cvCommonDcCallActiveCoderTypeRate CvcCoderTypeRate,
    cvCommonDcCallActiveCodecBytes INTEGER,
    cvCommonDcCallActiveInBandSignaling CvcInBandSignaling
    }

cvCommonDcCallActiveConnectionId OBJECT-TYPE
    SYNTAX CvcGUid
--    Rsyntax OCTET STRING(SIZE(0..16))
    ACCESS read-only
    STATUS mandatory
    DESCRIPTION
        "The global call identifier for the network call."
    ::= { cvCommonDcCallActiveEntry 1 }

cvCommonDcCallActiveVADEnable OBJECT-TYPE
    SYNTAX TruthValue
--    Rsyntax INTEGER {
--        true(1),
--        false(2)
--        }
    ACCESS read-only
    STATUS mandatory
    DESCRIPTION
        "The object indicates whether or not the VAD (Voice Activity
         Detection) is enabled for the voice call."
    ::= { cvCommonDcCallActiveEntry 2 }

cvCommonDcCallActiveCoderTypeRate OBJECT-TYPE
    SYNTAX CvcCoderTypeRate
--    Rsyntax INTEGER {
--        other(1),
--        fax2400(2),
--        fax4800(3),
--        fax7200(4),
--        fax9600(5),
--        fax14400(6),
--        fax12000(7),
--        g729r8000(10),
--        g729Ar8000(11),
--        g726r16000(12),
--        g726r24000(13),
--        g726r32000(14),
--        g711ulawr64000(15),
--        g711Alawr64000(16),
--        g728r16000(17),
--        g723r6300(18),
--        g723r5300(19),
--        gsmr13200(20),
--        g729Br8000(21),
--        g729ABr8000(22),
--        g723Ar6300(23),
--        g723Ar5300(24),
--        ietfg729r8000(25)
--        }
    ACCESS read-only
    STATUS mandatory
    DESCRIPTION
        "The negotiated coder rate. It specifies the transmit rate of
         voice/fax compression to its associated call leg for the call.
         This rate is different from the configuration rate because of
         rate negotiation during the call."
    ::= { cvCommonDcCallActiveEntry 3 }

cvCommonDcCallActiveCodecBytes OBJECT-TYPE
    SYNTAX INTEGER(10..255)
    ACCESS read-only
    STATUS mandatory
    DESCRIPTION
        "Specifies the payload size of the voice packet."
    ::= { cvCommonDcCallActiveEntry 4 }

cvCommonDcCallActiveInBandSignaling OBJECT-TYPE
    SYNTAX CvcInBandSignaling
--    Rsyntax INTEGER {
--        cas(1),
--        none(2),
--        cept(3),
--        transparent(4)
--        }
    ACCESS read-only
    STATUS mandatory
    DESCRIPTION
        "Specifies the type of in-band signaling being used on the call."
    ::= { cvCommonDcCallActiveEntry 5 }

cvCommonDcCallHistoryTable OBJECT-TYPE
    SYNTAX SEQUENCE OF CvCommonDcCallHistoryEntry
    ACCESS not-accessible
    STATUS mandatory
    DESCRIPTION
        "This table is the Common extension to the call history table of
         IETF Dial Control MIB. It contains Common call leg information
         about a network call leg."
    ::= { cvCommonDcCallHistory 1 }

cvCommonDcCallHistoryEntry OBJECT-TYPE
    SYNTAX CvCommonDcCallHistoryEntry
    ACCESS not-accessible
    STATUS mandatory
    DESCRIPTION
        "The common information regarding a single network call leg.
         The call leg entry is identified by using the same index
         objects that are used by Call Active table of IETF Dial
         Control MIB to identify the call.
         An entry of this table is created when its associated call
         history entry in the IETF Dial Control MIB is created and the
         call history entry contains information for the call
         establishment to a network dialpeer.
         The entry is deleted when its associated call history entry in
         the IETF Dial Control MIB is deleted."
    INDEX { cCallHistoryIndex }
    ::= { cvCommonDcCallHistoryTable 1 }

CvCommonDcCallHistoryEntry ::= SEQUENCE {
    cvCommonDcCallHistoryConnectionId CvcGUid,
    cvCommonDcCallHistoryVADEnable TruthValue,
    cvCommonDcCallHistoryCoderTypeRate CvcCoderTypeRate,
    cvCommonDcCallHistoryCodecBytes INTEGER,
    cvCommonDcCallHistoryInBandSignaling CvcInBandSignaling
    }

cvCommonDcCallHistoryConnectionId OBJECT-TYPE
    SYNTAX CvcGUid
--    Rsyntax OCTET STRING(SIZE(0..16))
    ACCESS read-only
    STATUS mandatory
    DESCRIPTION
        "The global call identifier for the gateway call."
    ::= { cvCommonDcCallHistoryEntry 1 }

cvCommonDcCallHistoryVADEnable OBJECT-TYPE
    SYNTAX TruthValue
--    Rsyntax INTEGER {
--        true(1),
--        false(2)
--        }
    ACCESS read-only
    STATUS mandatory
    DESCRIPTION
        "The object indicates whether or not the VAD (Voice Activity
         Detection) was enabled for the voice call."
    ::= { cvCommonDcCallHistoryEntry 2 }

cvCommonDcCallHistoryCoderTypeRate OBJECT-TYPE
    SYNTAX CvcCoderTypeRate
--    Rsyntax INTEGER {
--        other(1),
--        fax2400(2),
--        fax4800(3),
--        fax7200(4),
--        fax9600(5),
--        fax14400(6),
--        fax12000(7),
--        g729r8000(10),
--        g729Ar8000(11),
--        g726r16000(12),
--        g726r24000(13),
--        g726r32000(14),
--        g711ulawr64000(15),
--        g711Alawr64000(16),
--        g728r16000(17),
--        g723r6300(18),
--        g723r5300(19),
--        gsmr13200(20),
--        g729Br8000(21),
--        g729ABr8000(22),
--        g723Ar6300(23),
--        g723Ar5300(24),
--        ietfg729r8000(25)
--        }
    ACCESS read-only
    STATUS mandatory
    DESCRIPTION
        "The negotiated coder rate. It specifies the transmit rate of
         voice/fax compression to its associated call leg for the call.
         This rate is different from the configuration rate because of
         rate negotiation during the call."
    ::= { cvCommonDcCallHistoryEntry 3 }

cvCommonDcCallHistoryCodecBytes OBJECT-TYPE
    SYNTAX INTEGER(10..255)
    ACCESS read-only
    STATUS mandatory
    DESCRIPTION
        "Specifies the payload size of the voice packet."
    ::= { cvCommonDcCallHistoryEntry 4 }

cvCommonDcCallHistoryInBandSignaling OBJECT-TYPE
    SYNTAX CvcInBandSignaling
--    Rsyntax INTEGER {
--        cas(1),
--        none(2),
--        cept(3),
--        transparent(4)
--        }
    ACCESS read-only
    STATUS mandatory
    DESCRIPTION
        "Specifies the type of in-band signaling used on the call."
    ::= { cvCommonDcCallHistoryEntry 5 }

cvCommonDcCallGroup OBJECT IDENTIFIER ::= { cvCommonDcMIBGroups 1 }
-- OBJECT-GROUP
--  Status
--    mandatory
--  Descr
--    A collection of objects providing the common network
--     call leg information.
--  objects
--    cvCommonDcCallActiveConnectionId, 
--    cvCommonDcCallActiveVADEnable, 
--    cvCommonDcCallActiveCoderTypeRate, 
--    cvCommonDcCallActiveCodecBytes, 
--    cvCommonDcCallActiveInBandSignaling, 
--    cvCommonDcCallHistoryConnectionId, 
--    cvCommonDcCallHistoryVADEnable, 
--    cvCommonDcCallHistoryCoderTypeRate, 
--    cvCommonDcCallHistoryCodecBytes, 
--    cvCommonDcCallHistoryInBandSignaling

cvCommonDcMIBCompliance OBJECT IDENTIFIER ::= { cvCommonDcMIBCompliances 1 }
-- MODULE-COMPLIANCE
--  Status
--    mandatory
--  Descr
--    The compliance statement for entities which
--     implement the CISCO VOICE COMMON MIB
--  Module
--    >>current<<
--   MandGroup
--    cvCommonDcCallGroup


END
