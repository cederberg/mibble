-- $ID$
-- ********************************************************************
-- CISCO-GTP-MIB.my: MIB file for GPRS Tunnelling Protocol(GTP)
-- 
-- Feb 8 2000, Huiyang Yang.
-- June 2001, Rajesh M. L.
-- September 2001, Jeyachitra Alagar
--
-- Copyright (c) 2000, 2001 by cisco Systems, Inc.
-- All rights reserved.
-- ********************************************************************
-- $Endlog$

CISCO-GTP-MIB DEFINITIONS ::= BEGIN
 
IMPORTS
        MODULE-IDENTITY,
        NOTIFICATION-TYPE,
        OBJECT-TYPE,
        Integer32,
        Counter32,
        Gauge32
                FROM SNMPv2-SMI
        TruthValue
                FROM SNMPv2-TC
        Unsigned32
                FROM CISCO-TC
        InetAddressType,
        InetAddress
                FROM INET-ADDRESS-MIB
        MODULE-COMPLIANCE,
        OBJECT-GROUP,
        NOTIFICATION-GROUP
                FROM SNMPv2-CONF
        ciscoMgmt
                FROM CISCO-SMI;


cGtpMIB MODULE-IDENTITY
        LAST-UPDATED    "200109131535Z"
        ORGANIZATION    "Cisco Systems, Inc."
        CONTACT-INFO
                "       Cisco Systems
                        Customer Service
 
                Postal: 170 W Tasman Drive
                        San Jose, CA  95134
                        USA
 
                   Tel: +1 800 553-NETS
 
                E-mail: cs-gprs@cisco.com"
        DESCRIPTION
                "This MIB module manages the GPRS Tunnelling Protocol
                (GTP) on GGSN and SGSN.

                GPRS provides wireless access to packet data network on
                the GSM infrastructure.

                The following diagram illustrates a simplified GPRS
                logical architecture with the name of inter-node
                interface:
               
                +---------------------------------------------+         
                |                         +======+   a PLMN   | 
                |                         | SGSN |            |
                |                         +======+            |
                |                            |                |
                |                            Gn               |
                |                            |                |
                |+====+   +====+ +=====+ +======+    +======+ |    +===+
                || TE |-R-| MT |-| BSS |-| SGSN |-Gn-| GGSN |-|-Gi-|PDN|
                |+====+   +====+ +=====+ +======+    +======+ |    +===+
                |                                        |    |  
                |                                        |    | 
                +----------------------------------------|----+ 
                                                         Gp
                                                         |
                                +-----------------------------+
                                | +====+   +=====+   +======+ |   
                                | | MS |---| BSS |---| SGSN | |
                                | +====+   +=====+   +======+ |  
                                |                             | 
                                |                other PLMN   |
                                +-----------------------------+
                
                GTP is the protocol between GSN nodes (GSN peers) in
                the GPRS backbone network. It includes both the GTP
                signalling and data transfer procedures.

                GTP is used both on the Gn interface, i.e. the interface
                between GSN peers with in a PLMN, and the Gp
                interface between GSN peers in different PLMNs.
 
                SGSN is the serving GPRS support node, it responsible 
                for the delivery of data packets from and to the MS 
                within its service area.

                GGSN is the gateway GPRS support node, it provides 
                interworking with external PDN and is connected with 
                SGSNs via an IP-based GPRS backbone network.

                The GTP protocol is implemented only by SGSNs and GGSN.

                A PDP Context is an information set maintained by MS 
                and GSNs which describes the mobile wireless service
                call or session.

                A Qos Profile is associated with each PDP context which
                defines multiple attributes like precedence, delay, 
                reliability, peak throughput and mean throughput.
                Based on the precedence, delay and mean throughput an
                user is classified into one of the three Qos classes:
                Best Effort, Normal and Premium.
                
                Mean throughput is measured at the Gi and R reference 
                points in units of octets per second. It specifies the 
                average rate at which data is expected to be 
                transferred across the GPRS network during the 
                remaining lifetime of an activated PDP context.
                
                Acronyms and terms:

                 APN    Access Point Name
                 BSS    Base Station Subsystem
                 ETSI   European Telecommunications Standards Institute
                 GDM    GTP Director Module
                 Gi     Reference point between GPRS and an external 
                        packet data network.
                 Gn     the interface between GSNs within a PLMN 
                 Gp     the interface between GSNs in different PLMNs 
                 GGSN   Gateway GPRS Support Node
                 GPRS   General Packet Radio Service
                 GSM    Global System for Mobile communication
                 GSN    GPRS Support Node
                 G-PDU  GTP PDU 
                 MS     Mobile Station = TE + MT
                 MT     Mobile Termination
                 NMS    Network Management System
                 PDN    Public Data Network
                 PDP    Packet Data Protocol
                 PDU    Protocol Data Unit
                 PLMN   Public Land Mobile Network
                 R      Reference point between a non-ISDN compatible 
                        TE and MT. 
                 SGSN   Serving GPRS Support Node
                 TE     Terminal Equipment
                 T-PDU  the payload of G-PDU 
                 "

        REVISION       "200109131535Z"
        DESCRIPTION
                 "Modified the default value for cGtpMaximumPdps from 
                 1000 to 10000.

                 Added 'gtpdirector' to the enumeration of cGtpService.

                 The APN identifies whether the network is corporate 
                 or service provider network.  

                 The Single Access point feature enables the
                 service provider to add new access-points to the GGSN
                 without having to provision the HLR. The requests are
                 sent by the SGSN to the same virtual APN. A virtual
                 APN is not associated with any actual physical
                 network.  The GGSN processes the request and forwards
                 the packet to the appropriate access-point that is
                 specified in the PCO. This feature is supported only
                 in Cisco GGSNs.

                 The purpose of the GTP-Director is to provide a
                 mechanism for service providers using non-Cisco GGSN
                 to use the Single APN feature. 

                +==+  +===+  +====+   ====   +===+  +====+     +===+
                |MS|--|BSS|--|SGSN|--|PLMN|--|GDM|--|GGSN|--Gi-|PDN|
                +==+  +===+  +====+   ====   +===+  +====+     +===+
                                              | |
                                              | |   +====+
                                              | |___|GGSN|------Gi
                                              |     +====+       |
                                              |                  |
                                              |     +====+     +===+
                                              |_____|GGSN|--Gi-|PDN|
                                                    +====+     +===+

                 The GTP-Director also provides load balancing, using 
                 round robin mechanism, across GGSNs.  The
                 Cisco GGSNs may use the GTP-Director, but is not
                 necessary as they can use IOS-SLB ( Server Load
                 Balancing ).
                 "
        REVISION       "200106111600Z"
        DESCRIPTION   
                "* Added cGtpDynamicEchoTimerEnable,
                   cGtpDynamicEchoTimerMinTime, 
                   cGtpDynamicEchoTimerSmoothFactor.
                 * Deprecated cGtpGSNTotalBandwidthResrc,
                   cGtpPremiumQosMeanThroughput, 
                   cGtpNormalQosMeanThroughput,
                   cGtpBestEffortQosMeanThroughput, 
                   cGtpCurrentUsedBandwidth."
        REVISION       "200102071300Z"
        DESCRIPTION    
                "Initial version of this MIB module."
        ::= { ciscoMgmt 188 }

--      REFERENCE
--
--      "[1] GSM 03.60: Digital cellular telecommunications
--           system (Phase 2+); General Packet Radio Service
--           (GPRS); Service description; Stage 2. V7.1.0
--
--       [2] GSM 09.60: Digital cellular telecommunication
--           system (Phase 2+); General Packet Radio Service
--           (GPRS); GPRS Tunnelling Protocol (GTP) across
--           Gn and Gp Interface. V7.3.0"

-- 
-- Object definitions
-- 

cGtpMIBObjects      OBJECT IDENTIFIER
                        ::= { cGtpMIB 1 }

cGtpConfigurations  OBJECT IDENTIFIER
                        ::= { cGtpMIBObjects 1 }
cGtpStatus          OBJECT IDENTIFIER
                        ::= { cGtpMIBObjects 2 }
cGtpStatistics      OBJECT IDENTIFIER
                        ::= { cGtpMIBObjects 3 }
 
-- 
--  Configuration 
--  

cGtpGSNService            OBJECT-TYPE
    SYNTAX                BITS { 
                                 undefined(0),
                                 sgsn(1),
                                 ggsn(2),
                                 gtpdirector(3)
                               }
    MAX-ACCESS            read-write
    STATUS                current
    DESCRIPTION
        "This object indicates the type of GPRS service that will be
        enabled on the device:
           undefined - the GPRS service functionality is turned off.
           ggsn - the device will function as a GGSN.
           sgsn - the device will function as SGSN.
           gtpdirector - the device will function as GDM.

        When the device is configured to function as GDM, all the other
        objects in this MIB will not be accessible and the 
        CISCO-GTP-DIRECTOR-MIB should be used for managing the device.
        "
    DEFVAL { { undefined } }
    ::= { cGtpConfigurations 1 }

cGtpVersion                    OBJECT-TYPE
    SYNTAX                     INTEGER { 
                                  version0(1),
                                  version1(2)
                               }
    MAX-ACCESS                 read-write
    STATUS                     current
    DESCRIPTION
         "The gtp version supported by the GSN.
         "
    ::= { cGtpConfigurations 2 }

cGtpT3TunnelTimer          OBJECT-TYPE
    SYNTAX                 Integer32 (1..65535)
    UNITS                  "seconds"
    MAX-ACCESS             read-write
    STATUS                 current
    DESCRIPTION
       "When the GSN behaves as SGSN, the T3-TUNNEL timer is used 
        for mobility management. When a roaming MS moves from one 
        SGSN(Old SGSN) to a another SGSN(New SGSN), this timer is 
        started by the 'Old SGSN'. While the timer is running, the 
        T-PDUs received by the 'Old SGSN' (from the GGSN), and any 
        buffered T-PDUs are forwarded to the 'New SGSN'. 

        When the GSN behaves as GGSN, the GGSN starts this timer
        after receiving a Update PDP Context request message from 
        'New SGSN'. An Update PDP context request shall be sent by 
        SGSN as part of mobility management intimating that MS has 
        moved to this SGSN. While the timer is running, the GGSN will 
        not be forwarding any PDUs to the requesting 'New SGSN'.
       "
    DEFVAL { 20 }
    ::= { cGtpConfigurations 3 }

cGtpT3ResponseTimer        OBJECT-TYPE
    SYNTAX                 Integer32 (1..65535)
    UNITS                  "seconds"
    MAX-ACCESS             read-write
    STATUS                 current
    DESCRIPTION
        "The T3-RESPONSE timer for retransmission. This timer 
        is started by a GSN, upon the transmission of a signalling 
        request message; it is used for message retransmission 
        purposes, in the event that no response is received by 
        the time the timer expires.
        "
    DEFVAL { 1 }
    ::= { cGtpConfigurations 4 }

cGtpN3Request              OBJECT-TYPE
    SYNTAX                 Integer32 (1..65535)
    UNITS                  "retransmissions"
    MAX-ACCESS             read-write     
    STATUS                 current
    DESCRIPTION
        "Maximum number of retransmissions for a signalling 
         request message if no corresponding response message 
         is received for a request in cGtpT3ResponseTimer time.      
        "      
    DEFVAL { 5 }       
    ::= { cGtpConfigurations 5 }       

cGtpN3BufferSize            OBJECT-TYPE    
    SYNTAX                  Integer32 (2048..65535)      
    UNITS                   "bytes"     
    MAX-ACCESS              read-write     
    STATUS                  current
    DESCRIPTION
        "Maximum size of the receive buffer for G-PDUs and 
        signalling request messages. If a packet arrives with 
        more data bytes than the receive buffer can contain, 
        the packet will be discarded.
        "
    DEFVAL { 8192 }
    ::= { cGtpConfigurations 6 }       
         
cGtpEchoRequestTimerEnable  OBJECT-TYPE
    SYNTAX                  TruthValue
    MAX-ACCESS              read-write
    STATUS                  current
    DESCRIPTION
        "This object indicates whether Echo Request timer
        is used by the GGSN.
        - true  : will enable the Echo Request timer.
        - false : will disable the Echo Request timer.
        "
    DEFVAL { false }
    ::= { cGtpConfigurations 7 }

cGtpEchoRequestTimer        OBJECT-TYPE
    SYNTAX                  Integer32 (60..65535)
    UNITS                   "seconds"
    MAX-ACCESS              read-write
    STATUS                  current 
    DESCRIPTION
        "The time interval to transmit 'Echo Request' message.
         'Echo Response' message is normally received in response
         to 'Echo Request' message. In the event of no response to 
         the 'Echo Request' message, a notification is generated 
         identifying the peer GSN (i.e. cGtpGSN Address), which 
         fails to respond. 

         This object can be retrieved only if 
         cGtpEchoRequestTimerEnable is set to 'true'.
         "
    DEFVAL { 60 }
    ::= { cGtpConfigurations 8 }

cGtpGSNTotalBandwidthResrc   OBJECT-TYPE
    SYNTAX                   Unsigned32 (1..4294967295)
    UNITS                    "bits/sec"
    MAX-ACCESS               read-write
    STATUS                   deprecated
    DESCRIPTION
        "The total amount of bandwidth resource on the GSN,
         this total depends on various factors like system 
         throughput, memory size, maximum number of PDP contexts 
         supported.  A portion of the total resources will be 
         allocated to a user at the PDP context activation time 
         based on the Qos class the user is assigned to.
        "
    DEFVAL { 1048576 }
    ::= { cGtpConfigurations 9 }

cGtpMaximumPdps               OBJECT-TYPE
    SYNTAX                    Unsigned32 (1..4294967295)
    UNITS                     "PDP contexts"
    MAX-ACCESS                read-write
    STATUS                    current 
    DESCRIPTION
        "The maximum number of PDP contexts that can be activated 
        on the GSN.
        "
    DEFVAL { 10000 }
    ::= { cGtpConfigurations 10 }

cGtpNotifEnable               OBJECT-TYPE
    SYNTAX                    TruthValue
    MAX-ACCESS                read-write
    STATUS                    current
    DESCRIPTION
       "Indicates whether cGtpNotifications notification will
        be sent when a notification is generated by the device.
          - 'true',  it will enable the device to send a notification.
          - 'false', it will prevent the device from sending out a
                     notification.
       "
    DEFVAL { false }
    ::= { cGtpConfigurations 11 }

cGtpDynamicEchoTimerEnable   OBJECT-TYPE
    SYNTAX                   TruthValue
    MAX-ACCESS               read-write
    STATUS                   current
    DESCRIPTION
       "This object indicates whether dynamic echo timer is used 
        by the GGSN.
        - true  : will enable the dynamic echo timer.
        - false : will disable the dynamic echo timer.
       "
    DEFVAL { false }
    ::= { cGtpConfigurations 12 }

cGtpDynamicEchoTimerMinTime   OBJECT-TYPE
    SYNTAX                    Integer32 (1..60)
    UNITS                     "seconds"
    MAX-ACCESS                read-write
    STATUS                    current
    DESCRIPTION
       "This object specifies the minimum time used by the 
        dynamic echo timer. This object can be retrieved
        only if cGtpDynamicEchoTimerEnable is set to 'true'.
       "
    DEFVAL { 5 }
    ::= { cGtpConfigurations 13 }

cGtpDynamicEchoTimerSmoothFactor  OBJECT-TYPE
    SYNTAX                        Integer32 (1..100)
    MAX-ACCESS                    read-write
    STATUS                        current
    DESCRIPTION
       "This object specifies the smooth factor by which dynamic 
        echo timer can be adjusted. This object can be retrieved
        only if cGtpDynamicEchoTimerEnable is set to 'true'.
       "
    DEFVAL { 2 }
    ::= { cGtpConfigurations 14 }

--
-- Status
--

cGtpLastNoRespToEchoGSNIpAddrTyp     OBJECT-TYPE
    SYNTAX                           InetAddressType
    MAX-ACCESS                       read-only
    STATUS                           current
    DESCRIPTION
         "This object indicates the type of Internet address
         by which cGtpLastNoRespToEchoGSNIpAddr is reachable."
    ::= { cGtpStatus 1}

cGtpLastNoRespToEchoGSNIpAddr  OBJECT-TYPE
    SYNTAX                     InetAddress 
    MAX-ACCESS                 read-only
    STATUS                     current 
    DESCRIPTION
         "The IP address of the last peer GSN device that did not
         reply to an GTP 'Echo Request' message from the local GSN
         device."
    ::= { cGtpStatus 2}

cGtpPremiumQosMeanThroughput   OBJECT-TYPE
    SYNTAX                     Gauge32
    UNITS                      "bytes/sec"
    MAX-ACCESS                 read-only
    STATUS                     deprecated
    DESCRIPTION
       "The sum of the mean throughput for premium class QOS 
        users on the GSN.
       "
    ::= { cGtpStatus 3 }

cGtpNormalQosMeanThroughput     OBJECT-TYPE
    SYNTAX                      Gauge32
    UNITS                       "bytes/sec"
    MAX-ACCESS                  read-only
    STATUS                      deprecated
    DESCRIPTION
       "The sum of the mean throughput for normal class QOS 
        users on the GSN.
       "
    ::= { cGtpStatus 4 }

cGtpBestEffortQosMeanThroughput  OBJECT-TYPE
    SYNTAX                       Gauge32
    UNITS                        "bytes/sec"
    MAX-ACCESS                   read-only
    STATUS                       deprecated
    DESCRIPTION
       "The sum of the mean throughput for best-effort class 
        QOS users on the GSN. 
       "
    ::= { cGtpStatus 5 }

cGtpGSNTable                     OBJECT-TYPE
    SYNTAX                       SEQUENCE OF CGtpGSNEntry
    MAX-ACCESS                   not-accessible 
    STATUS                       current
    DESCRIPTION
        "GSN peer table. The SGSN-GGSN peer relationship is established
          as given in the following series of steps:
          1. When Mobile System (MS) wants service, it sends packets 
             to a SGSN  with specific APN.
          2. SGSN uses the DNS to resolve this APN to the IP address 
             of the GGSN which is the designated as the gateway to 
             this APN. 
          3. SGSN establishes a path to the GGSN using GTP protocol.
          4. The SGSN and GGSN peer maintains path by sending echo 
             request message to each other. If one side fails in echo 
             reply for certain times, the other side will send a 
             trap to NMS. A SGSN can have multiple GGSN as peers, 
             while a GGSN can have multiple SGSN peers, depending 
             on routing path.
        "
    ::= { cGtpStatus 6 }

cGtpGSNEntry                     OBJECT-TYPE
    SYNTAX                       CGtpGSNEntry
    MAX-ACCESS                   not-accessible
    STATUS                       current
    DESCRIPTION
        "GSN entry. The entry is created when a path between a GGSN
         and SGSN is setup and the corresponding peer is not yet listed 
         in the GSN peer table. The entry is deleted when the path 
         is released, or echo test message on the path times out 
         after certain retry number defined as cGtpN3Request.
        "

    INDEX    { cGtpGSNAddressType, cGtpGSNAddress }
    ::= { cGtpGSNTable 1 }

CGtpGSNEntry ::= SEQUENCE {
    cGtpGSNAddressType    InetAddressType,
    cGtpGSNAddress        InetAddress
    }

cGtpGSNAddressType               OBJECT-TYPE
    SYNTAX                       InetAddressType
    MAX-ACCESS                   not-accessible
    STATUS                       current
    DESCRIPTION
         "The type of Internet address by which cGtpGSNAddress
          is reachable.
         "
    ::= { cGtpGSNEntry 1 }

cGtpGSNAddress                   OBJECT-TYPE
    SYNTAX                       InetAddress
    MAX-ACCESS                   read-only
    STATUS                       current
    DESCRIPTION
         "Ip address that uniquely identify a GSN node.
         "
    ::= { cGtpGSNEntry 2 }

--
-- Statistics
--

cGtpPathFailureOccurrences        OBJECT-TYPE
    SYNTAX                        Counter32
    UNITS                         "times"
    MAX-ACCESS                    read-only
    STATUS                        current
    DESCRIPTION
         "The number of times that any one of this GSN's peers
         failed to respond to an GTP 'Echo Request' messages
         during the waiting intervals." 
    ::= { cGtpStatistics 1 }

cGtpCurrentUsedBandwidth          OBJECT-TYPE
    SYNTAX                        Gauge32
    UNITS                         "bits/sec"
    MAX-ACCESS                    read-only
    STATUS                        deprecated
    DESCRIPTION
        "The current amount of bandwith resource used on the GSN.
        "
    ::= { cGtpStatistics 2 }

cGtpTotalDroppedPackets           OBJECT-TYPE
    SYNTAX                        Counter32
    MAX-ACCESS                    read-only
    STATUS                        current
    DESCRIPTION
         "The total number of received GTP packets that could not
          be processed and are dropped since system started. 
         "
    ::= { cGtpStatistics 3 }

--
--  Notification Definitions
--

cGtpNotifPrefix       OBJECT IDENTIFIER
                           ::= { cGtpMIB 2 }
cGtpNotifications     OBJECT IDENTIFIER
                           ::= { cGtpNotifPrefix 0 }

-- 
-- notifications 
--

cGtpPathFailedNotification  NOTIFICATION-TYPE
    OBJECTS                 { cGtpLastNoRespToEchoGSNIpAddrTyp,
                              cGtpLastNoRespToEchoGSNIpAddr 
                            }
    STATUS                  current 
    DESCRIPTION
        "This notification is sent when one of this GSN's peers 
        failed to respond to the GTP 'Echo Request' message for 
        the waiting interval.
        "
    ::= { cGtpNotifications 1 }


--
-- Conformances definitions
-- 

cGtpMIBConformances   OBJECT IDENTIFIER
                           ::= { cGtpMIB 3 }

cGtpMIBCompliances    OBJECT IDENTIFIER
                           ::= { cGtpMIBConformances 1}
cGtpMIBGroups         OBJECT IDENTIFIER
                           ::= { cGtpMIBConformances 2}

--
-- Compliances statements
--

cGtpMIBCompliance        MODULE-COMPLIANCE
        STATUS           deprecated
        DESCRIPTION
             "The compliance statements for entities which
             implement the CISCO GTP MIB."
        MODULE      -- this module
        MANDATORY-GROUPS { cGtpConfigurationsGroup,
                           cGtpStatusGroup,
                           cGtpStatisticsGroup
                         }

        OBJECT           cGtpVersion
        MIN-ACCESS       read-only
        DESCRIPTION
            "Write access is not required."

        OBJECT           cGtpGSNAddress
        SYNTAX           InetAddress (SIZE (4))
        DESCRIPTION      
            "Support of IPv6 address and DNS is not mandatory."

        ::= { cGtpMIBCompliances 1 }

cGtpMIBComplianceRev1    MODULE-COMPLIANCE
        STATUS           deprecated
        DESCRIPTION
             "The compliance statements for entities which
             implement the CISCO GTP MIB."
        MODULE      -- this module
        MANDATORY-GROUPS { cGtpConfigurationsGroupRev1,
                           cGtpStatusGroupRev1,
                           cGtpStatisticsGroupRev1
                         }

        OBJECT           cGtpVersion
        MIN-ACCESS       read-only
        DESCRIPTION
            "Write access is not required."

        OBJECT           cGtpGSNAddress
        SYNTAX           InetAddress (SIZE (4))
        DESCRIPTION
            "Support of IPv6 address and DNS is not mandatory."

        ::= { cGtpMIBCompliances 2 }

cGtpMIBComplianceRev2    MODULE-COMPLIANCE
        STATUS           current
        DESCRIPTION
             "The compliance statements for entities which
             implement the CISCO GTP MIB."
        MODULE      -- this module
        MANDATORY-GROUPS { cGtpConfigurationsGroupRev1,
                           cGtpStatusGroupRev1,
                           cGtpStatisticsGroupRev1,
                           cGtpNotifGroup
                         }

        OBJECT           cGtpVersion
        MIN-ACCESS       read-only
        DESCRIPTION
            "Write access is not required."

        OBJECT           cGtpGSNAddress
        SYNTAX           InetAddress (SIZE (4))
        DESCRIPTION
            "Support of IPv6 address and DNS is not mandatory."

        ::= { cGtpMIBCompliances 3 }

--
-- units of conformance
--

cGtpConfigurationsGroup       OBJECT-GROUP
    OBJECTS                   { cGtpGSNService, 
                                cGtpVersion,
                                cGtpT3TunnelTimer, 
                                cGtpT3ResponseTimer, 
                                cGtpN3Request, 
                                cGtpN3BufferSize, 
                                cGtpEchoRequestTimer, 
                                cGtpGSNTotalBandwidthResrc, 
                                cGtpMaximumPdps, 
                                cGtpNotifEnable
                              }
    STATUS                    deprecated
    DESCRIPTION
        " A collection of GTP configurations."
    ::= { cGtpMIBGroups 1 }

cGtpStatusGroup               OBJECT-GROUP
    OBJECTS                   { cGtpLastNoRespToEchoGSNIpAddrTyp,
                                cGtpLastNoRespToEchoGSNIpAddr, 
                                cGtpPremiumQosMeanThroughput, 
                                cGtpNormalQosMeanThroughput, 
                                cGtpBestEffortQosMeanThroughput,
                                cGtpGSNAddress
                              }
    STATUS                    deprecated
    DESCRIPTION
        " A collection of GTP Status."
    ::= { cGtpMIBGroups 2 }

cGtpStatisticsGroup           OBJECT-GROUP
    OBJECTS                   { cGtpPathFailureOccurrences, 
                                cGtpCurrentUsedBandwidth,
                                cGtpTotalDroppedPackets
                              }
    STATUS                    deprecated
    DESCRIPTION
        " A collection of GTP statistics ."
    ::= { cGtpMIBGroups 3 }

cGtpConfigurationsGroupRev1   OBJECT-GROUP
    OBJECTS                   { cGtpGSNService,
                                cGtpVersion,
                                cGtpT3TunnelTimer,
                                cGtpT3ResponseTimer,
                                cGtpN3Request,
                                cGtpN3BufferSize,
                                cGtpEchoRequestTimerEnable,
                                cGtpEchoRequestTimer,
                                cGtpMaximumPdps,
                                cGtpNotifEnable,
                                cGtpDynamicEchoTimerEnable,
                                cGtpDynamicEchoTimerMinTime,
                                cGtpDynamicEchoTimerSmoothFactor
                              }
    STATUS                    current
    DESCRIPTION
        " A collection of GTP configurations."
    ::= { cGtpMIBGroups 4 }

cGtpStatusGroupRev1           OBJECT-GROUP
    OBJECTS                   { cGtpLastNoRespToEchoGSNIpAddrTyp,
                                cGtpLastNoRespToEchoGSNIpAddr,
                                cGtpGSNAddress
                              }
    STATUS                    current
    DESCRIPTION
        " A collection of GTP Status."
    ::= { cGtpMIBGroups 5 }

cGtpStatisticsGroupRev1       OBJECT-GROUP
    OBJECTS                   { cGtpPathFailureOccurrences,
                                cGtpTotalDroppedPackets
                              }
    STATUS                    current
    DESCRIPTION
        " A collection of GTP statistics ."
    ::= { cGtpMIBGroups 6 }

cGtpNotifGroup             NOTIFICATION-GROUP
    NOTIFICATIONS          { cGtpPathFailedNotification }
    STATUS                 current
    DESCRIPTION
        "A collection of GTP notifications."
    ::= { cGtpMIBGroups 7 }

END
