-- *****************************************************************
-- ciscoDs3 MIB -  The MIB for DS3/E3 Interface
--
-- January 1999, Shilpa Kale
--
-- February 2000, Subra Hegde
--
-- October  2000, Subra Hegde
--
-- Copyright (c) 1999-2000 by cisco Systems, Inc.
-- All rights reserved.
-- *****************************************************************
 
 
CISCO-DS3-MIB DEFINITIONS ::= BEGIN
IMPORTS
    MODULE-IDENTITY,
    OBJECT-TYPE,
    Counter32
    			FROM SNMPv2-SMI
    DisplayString       FROM SNMPv2-TC
    Unsigned32          FROM CISCO-TC
    MODULE-COMPLIANCE,
    OBJECT-GROUP        FROM SNMPv2-CONF
    ifIndex             FROM IF-MIB
    ciscoMgmt           FROM CISCO-SMI;
 
ciscoDs3MIB MODULE-IDENTITY
    LAST-UPDATED   "200010100000Z"
    ORGANIZATION   "Cisco Systems, Inc."
    CONTACT-INFO
                   "Cisco Systems
                    Customer Service
            Postal: 170 W Tasman Drive
                    San Jose, CA  95134
                    USA
                    Tel: +1 800 553-NETS
            E-mail: cs-wanatm@cisco.com"
    DESCRIPTION
        "The MIB module to describe DS3 line objects. This is
         an extension to the standard DS3 MIB(RFC 2496)."
    REVISION "200010100000Z"
    DESCRIPTION
        "Following enumerations are added to cds3LineType object:
         
         dsx3M23, dsx3SYNTRAN, dsx3CbitParity, dsx3ClearChannel,
         e3Framed, e3Plcp."
    REVISION "200002280000Z"
    DESCRIPTION
        "Initial version of this MIB Module."
    ::= { ciscoMgmt 132 }
 
ciscoDs3MIBObjects  OBJECT IDENTIFIER ::= { ciscoDs3MIB 1 }

-- Ds3 Config
cds3Config          OBJECT IDENTIFIER ::= { ciscoDs3MIBObjects 1 }
cds3Alarm           OBJECT IDENTIFIER ::= { ciscoDs3MIBObjects 2 }
cds3Stats           OBJECT IDENTIFIER ::= { ciscoDs3MIBObjects 3 }

cds3AlarmConfig     OBJECT IDENTIFIER ::= { cds3Alarm 1 }

-- --------------------------------------------------------------
-- Group ds3Config 
-- This group contains DS3 line configuration objects.
-- --------------------------------------------------------------

cds3ConfigTable OBJECT-TYPE
    SYNTAX SEQUENCE OF Cds3ConfigEntry
    MAX-ACCESS not-accessible
    STATUS     current
    DESCRIPTION
        "The DS3 Configuration table. 
         The table has objects for configuring a T3/E3 line." 
    ::= { cds3Config 1 }

cds3ConfigEntry OBJECT-TYPE
    SYNTAX     Cds3ConfigEntry
    MAX-ACCESS not-accessible
    STATUS     current
    DESCRIPTION
       "An entry in the table. There is an entry for each available
        T3/E3 line, with an ifType value of 'ds3'(30).
        By default, lines are disabled. 'ifAdmin' from ifTable must be
        used to up the line. The objects in this table can be modified
        only when the line is up."
    INDEX  { ifIndex }
    ::= { cds3ConfigTable 1 }
 
Cds3ConfigEntry ::=
    SEQUENCE {
        cds3LineType                    INTEGER,
        cds3LineAIScBitsCheck           INTEGER,
        cds3LineRcvFEACValidation       INTEGER,
        cds3LineOOFCriteria             INTEGER,
        cds3TraceToTransmit             DisplayString,
        cds3TraceToExpect               DisplayString,
        cds3TraceAlarm                  INTEGER,
	cds3InternalEqualizer           INTEGER,
        cds3NearEndLineLoopbackStatus   Unsigned32,
        cds3FarEndLineLoopbackStatus    Unsigned32
        }

cds3LineType OBJECT-TYPE
        SYNTAX  INTEGER {
                ds3cbitadm(1),
                ds3cbitplcp(2),
                e3g832adm(3),
	        e3g751adm(4),
	        e3g751plcp(5),
	        ds3m23adm(6),
	        ds3m23plcp(7),
	        other(8),
                dsx3M23(9),
                dsx3SYNTRAN(10),
                dsx3CbitParity(11),
                dsx3ClearChannel(12),
                e3Framed(13),
                e3Plcp(14)
        }
        MAX-ACCESS read-write
        STATUS     current 
        DESCRIPTION
           "This variable indicates the variety of DS3 C-bit
            or E3 application implementing this interface.
            The type of interface affects the interpretation
            of the usage and error statistics. The rate of DS3
            is 44.736 Mbps and E3 is 34.368 Mbps.
 
            The values, in sequence, describe:

	    Following values are applicable to DS3 interfaces only.

              ds3cbitadm       : Indicates C-BIT ADM mode 
              ds3cbitplcp      : Indicates C-BIT PLCP mode
              ds3m23adm        : Indicates M23 ADM mode 
              ds3m23plcp       : Indicates M23 PLCP mode 
              dsx3M23          : Refer ANSI T1.107-1988 [9]
              dsx3SYNTRAN      : Refer ANSI T1.107-1988 [9]
              dsx3CbitParity   : Refer ANSI T1.107-1988 [9]
              dsx3ClearChannel : Refer ANSI T1.107-1988 [9]

	    Following values are applicable to E3 interfaces only.

              e3g832adm  : Indicates G.832 ADM mode 
              e3g751adm  : Indicates G.751 ADM mode 
              e3g751plcp : Indicates G.751 PLCP mode
              e3Framed   : Refer CCITT G.751 [12]
              e3Plcp     : Refer ETSI T/NA(91)19 [14]."
        REFERENCE
           "ANSI T1.107, ANSI T1.102, CCITT G.751, ETSI T/NA(91)18"
        ::= { cds3ConfigEntry 1 }

cds3LineAIScBitsCheck OBJECT-TYPE
    SYNTAX  INTEGER {
            check(1),
            ignore(2)
            }
    MAX-ACCESS read-write
    STATUS     current
    DESCRIPTION
        "When check(1) is set, then Alarm Indication Signal (AIS) 
         is declared when '1010...'b is found and C-Bits are all zero.  
         When ignore(2) is set, an AIS condition is declared when the  
         '1010...'b is detected irrespective of the state of the C-Bits.
         Does not apply to the E3 interface."
    REFERENCE
         "RFC2496"   
    ::= { cds3ConfigEntry 2 }

cds3LineRcvFEACValidation OBJECT-TYPE
    SYNTAX INTEGER{
            fEACCodes4Of5(1),
            fEACCodes8Of10(2),
	    disable(3)
            }
    MAX-ACCESS read-write
    STATUS     current
    DESCRIPTION
        "This entry specifies the FEAC (Far End Alarm and Control) code 
         validation criteria. If 'fEACCodes4Of5' is specified, then a valid
         FEAC code is declared if 4 of 5 codes match. When 'fEACCodes8Of10' 
         is specified, then a valid FEAC code is declared when 8 of 10 codes
         match. If disable(3) is specified, then FEAC code generation 
         and detection is disabled. 
         Does not apply to the E3 interface."
    DEFVAL {fEACCodes4Of5}
    ::= { cds3ConfigEntry 3 }

cds3LineOOFCriteria OBJECT-TYPE
    SYNTAX  INTEGER {
            bits3Of8(1),
            bits3Of16(2)
            }
    MAX-ACCESS read-write
    STATUS     current
    DESCRIPTION
        "This entry specifies the out of frame(OOF) decision criteria.
         If 'bits3Of8' is specified then an OOF condition is declared if
         at least 3 of 8 framing bits are in error. When 'bits3Of16' is
         specified then OOF is declared if 3 of 16 framing bits are found
         to be in error.
         OOF is declared when errors are detected in  the framing
         octets for four consecutive frames.
         This object does not apply to E3 interface."
    DEFVAL {bits3Of8}
    ::= { cds3ConfigEntry 4 }

cds3TraceToTransmit OBJECT-TYPE
      SYNTAX     DisplayString (SIZE (1..16))
      MAX-ACCESS read-write
      STATUS     current
      DESCRIPTION
         "Transmitted G.832 Trail Trace string."
      REFERENCE
         "GR-253-CORE"
      ::= { cds3ConfigEntry 5 }
 
cds3TraceToExpect OBJECT-TYPE
      SYNTAX  DisplayString (SIZE (1..16))
      MAX-ACCESS    read-write
      STATUS    current
      DESCRIPTION
          "G.832 Trail Trace string that is expected to be received from
           the other end."
      REFERENCE
          "GR-253-CORE"
      ::= { cds3ConfigEntry 6 }

cds3TraceAlarm OBJECT-TYPE
     SYNTAX  INTEGER {
             noAlarm(1),
             traceFailure(2)
             }
     MAX-ACCESS  read-only
     STATUS  current
     DESCRIPTION
        "The value of this object is set to traceFailure(2) when
         DS3 line receives a  trace does not match the
         'cds3TraceToExpect'."
     REFERENCE
         "GR-253-CORE"
     ::= { cds3ConfigEntry 7 }

cds3InternalEqualizer OBJECT-TYPE
     SYNTAX  INTEGER {
                 use(1),
                 byPass(2)
             }
     MAX-ACCESS  read-write
     STATUS  current
     DESCRIPTION
        "This variable indicates whether the internal equalizer is being
         used or bypassed. Set this value depending on the line equipment
         to which the receiver is attached.
         Possible values are :
         
          use(1)      : Use the internal equalizer
          byPass(2)   : bypass internal equalizer(use external equalizer).
                        This option allows easy interfacing of the
                        device into systems already utilizing the external
		        equalizers."
     DEFVAL { use }
     ::= { cds3ConfigEntry 8 }

cds3NearEndLineLoopbackStatus OBJECT-TYPE
    SYNTAX      Unsigned32(0..2147483647)
    MAX-ACCESS  read-only
    STATUS      current
    DESCRIPTION
        "Indicates the loopback status of the near end DS1 on this 
         DS3 when loopback request is indicated.

         Following table lists the mapping of Bit position to
         DS1 or DS3 lines and the value.

         Bit Position     Line number      value
         ----------------------------------------

          0               DS3 Line       0 = no loop(loop down)
				         1 = loop(loop up)

	  1               DS1 line 1     0 = loop down
				         1 = loop up

	  2               DS1 line 2     0 = loop down
				         1 = loop up

	  3               DS1 line 3     0 = loop down
				         1 = loop up
	  ...
          ...

	  28              DS1 line 28    0 = loop down
				         1 = loop up

	  29              all DS1 lines  0 = loop up
	                                 1 = loop down
	"
     ::= { cds3ConfigEntry 9 }

cds3FarEndLineLoopbackStatus OBJECT-TYPE
    SYNTAX      Unsigned32(0..2147483647)
    MAX-ACCESS  read-only
    STATUS      current
    DESCRIPTION
        "Indicates the loopback status of the far end DS3,DS1
         when remote DS1 loopback request is initiated.
         The remote DS1 loopback is initiated by setting  dsx3SendCode
         object to dsx3SendDS1LoopCode(5).
	 For unchannelized DS3 applications DS1s are unassigned.

         Following table lists the mapping of Bit position to
         DS1 or DS3 lines and the value.

         Bit Position     Line number      value
         ----------------------------------------

          0               DS3 Line       0 = line loopback activate
					 1 = line loopback deactivate

	  1               DS1 line 1     0 = loop down
					 1 = loop up

	  2               DS1 line 2     0 = loop down
					 1 = loop up

	  3               DS1 line 3     0 = loop down
				         1 = loop up
	  ...
          ...

	  28              DS1 line 29    0 = loop down
					 1 = loop up

	  29              all DS1 lines  0 = loop down
					 1 = loop up
	"
     ::= { cds3ConfigEntry 10 }

-- --------------------------------------------------------------
--
-- Group cds3AlarmConfig 
--
-- --------------------------------------------------------------
cds3AlarmConfigTable OBJECT-TYPE
    SYNTAX  SEQUENCE OF Cds3AlarmConfigEntry
    MAX-ACCESS not-accessible
    STATUS     current
    DESCRIPTION
        "The DS3 interface alarm configuration table. This table contains
         the parameters associated with detecting and declaring alarms for
         the interface. The parameters include severity of alarm, alarm
         integration parameters and 15 minute and 24 hour thresholds."
    ::= { cds3AlarmConfig 1 }

cds3AlarmConfigEntry OBJECT-TYPE
    SYNTAX     Cds3AlarmConfigEntry
    MAX-ACCESS not-accessible
    STATUS     current
    DESCRIPTION     
       "An entry in the T3/E3 Alarm Configuration Table.
        The entries are automatically created for an ifType value of 
        'ds3'(30), with default values for objects. Thresholds may be 
        configured for:
            Line Code Violations(LCV), 
            LineErrored Seconds(LES),
            Line Severely Errored Seconds(LSES), 
            P-bit Coding Violations(PCV), 
            P-bit Errored Seconds(PES), 
            P-bit Severely Errored Seconds(PSES), 
            Severely Errored Seconds(SES), 
            Severely Errored Framing Seconds(SEFS), 
            Unavailable Seconds(UAS),
            C-bit coding violations(CCV),
            C-bit errored seconds(CES),
            C-bit errored seconds(CSES).
        Once these thresholds are exceeded, minor or major alarms
        are raised. Please refer to RFC2496 for descriptions of these
        errors."
    INDEX   { ifIndex }
    ::= { cds3AlarmConfigTable 1 }

Cds3AlarmConfigEntry ::=
    SEQUENCE {
        cds3NEAlarmUpCount                  Unsigned32,
        cds3NEAlarmDownCount                Unsigned32,
        cds3NEAlarmThreshold                Unsigned32,
        cds3FEAlarmUpCount                  Unsigned32,
        cds3FEAlarmDownCount                Unsigned32,
        cds3FEAlarmThreshold                Unsigned32,
        cds3StatisticalAlarmSeverity        INTEGER,
        cds3LCV15MinThreshold               Unsigned32,
        cds3LCV24HrThreshold                Unsigned32,
        cds3LES15MinThreshold               Unsigned32,
        cds3LES24HrThreshold                Unsigned32,
        cds3PCV15MinThreshold               Unsigned32,
        cds3PCV24HrThreshold                Unsigned32,
        cds3PES15MinThreshold               Unsigned32,
        cds3PES24HrThreshold                Unsigned32,
        cds3PSES15MinThreshold              Unsigned32,
        cds3PSES24HrThreshold               Unsigned32,
        cds3SEFS15MinThreshold              Unsigned32,
        cds3SEFS24HrThreshold               Unsigned32,
        cds3UAS15MinThreshold               Unsigned32,
        cds3UAS24HrThreshold                Unsigned32,
        cds3CCV15MinThreshold               Unsigned32,
        cds3CCV24HrThreshold                Unsigned32,
        cds3CES15MinThreshold               Unsigned32,
        cds3CES24HrThreshold                Unsigned32,
        cds3CSES15MinThreshold              Unsigned32,
        cds3CSES24HrThreshold               Unsigned32,
        cds3LSES15MinThreshold              Unsigned32,
        cds3LSES24HrThreshold               Unsigned32, 
        cds3LineStatisticalAlarmState       Unsigned32
        }

cds3NEAlarmUpCount OBJECT-TYPE
    SYNTAX     Unsigned32 (0..2147483647)
    MAX-ACCESS read-write
    STATUS     current
    DESCRIPTION
        "This parameter specifies the increment to the Near End alarm
         integration counters. The local alarms are LOS and LOF. The
         Default value is 6 and the integration counter is incremented by
         this value every 10 ms while the alarm persists. The
         counter is decremented by the value of 'cds3NEAlarmDownCount'
         while there is no alarm (the counter does not decrement below
         zero). When the integration counter exceeds 'cds3NEAlarmThreshold'
         an Alarm of the severity specified for the particular Near End 
         alarm is declared."
    DEFVAL {6}
    ::= { cds3AlarmConfigEntry 1 }
   
cds3NEAlarmDownCount OBJECT-TYPE
    SYNTAX     Unsigned32 (0..2147483647)
    MAX-ACCESS read-write
    STATUS     current
    DESCRIPTION
        "This parameter specifies the decrement to the Near End alarm
         integration counters. The  alarms are LOS and LOF. The
         Default value is 1 and the integration counter is decremented by
         this value every 10 ms while no alarm persists. The
         counter is incremented by the value of cds3NEAlarmUpCount
         while there is no alarm (the counter does not decrement below
         zero). When the integration counter reaches zero any Alarm
         previously declared is removed."
    DEFVAL {1}
    ::= { cds3AlarmConfigEntry 2 }

cds3NEAlarmThreshold OBJECT-TYPE
  SYNTAX     Unsigned32 (0..2147483647)
  MAX-ACCESS read-write
  STATUS     current
  DESCRIPTION
        "The value set in this object determines the value that
         the alarm integration counter must reach for an near end
         alarm to be declared. If the up count is 6, and the threshold 150,
         an Alarm is integrated in 2.5 seconds. If the down count is 1,
         then alarm will be cleared in 15 seconds."
   DEFVAL {150}
   ::= { cds3AlarmConfigEntry 3 }

cds3FEAlarmUpCount OBJECT-TYPE
    SYNTAX     Unsigned32 (0..2147483647)
    MAX-ACCESS read-write
    STATUS     current
    DESCRIPTION
        "This parameter specifies the increment to the Far End alarm
         integration counters. The  alarms are Remote Alarm Indication
         (RAI) and Alarm Indication Signal(AIS). The integration counter is
         incremented by this value every 10 ms while the alarm persists. The
         counter is decremented by this value while there is no alarm
         (the counter does not decrement below zero).
         When the integration counter exceeds cds3FEAlarmThreshold
         an Alarm of the severity specified for the particular far end
         alarm is declared."
     DEFVAL {6}
     ::= { cds3AlarmConfigEntry 4 }

cds3FEAlarmDownCount OBJECT-TYPE
     SYNTAX     Unsigned32 (0..2147483647)
     MAX-ACCESS read-write
     STATUS     current
     DESCRIPTION
         "This parameter specifies the decrement to the Far End alarm
          integration counters. The alarms are Alarm Indication Signal       
          (AIS) and Remote Alarm Indication (RAI). The integration counter
          is decremented by this value every 10 ms (till zero), while no 
          alarm persists. The counter is incremented by this value  while
          there is no alarm. When the integration counter decrements to 
          zero any previously declared Alarm is removed."
     DEFVAL {1}
     ::= { cds3AlarmConfigEntry 5 }

cds3FEAlarmThreshold OBJECT-TYPE
  SYNTAX     Unsigned32 (0..2147483647)
  MAX-ACCESS read-write
  STATUS     current
  DESCRIPTION
        "The value set in this object determines the value that
         the alarm integration counter must reach for an far end
         Alarm to be declared. If the up count is 6, the down count
         is 1 and the threshold 150, an Alarm is integrated in
         2.5 sec and removed in 15 seconds."
   DEFVAL {150}
   ::= { cds3AlarmConfigEntry 6 }
 
cds3StatisticalAlarmSeverity OBJECT-TYPE
    SYNTAX  INTEGER {
             minor(1),
             major(2),
             none(3)
             }
    MAX-ACCESS read-write
    STATUS     current
    DESCRIPTION
        "This variable is used to setup the severity of any of the
         Statistical alarms. So when a Statistical Counter exceeds its
         specified threshold the system will send the alarm with 
         appropriate severity. A value of none(3) indicates that no
         alarm will be raised."
    DEFVAL { none }
    ::= { cds3AlarmConfigEntry 7 }
 
cds3LCV15MinThreshold OBJECT-TYPE
  SYNTAX     Unsigned32 (0..2147483647)
  MAX-ACCESS read-write
  STATUS     current
  DESCRIPTION
     "The value set in this object determines the value
      which when exceeded in a 15 minute window causes
      a statistical alarm to be declared."
  REFERENCE
     "RFC2496"
  ::= { cds3AlarmConfigEntry 8 }

cds3LCV24HrThreshold OBJECT-TYPE
      SYNTAX     Unsigned32 (0..2147483647)
      MAX-ACCESS read-write
      STATUS     current
      DESCRIPTION
         "The value set in this object determines the value
          which when exceeded in a sliding 24 hour window causes
          a statistical alarm to be declared. The threshold is
          checked every 15 minutes for the preceding 24 hour interval."
     REFERENCE
         "RFC2496"
      ::= { cds3AlarmConfigEntry 9 }
 
cds3LES15MinThreshold OBJECT-TYPE
    SYNTAX     Unsigned32 (0..2147483647)
    MAX-ACCESS read-write
    STATUS     current
    DESCRIPTION
       "The value set in this object determines the value
        which when exceeded in a 15 minute window causes
        which when exceeded in a 15 minute window causes
        a statistical alarm to be declared."
    REFERENCE
       "RFC2496"
    ::= { cds3AlarmConfigEntry 10 }
 
 
cds3LES24HrThreshold OBJECT-TYPE
  SYNTAX     Unsigned32 (0..2147483647)
  MAX-ACCESS read-write
  STATUS     current
  DESCRIPTION
     "The value set in this object determines the value
      which when exceeded in a sliding 24 hour window causes
      a statistical alarm to be declared. The threshold is
      checked every 15 minutes for the preceding 24 hour interval."
  REFERENCE
     "RFC2496"
  ::= { cds3AlarmConfigEntry 11 }
 
cds3PCV15MinThreshold OBJECT-TYPE
  SYNTAX     Unsigned32 (0..2147483647)
  MAX-ACCESS read-write
  STATUS     current
  DESCRIPTION
     "The value set in this object determines the value which when 
      exceeded in a 15 minute window causes a statistical alarm to be
      declared.
      Not for E3."
  REFERENCE
     "RFC2496"
  ::= { cds3AlarmConfigEntry 12 }
 
cds3PCV24HrThreshold OBJECT-TYPE
  SYNTAX     Unsigned32 (0..2147483647)
  MAX-ACCESS read-write
  STATUS     current
  DESCRIPTION
      "The value set in this object determines the value
       which when exceeded in a sliding 24 hour window causes
       a statistical alarm to be declared. The threshold is
       checked every 15 minutes for the preceding 24 hour interval.
       Not for E3."
  REFERENCE
        "RFC2496"
  ::= { cds3AlarmConfigEntry 13 }
 
cds3PES15MinThreshold OBJECT-TYPE
  SYNTAX     Unsigned32 (0..2147483647)
  MAX-ACCESS read-write
  STATUS     current
  DESCRIPTION
     "The value set in this object determines the value which when exceeded
      in a 15 minute window causes a statistical alarm to be declared.
      Not for E3."
  REFERENCE
       "RFC2496"
  ::= { cds3AlarmConfigEntry 14 }
 
cds3PES24HrThreshold OBJECT-TYPE
   SYNTAX    Unsigned32 (0..2147483647)
  MAX-ACCESS read-write
  STATUS     current
  DESCRIPTION
    "The value set in this object determines the value
     which when exceeded in a sliding 24 hour window causes
     a statistical alarm to be declared. The threshold is
     checked every 15 minutes for the preceding 24 hour interval.
     Not for E3."
  REFERENCE
     "RFC2496"
    ::= { cds3AlarmConfigEntry 15 }
 
cds3PSES15MinThreshold OBJECT-TYPE
  SYNTAX     Unsigned32 (0..2147483647)
  MAX-ACCESS read-write
  STATUS     current
  DESCRIPTION
      "The value set in this object determines the value
       which when exceeded in a 15 minute window causes
       a statistical alarm to be declared.
       Not for E3."
  REFERENCE
     "RFC2496"
    ::= { cds3AlarmConfigEntry 16 }

cds3PSES24HrThreshold OBJECT-TYPE
    SYNTAX     Unsigned32 (0..2147483647)
    MAX-ACCESS read-write
    STATUS     current
    DESCRIPTION
        "The value set in this object determines the value
         which when exceeded in a sliding 24 hour window causes
         a statistical alarm to be declared. The threshold is
         checked every 15 minutes for the preceding 24 hour interval.
         Not for E3."
    REFERENCE
        "RFC2496"
    ::= { cds3AlarmConfigEntry 17 }
 
cds3SEFS15MinThreshold OBJECT-TYPE
    SYNTAX     Unsigned32 (0..2147483647)
    MAX-ACCESS read-write
    STATUS     current
    DESCRIPTION
       "The value set in this object determines the value which when exceeded
        in a 15 minute window causes a statistical alarm to be declared."
  REFERENCE
     "RFC2496"
    ::= { cds3AlarmConfigEntry 18 }
 
cds3SEFS24HrThreshold OBJECT-TYPE
    SYNTAX     Unsigned32 (0..2147483647)
    MAX-ACCESS read-write
    STATUS     current
    DESCRIPTION
       "The value set in this object determines the value
        which when exceeded in a sliding 24 hour window causes
        a statistical alarm to be declared. The threshold is
        checked every 15 minutes for the preceding 24 hour interval"
  REFERENCE
       "RFC2496"
    ::= { cds3AlarmConfigEntry 19 }
 
cds3UAS15MinThreshold OBJECT-TYPE
    SYNTAX     Unsigned32 (0..2147483647)
    MAX-ACCESS read-write
    STATUS     current
    DESCRIPTION
        "The value set in this object determines the value which when 
         exceeded in a 15 minute window causes  a statistical alarm to
         be declared."
    REFERENCE
       "RFC2496"
    ::= { cds3AlarmConfigEntry 20 }
 
cds3UAS24HrThreshold OBJECT-TYPE
    SYNTAX   Unsigned32 (0..2147483647)
  MAX-ACCESS read-write
  STATUS     current
  DESCRIPTION
        "The value set in this object determines the value
         which when exceeded in a sliding 24 hour window causes
         a statistical alarm to be declared. The threshold is
         checked every 15 minutes for the preceding 24 hour interval"
  REFERENCE
     "RFC2496"
    ::= { cds3AlarmConfigEntry 21 }
 
cds3CCV15MinThreshold OBJECT-TYPE
  SYNTAX     Unsigned32 (0..2147483647)
  MAX-ACCESS read-write
  STATUS     current
  DESCRIPTION
     "The value set in this object determines the value which when exceeded 
      in a 15 minute window causes a statistical alarm to be declared.
      Not for E3."
  REFERENCE
     "RFC2496"
   ::= { cds3AlarmConfigEntry 22 }
 
cds3CCV24HrThreshold OBJECT-TYPE
  SYNTAX     Unsigned32 (0..2147483647)
  MAX-ACCESS read-write
  STATUS     current
  DESCRIPTION
    "The value set in this object determines the value which when exceeded
     in a sliding 24 hour window causes  a statistical alarm to be declared.
     The threshold is checked every 15 minutes for the preceding 24 hour
     interval.
     Not for E3."
  REFERENCE
     "RFC2496"
  ::= { cds3AlarmConfigEntry 23 }
 
cds3CES15MinThreshold OBJECT-TYPE
   SYNTAX     Unsigned32 (0..2147483647)
   MAX-ACCESS read-write
   STATUS     current
   DESCRIPTION
      "The value set in this object determines the value which when exceeded
       in a 15 minute window causes a statistical alarm to be declared.
       Not for E3."
   REFERENCE
        "RFC2496"
   ::= { cds3AlarmConfigEntry 24 }
 
cds3CES24HrThreshold OBJECT-TYPE
   SYNTAX     Unsigned32 (0..2147483647)
   MAX-ACCESS read-write
   STATUS     current
   DESCRIPTION
      "The value set in this object determines the value which when exceeded
       in a sliding 24 hour window causes a statistical alarm to be declared.
       Not for E3."
   REFERENCE
     "RFC2496"
   ::= { cds3AlarmConfigEntry 25 }
 
cds3CSES15MinThreshold OBJECT-TYPE
   SYNTAX     Unsigned32 (0..2147483647)
   MAX-ACCESS read-write
   STATUS     current
   DESCRIPTION
      "The value set in this object determines the value which when exceeded
       in a 15 minute window causes a statistical alarm to be declared.
       Not for E3."
   REFERENCE
      "RFC2496"
   ::= { cds3AlarmConfigEntry 26 }
 
cds3CSES24HrThreshold OBJECT-TYPE
    SYNTAX     Unsigned32 (0..2147483647)
    MAX-ACCESS read-write
    STATUS     current
    DESCRIPTION
       "The value set in this object determines the value which when 
        exceeded in a sliding 24 hour window causes a statistical 
        alarm to be declared. Not for E3."
    REFERENCE
       "RFC2496"
    ::= { cds3AlarmConfigEntry 27 }

cds3LSES15MinThreshold OBJECT-TYPE
   SYNTAX     Unsigned32 (0..2147483647)
   MAX-ACCESS read-write
   STATUS     current
   DESCRIPTION
      "Used to set the 15 minute threshold for LSES(Line Severely Errored
       Seconds).

       The value set in this object determines the value which when 
       exceeded in a 15 minute window causes a statistical alarm to be
       declared."
   REFERENCE
       "Bellcore TR-TSV-000773"
   ::= { cds3AlarmConfigEntry 28 }
 
cds3LSES24HrThreshold OBJECT-TYPE
    SYNTAX     Unsigned32 (0..2147483647)
    MAX-ACCESS read-write
    STATUS     current
    DESCRIPTION
       "The value set in this object determines the value which when
        exceeded in a sliding 24 hour window causes a statistical alarm 
        to be declared."
    REFERENCE
       "Bellcore TR-TSV-000773"
    ::= { cds3AlarmConfigEntry 29 }
 
cds3LineStatisticalAlarmState OBJECT-TYPE
    SYNTAX     Unsigned32 (0..2147483647)
    MAX-ACCESS read-only
    STATUS     current
    DESCRIPTION
       "This is a bitmap of the DS3 Line Statistical alarms. It is
        represented as a sum where value 2^(N-1) is added to the 
        sum if threshold corresponding to bit N is exceeded. Zero 
        indicates no alarms.

        Itemized below are the individual alarm bits:
        BitPosition    Alarm
        -----------    -----
          1            PES current 15 minute threshold exceeded
          2            PES 24 hour threshold exceeded
          3            PSES current 15 minute threshold exceeded
          4            PSES  24 hour threshold exceeded
          5            SEFS current 15 minute threshold exceeded
          6            SEFS 24 hour  threshold exceeded
          7            UAS current 15 minute threshold exceeded
          8            UAS  24 hour threshold exceeded
          9            LCV current 15 minute threshold exceeded
         10            LCV  24 hour threshold exceeded
         11            PCV current 15 minute threshold exceeded
         12            PCV  24 hour threshold exceeded
         13            LES current 15 minute threshold exceeded
         14            LES  24 hour threshold exceeded
         15            CCV current 15 minute threshold exceeded
         16            CCV  24 hour threshold exceeded
         17            CES current 15 minute threshold exceeded
         18            CES  24 hour threshold exceeded
         19            CSES current 15 minute threshold exceeded
         20            CSES 24 hour threshold exceeded
         21            LSES current 15 minute threshold exceeded
         22            LSES 24 hour threshold exceeded"
    DEFVAL {0}
    ::= { cds3AlarmConfigEntry 30 }
 
-- --------------------------------------------------------------
--
-- Group cds3Stats 
--
-- --------------------------------------------------------------
 
cds3StatsTable OBJECT-TYPE
   SYNTAX  SEQUENCE OF Cds3StatsEntry
   MAX-ACCESS  not-accessible
   STATUS  current
   DESCRIPTION
       "T3/E3 Statistics table.  This table maintains the number of times the 
        line encountered Loss of Signal(LOS), out of frame(LOF), Alarm
        Indication signals(AIS), Remote alarm indications(RAI), C-bit coding
        violations(CCV), Framing Errors(FE), from the time it is up. Line
        fails and goes down as a result of failures. When the line is brought 
        back up again by the user the error statistics are cleared." 
     ::= { cds3Stats 1 }

 cds3StatsEntry OBJECT-TYPE
     SYNTAX      Cds3StatsEntry
     MAX-ACCESS  not-accessible
     STATUS      current
     DESCRIPTION 
        "An entry in the T3/E3 Statistics table. Statistics
         are gathered for each existing T3/E3 line. An entry is created
         automatically for each T3/E3 line that is activated."
     INDEX   { ifIndex }
     ::= { cds3StatsTable 1 }

 Cds3StatsEntry ::=
     SEQUENCE {
     cds3RcvLOSCount Counter32,
     cds3RcvOOFCount Counter32,
     cds3RAICount    Counter32,
     cds3CCVCount    Counter32,
     cds3FECount     Counter32,
     cds3EXZSCount   Counter32,
     cds3LCVCount    Counter32,
     cds3PCVCount    Counter32,
     cds3CPECount    Counter32,
     cds3FEBECount   Counter32,
     cds3RcvAISCount Counter32
     }

cds3RcvLOSCount OBJECT-TYPE
     SYNTAX     Counter32
     MAX-ACCESS read-only
     STATUS     current
     DESCRIPTION
        "The number of times Loss of Signal was detected
         with or without integrating to LOS alarm."
     ::= { cds3StatsEntry 1 }

cds3RcvOOFCount OBJECT-TYPE
   SYNTAX     Counter32
   MAX-ACCESS read-only
   STATUS     current
   DESCRIPTION
      "The number of times Out of Frame was detected with or without
       integrating to OOF alarm."
   ::= { cds3StatsEntry 2 }

cds3RAICount OBJECT-TYPE
    SYNTAX     Counter32
    MAX-ACCESS read-only
    STATUS     current
    DESCRIPTION
      "The number of timesRemote Alarm Indication was detected with
       or without integrating to RAI alarm."
    ::= { cds3StatsEntry 3 }

cds3CCVCount OBJECT-TYPE
    SYNTAX     Counter32
    MAX-ACCESS read-only
    STATUS     current
    DESCRIPTION
      "The counter associated with the number of C-Bit Coding 
       Violations encountered by a T3/E3 interface."
    ::= { cds3StatsEntry 4 }

cds3FECount OBJECT-TYPE
    SYNTAX     Counter32
    MAX-ACCESS read-only
    STATUS     current
    DESCRIPTION
     "The number of Framing Errors encountered by a T3/E3 interface."  
    ::= { cds3StatsEntry 5 }

cds3EXZSCount OBJECT-TYPE
    SYNTAX     Counter32
    MAX-ACCESS read-only
    STATUS     current
    DESCRIPTION
        "The number of Excessive Zeros(EXZ) by a T3/E3 interface.
	 An EXZ is the occurrence of any string of zeros having length
         equal to or greater than 3 for B3ZS, or any string of zeros
         having length greater than 4 for HDB3."
    REFERENCE 
        "RFC2496 Section 2.4.1."
    ::= { cds3StatsEntry 6 }

cds3LCVCount OBJECT-TYPE
    SYNTAX     Counter32
    MAX-ACCESS read-only
    STATUS     current
    DESCRIPTION
        "The count of both BPVs(Bipolar Violations) and EXZs(Excessive
	 Zeros) encountered by a T3/E3 interface.An EXZ increments
	 the LCV by one regardless of the length of the zero string."
    REFERENCE
        "RFC2496 Section 2.4.1."
    ::= { cds3StatsEntry 7 }

cds3PCVCount OBJECT-TYPE
    SYNTAX     Counter32
    MAX-ACCESS read-only
    STATUS     current
    DESCRIPTION
        "This is the count of P-bit Coding Violation(PCV) error event
         encountered by DS3 interface. For all DS3 applications, a 
         coding violation error event is a P-bit Parity Error(PERR) event. 
         The parity errors occur when the calculated parity in the 
         information bits of the DS3 frame does not match up with an 
         expected parity value."
    REFERENCE 
        "RFC2496 Section 2.4.1."
    ::= { cds3StatsEntry 8 }

cds3CPECount OBJECT-TYPE
    SYNTAX     Counter32
    MAX-ACCESS read-only
    STATUS     current
    DESCRIPTION
        "The number of C-bit parity errors(CPERR) on a DS3 interface.
         This value is calculated over noninformation bits in the
	 DS3 frame."
    ::= { cds3StatsEntry 9 }

cds3FEBECount OBJECT-TYPE
    SYNTAX     Counter32
    MAX-ACCESS read-only
    STATUS     current
    DESCRIPTION
        "The number of Far End Block Errors(FEBE) encountered by
         a T3/E3 interface.These include frame alignment errors,
         multiframe alignment errors, and C-bit parity errors.
         These errors are generated by the transmitter at the 
         far end, and indicate that the transmitter,cabling or the
         upstream node is faulty."
    ::= { cds3StatsEntry 10 }

cds3RcvAISCount OBJECT-TYPE
   SYNTAX     Counter32
   MAX-ACCESS read-only
   STATUS     current
   DESCRIPTION
      "The number of times Alarm Indication Signals(AIS) were detected.
       The AIS indicates that an upstream failure has been detected by
       the far end."
   REFERENCE
       "RFC2496 Section 2.4.3."
   ::= { cds3StatsEntry 11 }

-- --------------------------------------------------------------
--
-- Group cds3PlcpAlarmConfig
--
-- --------------------------------------------------------------

cds3AlarmConfigPlcpTable OBJECT-TYPE
    SYNTAX  SEQUENCE OF Cds3AlarmConfigPlcpEntry
    MAX-ACCESS  not-accessible
    STATUS      current
    DESCRIPTION
        "The ATM interface PLCP alarm configuration table. PLCP is a sublayer
         over the DS3 interface, that carries ATM cells."
    ::= { cds3AlarmConfig 2 }

cds3AlarmConfigPlcpEntry OBJECT-TYPE
    SYNTAX  Cds3AlarmConfigPlcpEntry
    MAX-ACCESS  not-accessible
    STATUS      current
    DESCRIPTION
        "An entry in the DS3 PLCP Alarm Configuration table. The entries
         contain parameters to configure DS3 PLCP error statistics 
         thresholds, so that an alarm is raised whenever any threshold
         is exceeded. The entries are automatically created for active
         DS3 interfaces with Plcp framing enabled, with default values 
         for objects."
    INDEX   { ifIndex }
    ::= { cds3AlarmConfigPlcpTable 1 }

Cds3AlarmConfigPlcpEntry ::=
    SEQUENCE {
        cds3PlcpStatisticalAlarmSeverity INTEGER,
        cds3PlcpBip8CV15MinThreshold     Unsigned32,
        cds3PlcpBip8CV24HrThreshold      Unsigned32,
        cds3PlcpBip8ES15MinThreshold     Unsigned32,
        cds3PlcpBip8ES24HrThreshold      Unsigned32,
        cds3PlcpBip8SES15MinThreshold    Unsigned32,
        cds3PlcpBip8SES24HrThreshold     Unsigned32,
        cds3PlcpSEFS15MinThreshold       Unsigned32,
        cds3PlcpSEFS24HrThreshold        Unsigned32,
        cds3PlcpUAS15MinThreshold        Unsigned32,
        cds3PlcpUAS24HrThreshold         Unsigned32
        }
 
cds3PlcpStatisticalAlarmSeverity OBJECT-TYPE
    SYNTAX INTEGER {
           minor(1),
           major(2),
           none(3)
           }
    MAX-ACCESS read-write
    STATUS     current
    DESCRIPTION
        "This variable sets up the severity of PLCP Statistical
         alarm. So when PLCP Statistical alarm is detected the
         module will send the alarm with appropriate severity.
         A value of none(3) indicates that no alarm will be raised."
    DEFVAL { none }
    ::= { cds3AlarmConfigPlcpEntry 1 }

cds3PlcpBip8CV15MinThreshold OBJECT-TYPE
    SYNTAX     Unsigned32 (0..2147483647)
    MAX-ACCESS read-write
    STATUS     current
    DESCRIPTION
       "The value set in this object determines the value which when exceeded 
        in a 15 minute window causes a statistical alarm to be declared."
    ::= { cds3AlarmConfigPlcpEntry 2 }

cds3PlcpBip8CV24HrThreshold OBJECT-TYPE
  SYNTAX     Unsigned32 (0..2147483647)
  MAX-ACCESS read-write
  STATUS     current
  DESCRIPTION
      "The value set in this object determines the value
       which when exceeded in a sliding 24 hour window causes
       a statistical alarm to be declared. The threshold is
       checked every 15 minutes for the preceding 24 hour interval."
  ::= { cds3AlarmConfigPlcpEntry 3 }

cds3PlcpBip8ES15MinThreshold OBJECT-TYPE
  SYNTAX     Unsigned32 (0..2147483647)
  MAX-ACCESS read-write
  STATUS     current
  DESCRIPTION
      "The value set in this object determines the value which when exceeded
       in a 15 minute window causes a statistical alarm to be declared."
  ::= { cds3AlarmConfigPlcpEntry 4 }

cds3PlcpBip8ES24HrThreshold OBJECT-TYPE
  SYNTAX     Unsigned32 (0..2147483647)
  MAX-ACCESS read-write
  STATUS     current
  DESCRIPTION
      "The value set in this object determines the value
       which when exceeded in a sliding 24 hour window causes
       a statistical alarm to be declared. The threshold is
       checked every 15 minutes for the preceding 24 hour interval."
  ::= { cds3AlarmConfigPlcpEntry 5 }                                

cds3PlcpBip8SES15MinThreshold OBJECT-TYPE
  SYNTAX     Unsigned32 (0..2147483647)
  MAX-ACCESS read-write
  STATUS     current
  DESCRIPTION
      "The value set in this object determines the value which when exceeded
       in a 15 minute window causes a statistical alarm to be declared."
  ::= { cds3AlarmConfigPlcpEntry 6 }

cds3PlcpBip8SES24HrThreshold OBJECT-TYPE
  SYNTAX     Unsigned32 (0..2147483647)
  MAX-ACCESS read-write
  STATUS     current
  DESCRIPTION
      "The value set in this object determines the value which when exceeded
      in a sliding 24 hour window causes a statistical alarm to be declared. 
      The threshold is checked every 15 minutes for the preceding 24 hour
      interval."
  ::= { cds3AlarmConfigPlcpEntry 7 }

cds3PlcpSEFS15MinThreshold OBJECT-TYPE
  SYNTAX     Unsigned32 (0..2147483647)
  MAX-ACCESS read-write
  STATUS     current
  DESCRIPTION
      "The value set in this object determines the value which when exceeded 
       in a 15 minute window causes a statistical alarm to be declared."
  ::= { cds3AlarmConfigPlcpEntry 8 }

cds3PlcpSEFS24HrThreshold OBJECT-TYPE
  SYNTAX     Unsigned32 (0..2147483647)
  MAX-ACCESS read-write
  STATUS     current
  DESCRIPTION
      "The value set in this object determines the value
       which when exceeded in a sliding 24 hour window causes
       a statistical alarm to be declared. The threshold is
       checked every 15 minutes for the preceding 24 hour interval."
  ::= { cds3AlarmConfigPlcpEntry 9 }

cds3PlcpUAS15MinThreshold OBJECT-TYPE
  SYNTAX     Unsigned32 (0..2147483647)
  MAX-ACCESS read-write
  STATUS     current
  DESCRIPTION
        "The value set in this object determines the value which when
         exceeded in a 15 minute window causes a statistical alarm to be
         declared."
  ::= { cds3AlarmConfigPlcpEntry 10 }

cds3PlcpUAS24HrThreshold OBJECT-TYPE
  SYNTAX     Unsigned32 (0..2147483647)
  MAX-ACCESS read-write
  STATUS     current
  DESCRIPTION
      "The value set in this object determines the value
       which when exceeded in a sliding 24 hour window causes
       a statistical alarm to be declared. The threshold is
       checked every 15 minutes for the preceding 24 hour interval."
  ::= { cds3AlarmConfigPlcpEntry 11 }

-- --------------------------------------------------------------
--
-- Group cds3PlcpAlarm group
--
-- --------------------------------------------------------------
cds3AlarmPlcpTable OBJECT-TYPE
    SYNTAX  SEQUENCE OF Cds3AlarmPlcpEntry
    MAX-ACCESS  not-accessible
    STATUS  current
    DESCRIPTION
        "The Plcp interface alarm table. This table maintains the
         CV,ES,SES, SEFS and UAS for DS3 line with Plcp framing selected.
         Please refer to RFC2496 for description of these various error
         statistics." 
    ::= { cds3Alarm 2 }

cds3AlarmPlcpEntry OBJECT-TYPE
    SYNTAX  Cds3AlarmPlcpEntry
    MAX-ACCESS  not-accessible
    STATUS  current
    DESCRIPTION
        "An entry in the DS3 Plcp Alarm table. Bucket statistics(15 minute
         and 24 hour interval statistics) are gathered for each existing DS3
         line with PLCP frame format selected. An entry is created
         automatically and is indexed by  the DS3 line number.  "
    INDEX   { ifIndex }
    ::= { cds3AlarmPlcpTable 1 }

Cds3AlarmPlcpEntry ::=
    SEQUENCE {
        cds3PlcpLineAlarmState              Unsigned32,
        cds3PlcpLineStatisticalAlarmState   Unsigned32,
        cds3PlcpBip8CVCurrent               Counter32,
        cds3PlcpBip8CV24HrBucket            Counter32,
        cds3PlcpBip8ESCurrent               Counter32,
        cds3PlcpBip8ES24HrBucket            Counter32,
        cds3PlcpBip8SESCurrent              Counter32,
        cds3PlcpBip8SES24HrBucket           Counter32,
        cds3PlcpSEFSCurrent                 Counter32,
        cds3PlcpSEFS24HrBucket              Counter32,
        cds3PlcpUASCurrent                  Counter32,
        cds3PlcpUAS24HrBucket               Counter32
        }

cds3PlcpLineAlarmState OBJECT-TYPE
    SYNTAX Unsigned32
    MAX-ACCESS read-only
    STATUS     current
    DESCRIPTION
         "This variable is a bitmap of the DS3 Line ALarms.
          It is represented as sum where value 2^(N-1) is added to the 
          sum if alarm corresponding to bit N is exceeded.
          A value of zero for this object indicates no alarms.

          Itemized below are the individual bits:
            BitPosition    Alarm
            -----------    -----
            1              Receiving RAI
            2              Transmitting RAI
            3              Receiving OOF
            4              Near End Local Loopback in effect
            5              Near End Remote Loopback in effect "
     ::= { cds3AlarmPlcpEntry 1 }
 
cds3PlcpLineStatisticalAlarmState OBJECT-TYPE
    SYNTAX Unsigned32
    MAX-ACCESS read-only
    STATUS     current
    DESCRIPTION
         "This variable is a bitmap of the DS3 Plcp Line Statictical
          Alarms. It is represented as a sum, where value 2^(N-1) is added
          to the sum if threshold corresponding to bit N is exceeded.
          A value of zero for this object indicates no alarms.

          Itemized below are the individual alarm bits:
          BitPosition    Alarm
          -----------    -----
          1              Bip8CV 15 minute threshold exceeded
          2              Bip8CV 24 hour threshold exceeded
          3              Bip8ES 15 minute threshold exceeded
          4              Bip8ES 24 hour threshold exceeded
          5              Bip8SES 15 minute threshold exceeded
          6              Bip8SES 24 hour threshold exceeded
          7              Plcp SEFS 15 minute threshold exceeded
          8              Plcp SEFS 24 hour threshold exceeded
          9              Plcp UAS 15 minute threshold exceeded
          10             Plcp UAS 24 hour threshold exceeded"
    ::= { cds3AlarmPlcpEntry 2 }

cds3PlcpBip8CVCurrent OBJECT-TYPE
    SYNTAX     Counter32
    MAX-ACCESS read-only
    STATUS     current
    DESCRIPTION
        "The number of BIP-8 code violations (CV) encountered by
         the line in the current 15 minute period."
    ::= { cds3AlarmPlcpEntry 3 }
 
cds3PlcpBip8CV24HrBucket OBJECT-TYPE
     SYNTAX     Counter32
     MAX-ACCESS read-only
     STATUS     current
     DESCRIPTION
        "The number of BIP-8 CVs encountered by the line in the last 24 
         hours."
     ::= { cds3AlarmPlcpEntry 4 }

cds3PlcpBip8ESCurrent OBJECT-TYPE
  SYNTAX     Counter32
  MAX-ACCESS read-only
  STATUS     current
  DESCRIPTION
      "The number of BIP-8 Errored Seconds(ES) encountered by the line
       in the current 15 minute period."
  ::= { cds3AlarmPlcpEntry 5 }

cds3PlcpBip8ES24HrBucket OBJECT-TYPE
  SYNTAX     Counter32
  MAX-ACCESS read-only
  STATUS     current
  DESCRIPTION
     "The number of BIP-8 ES encountered by the line in the last 24 hour."
  ::= { cds3AlarmPlcpEntry 6 }

cds3PlcpBip8SESCurrent OBJECT-TYPE
  SYNTAX     Counter32
  MAX-ACCESS read-only
  STATUS     current
  DESCRIPTION
      "The number of BIP-8 Severely Errored Seconds(ES) encountered by the
       line in the current 15 minute period."
  ::= { cds3AlarmPlcpEntry 7 }

cds3PlcpBip8SES24HrBucket OBJECT-TYPE
  SYNTAX     Counter32
  MAX-ACCESS read-only
  STATUS     current
  DESCRIPTION
     "The number of BIP-8 SES encountered by the line in the last 24 hour."
  ::= { cds3AlarmPlcpEntry 8 }

cds3PlcpSEFSCurrent OBJECT-TYPE
  SYNTAX     Counter32
  MAX-ACCESS read-only
  STATUS     current
  DESCRIPTION
     "The number of BIP-8 Severely Errored Framing Seconds(SEFS)
      encountered by the line in the current 15-minute period."
  ::= { cds3AlarmPlcpEntry 9 }

cds3PlcpSEFS24HrBucket OBJECT-TYPE
  SYNTAX     Counter32
  MAX-ACCESS read-only
  STATUS     current
  DESCRIPTION
     "The number of BIP-8 SEFS encountered by the line in the last 24 hour."
  ::= { cds3AlarmPlcpEntry 10 }

cds3PlcpUASCurrent OBJECT-TYPE
  SYNTAX     Counter32
  MAX-ACCESS read-only
  STATUS     current
  DESCRIPTION
      "The number of Unavailable Seconds(UAS) encountered by the line 
       in the current 15-minute period."
  ::= { cds3AlarmPlcpEntry 11 }

cds3PlcpUAS24HrBucket OBJECT-TYPE
  SYNTAX     Counter32
  MAX-ACCESS read-only
  STATUS     current
  DESCRIPTION
     "The number of BIP-8 UAS encountered by the line in the last 24 hour."
  ::= { cds3AlarmPlcpEntry 12}

-- --------------------------------------------------------------
--
-- Group ds3PlcpStats
--
-- --------------------------------------------------------------
cds3PlcpStatsTable OBJECT-TYPE
    SYNTAX  SEQUENCE OF Cds3PlcpStatsEntry
    MAX-ACCESS  not-accessible
    STATUS  current
    DESCRIPTION
        "T3 Plcp Statistics table. This table maintains the errors 
         encountered by the T3 line with  Plcp frame format selected, 
         from the time the line is up.Line fails and goes down as a 
         result of failures. When the line is brought  back up again 
         by the user after eliminating the error conditions, the 
         statistics are cleared."
    ::= { cds3Stats 2 }

cds3PlcpStatsEntry OBJECT-TYPE
    SYNTAX     Cds3PlcpStatsEntry
    MAX-ACCESS not-accessible
    STATUS     current 
    DESCRIPTION
        "An entry in the T3 Plcp Stats table. Statistics are gathered for 
         each existing T3 line with PLCP frame format selected. An entry is
         created automatically and is indexed by the T3 line number."
    INDEX   { ifIndex }
    ::= { cds3PlcpStatsTable 1 }

Cds3PlcpStatsEntry ::=
    SEQUENCE {
        cds3PlcpRcvBip8Count    Counter32,
        cds3PlcpRcvOOFCount     Counter32,
        cds3PlcpRcvRAICount     Counter32,
        cds3PlcpFECount         Counter32,
        cds3PlcpFESecCount      Counter32,
        cds3PlcpSEFSecCount     Counter32,
        cds3PlcpFEBECount       Counter32,
        cds3PlcpFEBESecCount    Counter32,
        cds3PlcpSEFEBESecCount  Counter32
        }

cds3PlcpRcvBip8Count OBJECT-TYPE
    SYNTAX     Counter32
    MAX-ACCESS read-only
    STATUS     current
    DESCRIPTION
        "The number of of BIP-8 errors encountered by the line."
    ::= { cds3PlcpStatsEntry 1 }
 
cds3PlcpRcvOOFCount OBJECT-TYPE
  SYNTAX     Counter32
  MAX-ACCESS read-only
  STATUS     current
  DESCRIPTION
      "The number of times Out of Frame(OOF) was detected
       with or without integrating to OOF alarm."
  ::= { cds3PlcpStatsEntry 2 }

cds3PlcpRcvRAICount OBJECT-TYPE
  SYNTAX     Counter32
  MAX-ACCESS read-only
  STATUS     current
  DESCRIPTION
      "The number of times Remote Alarm Indication(RAI) was detected
       with or without integrating to RAI alarm."
  ::= { cds3PlcpStatsEntry 3 }

cds3PlcpFECount OBJECT-TYPE
  SYNTAX     Counter32
  MAX-ACCESS read-only
  STATUS     current
  DESCRIPTION
      "The number of Framing Errors detected."
  ::= { cds3PlcpStatsEntry 4 }

cds3PlcpFESecCount OBJECT-TYPE
    SYNTAX   Counter32
  MAX-ACCESS read-only
  STATUS     current
  DESCRIPTION
     "The number of Framing Error errored seconds."
  ::= { cds3PlcpStatsEntry 5 }

cds3PlcpSEFSecCount OBJECT-TYPE
  SYNTAX     Counter32
  MAX-ACCESS read-only
  STATUS     current
  DESCRIPTION
      "The number of Severely errored Framing error seconds."
  ::= { cds3PlcpStatsEntry 6 }

cds3PlcpFEBECount OBJECT-TYPE
  SYNTAX      Counter32
  MAX-ACCESS  read-only
  STATUS      current
  DESCRIPTION
     "The count of Far End Block Errors (FEBE) detected."
  ::= { cds3PlcpStatsEntry 7 }

cds3PlcpFEBESecCount OBJECT-TYPE
    SYNTAX    Counter32
  MAX-ACCESS  read-only
  STATUS      current
  DESCRIPTION
      "The number of FEBE errored seconds."
  ::= { cds3PlcpStatsEntry 8 }

cds3PlcpSEFEBESecCount OBJECT-TYPE
  SYNTAX     Counter32
  MAX-ACCESS read-only
  STATUS     current
  DESCRIPTION
     "The number of Severely errored FEBE seconds."
  ::= { cds3PlcpStatsEntry 9 }

-- --------------------------------------------------------------
--
-- DS3 Interval table
--
-- --------------------------------------------------------------
cds3IntervalTable OBJECT-TYPE
    SYNTAX  SEQUENCE OF Cds3IntervalEntry
    MAX-ACCESS not-accessible
    STATUS     current
    DESCRIPTION
        "The DS3 interface interval table."
    ::= { cds3Stats 4 }

cds3IntervalEntry OBJECT-TYPE
    SYNTAX     Cds3IntervalEntry
    MAX-ACCESS not-accessible
    STATUS     current
    DESCRIPTION     
       "An entry in the T3/E3 current interval table."
    INDEX   { ifIndex, cds3IntervalNumber }
    ::= { cds3IntervalTable 1 }

Cds3IntervalEntry ::=
    SEQUENCE {
        cds3IntervalNumber               INTEGER,
        cds3IntervalLSESs                Counter32
        }

cds3IntervalNumber OBJECT-TYPE
    SYNTAX  INTEGER (0..96)
    MAX-ACCESS  read-only
    STATUS  current
    DESCRIPTION
       "A number between 0 and 96, where 1 is the most
        recently completed 15 minute interval and 96 is
        the 15 minute interval completed 23 hours and 45
        minutes prior to interval number 1. Interval number
        0 refers to the current 15 minute data."
    ::= { cds3IntervalEntry 1 }

cds3IntervalLSESs OBJECT-TYPE
    SYNTAX     Counter32
    MAX-ACCESS read-only
    STATUS     current
    DESCRIPTION
        "The number of LSESs encountered by the line
         in 15 minute interval."
    ::= { cds3IntervalEntry 2 }

-- --------------------------------------------------------------
--
-- Current 24 hour interval
--
-- --------------------------------------------------------------
cds3Current24HrTable OBJECT-TYPE
    SYNTAX  SEQUENCE OF Cds3Current24HrEntry
    MAX-ACCESS not-accessible
    STATUS     current
    DESCRIPTION
        "The DS3 interface current 24 hour table. This table contains
         counters for current 24 hour interval. Threshold on this counters
         are configured through cds3AlarmConfigTable table. 24 hour 
         interval is aligned to wall clock."
    ::= { cds3Stats 5 }

cds3Current24HrEntry OBJECT-TYPE
    SYNTAX     Cds3Current24HrEntry
    MAX-ACCESS not-accessible
    STATUS     current
    DESCRIPTION     
       "An entry in the T3/E3 current 24 hour counter table.
        The entries are automatically created for an ifType value of 
        'ds3'(30), when interface is made active."
    INDEX   { ifIndex }
    ::= { cds3Current24HrTable 1 }

Cds3Current24HrEntry ::=
    SEQUENCE {
        cds3LCVCurrent24Hr                Counter32,
        cds3LESCurrent24Hr                Counter32,
        cds3PCVCurrent24Hr                Counter32,
        cds3PESCurrent24Hr                Counter32,
        cds3PSESCurrent24Hr               Counter32,
        cds3SEFSCurrent24Hr               Counter32,
        cds3UASCurrent24Hr                Counter32,
        cds3CCVCurrent24Hr                Counter32,
        cds3CESCurrent24Hr                Counter32,
        cds3CSESCurrent24Hr               Counter32,
        cds3LSESCurrent24Hr               Counter32
        }

cds3LCVCurrent24Hr OBJECT-TYPE
    SYNTAX     Counter32
    MAX-ACCESS read-only
    STATUS     current
    DESCRIPTION
        "The number of LCVs encountered by the line since
         the start of current 24 hour period."
    ::= { cds3Current24HrEntry 1 }
 
cds3LESCurrent24Hr OBJECT-TYPE
  SYNTAX     Counter32
  MAX-ACCESS read-only
  STATUS     current
  DESCRIPTION
      "The number LESs encountered by the line since
       the start of current 24 hour period."
  ::= { cds3Current24HrEntry 2 }

cds3PCVCurrent24Hr OBJECT-TYPE
  SYNTAX     Counter32
  MAX-ACCESS read-only
  STATUS     current
  DESCRIPTION
      "The number PCVs encountered by the line since
       the start of current 24 hour period."
  ::= { cds3Current24HrEntry 3 }

cds3PESCurrent24Hr OBJECT-TYPE
  SYNTAX     Counter32
  MAX-ACCESS read-only
  STATUS     current
  DESCRIPTION
      "The number of PESs encountered by the line since
       the start of current 24 hour period."
  ::= { cds3Current24HrEntry 4 }

cds3PSESCurrent24Hr OBJECT-TYPE
  SYNTAX   Counter32
  MAX-ACCESS read-only
  STATUS     current
  DESCRIPTION
     "The number of PSESs encountered by the line since
      the start of current 24 hour period."
  ::= { cds3Current24HrEntry 5 }

cds3SEFSCurrent24Hr OBJECT-TYPE
  SYNTAX     Counter32
  MAX-ACCESS read-only
  STATUS     current
  DESCRIPTION
      "The number of SEFSs encountered by the line since
       the start of the current 24 hour period."
  ::= { cds3Current24HrEntry 6 }

cds3UASCurrent24Hr OBJECT-TYPE
  SYNTAX      Counter32
  MAX-ACCESS  read-only
  STATUS      current
  DESCRIPTION
     "The number of UASs encountered by the line since
      the start of current 24 hour period."
  ::= { cds3Current24HrEntry 7 }

cds3CCVCurrent24Hr OBJECT-TYPE
  SYNTAX    Counter32
  MAX-ACCESS  read-only
  STATUS      current
  DESCRIPTION
      "The number CCVs encounterd by the line since the start
       of current 24 hour period."
  ::= { cds3Current24HrEntry 8 }

cds3CESCurrent24Hr OBJECT-TYPE
  SYNTAX     Counter32
  MAX-ACCESS read-only
  STATUS     current
  DESCRIPTION
     "The number of CESs encountered by the line since the
      start of current 24 hour period."
  ::= { cds3Current24HrEntry 9 }

cds3CSESCurrent24Hr OBJECT-TYPE
  SYNTAX     Counter32
  MAX-ACCESS read-only
  STATUS     current
  DESCRIPTION
     "The number of CSESs encountered by the line since th
      start of current 24 hour period."
  ::= { cds3Current24HrEntry 10 }

cds3LSESCurrent24Hr OBJECT-TYPE
  SYNTAX     Counter32
  MAX-ACCESS read-only
  STATUS     current
  DESCRIPTION
     "The number of LSESs (Line severedly errored seconds) 
      encountered by the line since the start of current
      24 hour period."
  ::= { cds3Current24HrEntry 11 }

-- --------------------------------------------------------------
--
-- Previous 24 hour interval data
--
-- --------------------------------------------------------------

cds3Previous24HrTable OBJECT-TYPE
    SYNTAX  SEQUENCE OF Cds3Previous24HrEntry
    MAX-ACCESS not-accessible
    STATUS     current
    DESCRIPTION
        "The DS3 interface previous 24 hour table. This table contains
         counters for previous 24 hour interval. Implementation of
         this table is optional."
    ::= { cds3Stats 6 }

cds3Previous24HrEntry OBJECT-TYPE
    SYNTAX     Cds3Previous24HrEntry
    MAX-ACCESS not-accessible
    STATUS     current
    DESCRIPTION     
       "An entry in the T3/E3 current 24 hour counter table.
        The entries are automatically created for an ifType value of 
        ds3(30), when interface is made active."
    INDEX   { ifIndex }
    ::= { cds3Previous24HrTable 1 }

Cds3Previous24HrEntry ::=
    SEQUENCE {
        cds3LCVPrevious24Hr                Counter32,
        cds3LESPrevious24Hr                Counter32,
        cds3PCVPrevious24Hr                Counter32,
        cds3PESPrevious24Hr                Counter32,
        cds3PSESPrevious24Hr               Counter32,
        cds3SEFSPrevious24Hr               Counter32,
        cds3UASPrevious24Hr                Counter32,
        cds3CCVPrevious24Hr                Counter32,
        cds3CESPrevious24Hr                Counter32,
        cds3CSESPrevious24Hr               Counter32,
        cds3LSESPrevious24Hr               Counter32
        }

cds3LCVPrevious24Hr OBJECT-TYPE
    SYNTAX     Counter32
    MAX-ACCESS read-only
    STATUS     current
    DESCRIPTION
        "The number of LCVs encountered by the line in
         the previous 24 hour period."
    ::= { cds3Previous24HrEntry 1 }
 
cds3LESPrevious24Hr OBJECT-TYPE
  SYNTAX     Counter32
  MAX-ACCESS read-only
  STATUS     current
  DESCRIPTION
      "The number LESs encountered by the line in
       the previous 24 hour period."
  ::= { cds3Previous24HrEntry 2 }

cds3PCVPrevious24Hr OBJECT-TYPE
  SYNTAX     Counter32
  MAX-ACCESS read-only
  STATUS     current
  DESCRIPTION
      "The number PCVs encountered by the line in
       the previous 24 hour period."
  ::= { cds3Previous24HrEntry 3 }

cds3PESPrevious24Hr OBJECT-TYPE
  SYNTAX     Counter32
  MAX-ACCESS read-only
  STATUS     current
  DESCRIPTION
      "The number of PESs encountered by the line in
       the previous 24 hour period."
  ::= { cds3Previous24HrEntry 4 }

cds3PSESPrevious24Hr OBJECT-TYPE
  SYNTAX   Counter32
  MAX-ACCESS read-only
  STATUS     current
  DESCRIPTION
     "The number of PSESs encountered by the line in
      the previous 24 hour period."
  ::= { cds3Previous24HrEntry 5 }

cds3SEFSPrevious24Hr OBJECT-TYPE
  SYNTAX     Counter32
  MAX-ACCESS read-only
  STATUS     current
  DESCRIPTION
      "The number of SEFSs encountered by the line in
       the start of the current 24 hour period."
  ::= { cds3Previous24HrEntry 6 }

cds3UASPrevious24Hr OBJECT-TYPE
  SYNTAX      Counter32
  MAX-ACCESS  read-only
  STATUS      current
  DESCRIPTION
     "The number of UASs encountered by the line in
      the previous 24 hour period."
  ::= { cds3Previous24HrEntry 7 }

cds3CCVPrevious24Hr OBJECT-TYPE
  SYNTAX    Counter32
  MAX-ACCESS  read-only
  STATUS      current
  DESCRIPTION
      "The number CCVs encounterd by the line in the
       previous 24 hour period."
  ::= { cds3Previous24HrEntry 8 }

cds3CESPrevious24Hr OBJECT-TYPE
  SYNTAX     Counter32
  MAX-ACCESS read-only
  STATUS     current
  DESCRIPTION
     "The number of CESs encountered by the line in
      the previous 24 hour period."
  ::= { cds3Previous24HrEntry 9 }

cds3CSESPrevious24Hr OBJECT-TYPE
  SYNTAX     Counter32
  MAX-ACCESS read-only
  STATUS     current
  DESCRIPTION
     "The number of CSESs encountered by the line in
      the previous 24 hour period."
  ::= { cds3Previous24HrEntry 10 }


cds3LSESPrevious24Hr OBJECT-TYPE
  SYNTAX     Counter32
  MAX-ACCESS read-only
  STATUS     current
  DESCRIPTION
     "The number of LSESs encountered by the line in
      the previous 24 hour period."
  ::= { cds3Previous24HrEntry 11 }

-- conformance information
 
ciscoDs3MIBConformance OBJECT IDENTIFIER ::= { ciscoDs3MIB 8 }
ciscoDs3MIBCompliances OBJECT IDENTIFIER ::= { ciscoDs3MIBConformance 1 }
ciscoDs3MIBGroups      OBJECT IDENTIFIER ::= { ciscoDs3MIBConformance 2 }
 
ciscoDs3MIBCompliance MODULE-COMPLIANCE
     STATUS current
     DESCRIPTION
        "The Compliance statement for ciscoDs3 management group."
     MODULE -- this module
     MANDATORY-GROUPS { ciscoDs3ConfMIBGroup }
 
     GROUP cds3StatsMIBGroup
     DESCRIPTION
         "Implementation of this group is optional."

     GROUP ciscoDs3AlarmMIBGroup
     DESCRIPTION
         "Implementation of this group is optional."

     GROUP ciscoPlcpCounterMIBGroup
     DESCRIPTION
         "Implementation of this group is optional."

     GROUP ciscoDs3Previous24HrGroup
     DESCRIPTION
         "Implementation of this group is optional. ciscoDs3AlarmMIBGroup
          needs to be implemented for this group to be implemented."
   
     OBJECT     cds3NearEndLineLoopbackStatus
     MIN-ACCESS not-accessible
     DESCRIPTION
         "Read access is not required for agents which can not provide
	  the status of the near end loopback."

     OBJECT     cds3FarEndLineLoopbackStatus
     MIN-ACCESS not-accessible
     DESCRIPTION
         "Read access is not required for agents which can not provide
	  the status of the far end loopback."
     ::= { ciscoDs3MIBCompliances 1 }


-- units of conformance
ciscoDs3ConfMIBGroup  OBJECT-GROUP
        OBJECTS {
            cds3LineType,         
            cds3LineAIScBitsCheck,     
            cds3LineRcvFEACValidation,   
            cds3LineOOFCriteria,        
            cds3TraceToTransmit,
            cds3TraceToExpect,
            cds3TraceAlarm,
            cds3InternalEqualizer,
            cds3NearEndLineLoopbackStatus,
	    cds3FarEndLineLoopbackStatus
            }
       STATUS current
       DESCRIPTION
          "Collection of DS3/E3 line related configuration parameters."
       ::= { ciscoDs3MIBGroups 1}

cds3StatsMIBGroup OBJECT-GROUP
    OBJECTS {
         cds3RcvLOSCount,
         cds3RcvOOFCount,
         cds3RAICount,
         cds3CCVCount,
         cds3FECount, 
         cds3EXZSCount,
         cds3LCVCount,
         cds3PCVCount,
         cds3CPECount,
         cds3FEBECount,
         cds3RcvAISCount
         }
     STATUS current
     DESCRIPTION
        "Collection of DS3/E3 line related real time counters."
     ::= { ciscoDs3MIBGroups 2 }

ciscoDs3AlarmMIBGroup OBJECT-GROUP
        OBJECTS {
            cds3NEAlarmUpCount,
            cds3NEAlarmDownCount,
            cds3NEAlarmThreshold,
            cds3FEAlarmUpCount,
            cds3FEAlarmDownCount,
            cds3FEAlarmThreshold,
            cds3StatisticalAlarmSeverity ,
            cds3LCV15MinThreshold,
            cds3LCV24HrThreshold ,
            cds3LES15MinThreshold,
            cds3LES24HrThreshold ,
            cds3PCV15MinThreshold,
            cds3PCV24HrThreshold,
            cds3PES15MinThreshold,
            cds3PES24HrThreshold,
            cds3PSES15MinThreshold,
            cds3PSES24HrThreshold ,
            cds3SEFS15MinThreshold,
            cds3SEFS24HrThreshold,
            cds3UAS15MinThreshold,
            cds3UAS24HrThreshold ,
            cds3CCV15MinThreshold,
            cds3CCV24HrThreshold ,
            cds3CES15MinThreshold,
            cds3CES24HrThreshold ,
            cds3CSES15MinThreshold,
            cds3CSES24HrThreshold,
            cds3LSES15MinThreshold,
            cds3LSES24HrThreshold,
            cds3LineStatisticalAlarmState,
            cds3IntervalNumber,
            cds3IntervalLSESs,
            cds3LCVCurrent24Hr,
            cds3LESCurrent24Hr,
            cds3PCVCurrent24Hr,
            cds3PESCurrent24Hr,
            cds3PSESCurrent24Hr,
            cds3SEFSCurrent24Hr,
            cds3UASCurrent24Hr,
            cds3CCVCurrent24Hr,
            cds3CESCurrent24Hr,
            cds3CSESCurrent24Hr,
            cds3LSESCurrent24Hr
            }
       STATUS current
       DESCRIPTION
          "Collection of DS3/E3 related interval counters and threshold 
           parameters."
       ::= { ciscoDs3MIBGroups 3 }

ciscoPlcpCounterMIBGroup OBJECT-GROUP
        OBJECTS {
            cds3PlcpRcvBip8Count, 
            cds3PlcpRcvOOFCount, 
            cds3PlcpRcvRAICount,
            cds3PlcpFECount, 
            cds3PlcpFESecCount,
            cds3PlcpSEFSecCount,
            cds3PlcpFEBECount, 
            cds3PlcpFEBESecCount,
            cds3PlcpSEFEBESecCount
            }
       STATUS current
       DESCRIPTION
          "Collection of PLCP related real time counters."
       ::= { ciscoDs3MIBGroups 4 }

ciscoPlcpAlarmMIBGroup OBJECT-GROUP
        OBJECTS {
        cds3PlcpStatisticalAlarmSeverity,
        cds3PlcpBip8CV15MinThreshold,
        cds3PlcpBip8CV24HrThreshold,
        cds3PlcpBip8ES15MinThreshold,
        cds3PlcpBip8ES24HrThreshold,
        cds3PlcpBip8SES15MinThreshold,
        cds3PlcpBip8SES24HrThreshold,
        cds3PlcpSEFS15MinThreshold,
        cds3PlcpSEFS24HrThreshold,
        cds3PlcpUAS15MinThreshold,
        cds3PlcpUAS24HrThreshold ,
        cds3PlcpLineAlarmState ,
        cds3PlcpLineStatisticalAlarmState,
        cds3PlcpBip8CVCurrent,
        cds3PlcpBip8CV24HrBucket,
        cds3PlcpBip8ESCurrent,
        cds3PlcpBip8ES24HrBucket,
        cds3PlcpBip8SESCurrent,
        cds3PlcpBip8SES24HrBucket,
        cds3PlcpSEFSCurrent,
        cds3PlcpSEFS24HrBucket,
        cds3PlcpUASCurrent,
        cds3PlcpUAS24HrBucket
        }
       STATUS current
       DESCRIPTION
          "Collection of PLCP related interval counters and threshold 
           parameters."
       ::= { ciscoDs3MIBGroups 5 }
 
ciscoDs3Previous24HrGroup OBJECT-GROUP
        OBJECTS {
            cds3LCVPrevious24Hr,
            cds3LESPrevious24Hr,
            cds3PCVPrevious24Hr,
            cds3PESPrevious24Hr,
            cds3PSESPrevious24Hr,
            cds3SEFSPrevious24Hr,
            cds3UASPrevious24Hr,
            cds3CCVPrevious24Hr,
            cds3CESPrevious24Hr,
            cds3CSESPrevious24Hr,
            cds3LSESPrevious24Hr
        }
        STATUS current
        DESCRIPTION
           "A collection DS3/E3 related previous 24 hour counters."
        ::= { ciscoDs3MIBGroups 6 }
END
