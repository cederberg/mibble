-- *****************************************************************   
-- CISCO-ITP-SP-MIB: Itp Signalling Point 
--                       
-- June 2001,  John Linton, Shekhar Acharya
--
-- Copyright (c) 2001-2002 by Cisco Systems, Inc.
-- All rights reserved.
-- *****************************************************************
CISCO-ITP-SP-MIB DEFINITIONS ::= BEGIN

IMPORTS
        Counter32,
        Integer32,
        Gauge32,
        MODULE-IDENTITY,
        NOTIFICATION-TYPE,
        OBJECT-TYPE,
        TimeTicks,
        Unsigned32
             FROM SNMPv2-SMI
                
        SnmpAdminString 
              	FROM SNMP-FRAMEWORK-MIB

        InetAddressType, 
        InetAddress
             FROM INET-ADDRESS-MIB         
             
        InterfaceIndexOrZero
             FROM IF-MIB
        --   FROM CISCO-TC
                
        RowStatus,
        TimeStamp,
        TruthValue,
        TEXTUAL-CONVENTION
             FROM SNMPv2-TC

        CItpTcAclId,
        CItpTcCLLI, 
        CItpTcDisplayPC, 
        CItpTcLinksetId, 
        CItpTcLinkSLC, 
        CItpTcLinkType, 
        CItpTcNetworkIndicator,
        CItpTcPointCode,
        CItpTcPointCodeType,
        CItpTcQos,
        CItpTcRouteTableName, 
        CItpTcSs7Variant, 
        CItpTcTimerMtp2T01, 
        CItpTcTimerMtp2T02, 
        CItpTcTimerMtp2T03, 
        CItpTcTimerMtp2T04E, 
        CItpTcTimerMtp2T04N, 
        CItpTcTimerMtp2T05,
        CItpTcTimerMtp2T06,
        CItpTcTimerMtp2T07,
        CItpTcTimerMtp3T01,
        CItpTcTimerMtp3T02,
        CItpTcTimerMtp3T03,
        CItpTcTimerMtp3T04,
        CItpTcTimerMtp3T05,
        CItpTcTimerMtp3T06,
        CItpTcTimerMtp3T07,
        CItpTcTimerMtp3T08,
        CItpTcTimerMtp3T10,
        CItpTcTimerMtp3T11,
        CItpTcTimerMtp3T12,
        CItpTcTimerMtp3T13,
        CItpTcTimerMtp3T14,
        CItpTcTimerMtp3T15,
        CItpTcTimerMtp3T16,
        CItpTcTimerMtp3T17,
        CItpTcTimerMtp3T18,
        CItpTcTimerMtp3T19,
        CItpTcTimerMtp3T20,
        CItpTcTimerMtp3T21,
        CItpTcTimerMtp3T22,
        CItpTcTimerMtp3T23,
        CItpTcTimerMtp3T24,
        CItpTcTimerMtp3T25,
        CItpTcTimerMtp3T26,
        CItpTcTimerMtp3T27,
        CItpTcTimerMtp3T28,
        CItpTcTimerMtp3T29,
        CItpTcTimerMtp3T30,
        CItpTcTimerMtp3T31,
        CItpTcTimerMtp3T32,
        CItpTcTimerMtp3T33,
        CItpTcTimerMtp3T34,
        CItpTcTimerLinkTest, 
        CItpTcTimerLinkMessage, 
        CItpTcTimerLinkActRetry 
             FROM CISCO-ITP-TC-MIB

        MODULE-COMPLIANCE,
        NOTIFICATION-GROUP,
        OBJECT-GROUP
             FROM SNMPv2-CONF
                
        ciscoMgmt
             FROM CISCO-SMI;        

ciscoItpSpMIB MODULE-IDENTITY
        LAST-UPDATED    "200203070000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7@cisco.com"
                
        DESCRIPTION
               "The MIB for managing Signalling Points and its 
                associated messages transported over Signalling 
                System  No. 7 (SS7) Network via Cisco IP Transfer
                Point.  
                
                The Cisco IP Transfer Point (ITP) is a hardware 
                and software solution that transports SS7 traffic 
                using IP. Each ITP node provides function similar
                to SS7 Signalling point.   
                
                The relevant ITU documents describing this technology
                is the ITU Q series, including ITU Q.700: Introduction
                to CCITT Signalling System No. 7 and ITU Q.701 
                Functional description of the message transfer part
                (MTP) of Signalling System No. 7. 
                
                This MIB models the SP as follows:
                
                The SP is associated with one or more point codes.
                Each pointcode is associated with:
                  an SS7 variant, timers, and linksets.
                
                Linksets contain:
                  destination point code 
                  linkset byte/packet statistics,
                  accounting information per Destination Point 
                  Code(DPC) and Originating Point Code (OPC) 
                  violation accounting information per DPC and OPC
                  links,  reference to incoming and outgoing ACL
                  reference to a routing table for each SS7 packet type
                
                Links contain:
                  timers, and byte/packet statistics.
                
                The figure below provides a diagrammatic representation
                of the relationships. Each box may be replicated
                providing multiple instances of the object. 
                
                '--->' indicates that the object to the left contains
                a reference to the object to the right.
                
                '###>' indicates that the object to the left contains
                an instance of the object to the right.
                
                The down arrow indicates that the object being pointed
                to contains snmp indices of the objects above it.
                
                
                  ________________
                 |                |
                 |      Sp        |###> point code, timers
                 |________________|
                         |
                         V
                  ________________
                 |                |
                 |                |---> Accounting
                 |    Linkset     |---> Violation Accounting
                 |                |---> Incoming ACL
                 |                |---> Outgoing ACL
                 |________________|---> Routing Tables.
                         |
                         V
                  ________________
                 |     Link       |###> timers
                 |________________|---> statistics


        Abbreviations:
          AERM  - Alignment Error Rate Monitor
          CLLI  - Common Language Location Codes 
          HSL   - High Speed Link (ATM based)
          LLSC  - link set control 
          LSAC  - Signalling link activity control
          LSDA  - Signalling data link allocation 
          LSLA  - Signalling link activation 
          LSLD  - Signalling link deactivation 
          LSLR  - Signalling link restoration 
          LSSU  - Link Status Signal Unit
          LSTA  - Signalling terminal allocation 
          MTP   - Message Transport Protocol
          MTP2  - Layer 2 of Message Transport Protocol
          MTP3  - Layer 3 of Message Transport Protocol
          PC    - Point Code
          RTN   - RouteTableName
          SCTP  - Stream Transmission Protocol(RFC 2960)
          SIB   - Status Indicator Busy
          SP    - Signalling Point
          SS7   -  System  No. 7 (SS7) Network
          SUERM - Signal Unit Error Rate Monitor 
          TCBC  - Changeback control
          TCOC  - Changeover control
          TCRC  - Controlled rerouting control
          TFRC  - Forced rerouting control
          TLAC  - Link availability control
          TPRC  - Signalling point restart control
          TRCC  - Signalling route set congestion control
          TSFC  - Signalling traffic flow control
          TSRC  - Signalling routing control "
          
        REVISION        "200203070000Z"
        DESCRIPTION
                "Added support for notification on link utilization.
                 Textual conventions:
                    CItpSpSampleInterval
                    CItpSpPercentThreshold 
                    CItpSpLinkUtilization
                    CItpSpLinkCapacity
                    CItpSpLinkUtilizationState
                 
                 Scalars:
                    cItpSpUtilSampleInterval    
                    cItpSpUtilThreshold 
                    cItpSpUtilAbateDelta 
                    
                 Linkset table:
                    cItpSpLinksetPlanCapacity - deprecated.  
                    
                 Link table:
                    cItpSpLinkPlanCapacityRcvd
                    cItpSpLinkUtilThresholdRcvd
                    cItpSpLinkUtilizationRcvd
                    cItpSpLinkUtilStateRcvd
                    cItpSpLinkL2BytesRcvd  
                    cItpSpLinkPlanCapacitySent
                    cItpSpLinkUtilThresholdSent
                    cItpSpLinkUtilizationSent
                    cItpSpLinkUtilStateSent
                    cItpSpLinkL2BytesSent
                    
                    
                 Notification enable:   
                    cItpSpLinkUtilNotifEnabled
                    
                 Notification:   
                    cItpSpLinkRcvdUtilChange
                    cItpSpLinkSentUtilChange"
                   
        REVISION        "200201230000Z"
        DESCRIPTION
                "Modified the following objects:
                   cItpSpLinkType:  Added new high speed link type
                      to textual convention CItpTcLinkType. 
                      
                   cItpSpVariant:  Added new China SS7 variant       
                      to textual convention CItpTcSs7Variant. 
                   Add new enumerate 
                   
                 Added the following objects:
                   cItpSpDistSccpUnseq
                   cItpSpSummaryRoutingException
                   cItpSpLinksetVariant 
                   cItpSpLinkDroppedPkts   
                   cItpSpLinkTransmittedLssu 
                   cItpSpLinkReceivedLssu 
                   cItpSpLinkProtocolDetails
                   cItpSpLinkLsacState
                   cItpSpLinkTsrcState
                   cItpSpLinkTcocState
                   cItpSpLinkTcocLocalBSNT    
                   cItpSpLinkTcocRemoteBSNT    
                   cItpSpLinkTcbcState
                   cItpSpLinkReceivedSIB           
                   cItpSpLinkTransmittedSIB         
                   cItpSpLinkMtp2ExpiredT01  
                   cItpSpLinkMtp2ExpiredT02  
                   cItpSpLinkMtp2ExpiredT03  
                   cItpSpLinkMtp2ExpiredT04 
                   cItpSpLinkMtp2ExpiredT05  
                   cItpSpLinkMtp2ExpiredT06  
                   cItpSpLinkMtp2ExpiredT07  
                   cItpSpLinkOMAERMCount     
                   cItpSpLinkOMAERMFailCount 
                   cItpSpLinkOMSURMCount     
                   cItpSpLinkOMSURMFailCount" 
                 
        REVISION        "200108290000Z"
        DESCRIPTION
                "Initial version of this MIB module."
        ::= { ciscoMgmt  232 }


-- Top-level structure of the MIB
cItpSpMIBNotifs           OBJECT IDENTIFIER ::= { ciscoItpSpMIB    0 }
cItpSpMIBObjects          OBJECT IDENTIFIER ::= { ciscoItpSpMIB    1 }
cItpSpMIBConformance      OBJECT IDENTIFIER ::= { ciscoItpSpMIB    2 }

cItpSpScalars             OBJECT IDENTIFIER ::= { cItpSpMIBObjects 1 }
cItpSpPointCode           OBJECT IDENTIFIER ::= { cItpSpMIBObjects 2 }
cItpSpLinkset             OBJECT IDENTIFIER ::= { cItpSpMIBObjects 3 }
cItpSpLink                OBJECT IDENTIFIER ::= { cItpSpMIBObjects 4 }
cItpSpNotificationsEnable OBJECT IDENTIFIER ::= { cItpSpMIBObjects 5 }

-- **************************************************************
-- *                                                            *
-- * Textual Conventions                                        *
-- *                                                            *
-- **************************************************************
CItpSpSequenceNumber ::= TEXTUAL-CONVENTION
        STATUS          current
        DESCRIPTION
                "This textual convention defines all of the allowed
                 values for a sequence of integers used by the 
                 SS7 protocol to transmit and acknowledge packets.
                 The range is specified from 0 to maximum allowed 
                 value for extended sequence numbers.  The actual 
                 range will depend on the type of link and   
                 the variant.  The value will increase and then wrap
                 to the zero value. The following are examples of 
                 valid sequences.
                 0..126,127,0..
                 0..254,255,0..
                 0..32766,32767,0..
                 0..65534,65535,0.."
        SYNTAX Unsigned32 ( 0..65535 )
        
CItpSpSampleInterval ::= TEXTUAL-CONVENTION
        STATUS          current
        DESCRIPTION
                "This textual convention defines the allowed values
                 for a sample interval.  This value is specified in
                 seconds and ranges from 1 minute to 1 hour."
        SYNTAX Unsigned32 ( 60..3600 )
        
CItpSpPercentThreshold ::= TEXTUAL-CONVENTION
        STATUS          current
        DESCRIPTION
                "This textual convention defines the allowed values
                 for a thresholds specified as percentage of 
                 link utilization.  A value of zero indicates that
                 this specific threshold is to be ignored."  
        SYNTAX Unsigned32 (0..100)
        
CItpSpLinkUtilization ::= TEXTUAL-CONVENTION
        STATUS          current
        DESCRIPTION
                "This textual convention defines a range of 
                 percentages that represent the utilization of 
                 a link. Any value over 999 will be represented
                 as 999.
                 
                 For SS7 links based on IP/SCTP the link capacity 
                 is not directly related to the interface speed used
                 to transmit packets.  This is different from serial
                 and HSL links.  The capacity of these types of 
                 links depend on the amount of resources available
                 in the IP cloud.  The IP cloud must be provisioned
                 to support traffic for all SS7 links. In order to 
                 monitor link utilization on IP/SCTP based SS7 links
                 a planned capacity must be specified.  If this value
                 is incorrectly estimated or traffic exceeds this 
                 expected value link utilization may exceed 100
                 percent.  This is possible because the IP cloud
                 may be provisioned with additional capacity or 
                 may discard less important traffic based on Qos
                 parameters.
                 
                 When a SS7 link has not be configured for link 
                 utilization monitoring this value object will
                 have a value of zero."
        SYNTAX Unsigned32 (0..999)
        
CItpSpLinkCapacity ::= TEXTUAL-CONVENTION
        STATUS          current
        DESCRIPTION
                "This textual convention defines the planned 
                 capacity of a SS7 link in bit per second. 
                 
                 If the link type is serial or HSL the link capacity
                 can be obtained from information in the IF-MIB. 
                 
                 If the link type is sctp/ip a value of zero 
                 indicates that link utilization should not 
                 be calculated for this SS7 link."
        SYNTAX Unsigned32 (0 | 56000..2147483647)

CItpSpLinkUtilizationState ::= TEXTUAL-CONVENTION
    STATUS              current
    DESCRIPTION
         "Link Utilization State as follows:
            'unMonitored(0)'    - traffic for a specified direction 
                                  is not being monitored.
            'underThreshold(1)' - traffic for a specified direction
                on a link is below the specified threshold.
                      
            'overThreshold(2)'  - traffic for a specified direction 
                on a link is above to or exceeds the specified 
                threshold."
    SYNTAX INTEGER {
                    unMonitored(0),
                    underThreshold(1),
                    overThreshold(2)
    }
    
--  *************************************************************
--  *                                                           *
--  * SP - Scalars                                              *
--  *                                                           *
--  *************************************************************

cItpSpVariant                    OBJECT-TYPE
    SYNTAX                       CItpTcSs7Variant 
    MAX-ACCESS                   read-write
    STATUS                       current
    DESCRIPTION
            "The SS7 variant implemented in this SP."
    ::= { cItpSpScalars  1 }
        
cItpSpCLLICode                   OBJECT-TYPE
    SYNTAX                       CItpTcCLLI
    MAX-ACCESS                   read-write
    STATUS                       current
    DESCRIPTION
            "Common Language Location Codes (CLLI Codes)."
    ::= { cItpSpScalars  2 }

cItpSpDisplayName                OBJECT-TYPE
    SYNTAX                       SnmpAdminString ( SIZE ( 0..30 ) )
    MAX-ACCESS                   read-write
    STATUS                       current
    DESCRIPTION
            "A short identifier for the Signalling point.
             This value can be set by system administrator
             or defaults to the local point code formatted
             as an ASCII string."
    ::= { cItpSpScalars  3 }

cItpSpDescription                OBJECT-TYPE
       SYNTAX                    SnmpAdminString ( SIZE ( 0..254 ) )
       MAX-ACCESS                read-write
       STATUS                    current
       DESCRIPTION
               "A textual description for the Signalling point."
    ::= { cItpSpScalars  4 }

cItpSpMtp2T01                     OBJECT-TYPE
    SYNTAX                        CItpTcTimerMtp2T01  
    UNITS                         "milliseconds"
    MAX-ACCESS                    read-write
    STATUS                        current
    DESCRIPTION
            "Alignment ready timer." 
    ::= { cItpSpScalars  5 }

cItpSpMtp2T02                     OBJECT-TYPE
    SYNTAX                        CItpTcTimerMtp2T02  
    UNITS                         "milliseconds"
    MAX-ACCESS                    read-write
    STATUS                        current
    DESCRIPTION
            "Not aligned timer."
    ::= { cItpSpScalars  6 }

cItpSpMtp2T03                     OBJECT-TYPE
    SYNTAX                        CItpTcTimerMtp2T03
    UNITS                         "milliseconds"
    MAX-ACCESS                    read-write
    STATUS                        current
    DESCRIPTION
            "Aligned timer."
    ::= { cItpSpScalars  7 }

cItpSpMtp2T04E                    OBJECT-TYPE
    SYNTAX                        CItpTcTimerMtp2T04E
    UNITS                         "milliseconds"
    MAX-ACCESS                    read-write
    STATUS                        current   
    DESCRIPTION
            "Proving period timer emergency timer. "
    ::= { cItpSpScalars  8 }

cItpSpMtp2T04N                    OBJECT-TYPE
    SYNTAX                        CItpTcTimerMtp2T04N
    UNITS                         "milliseconds"
    MAX-ACCESS                    read-write
    STATUS                        current
    DESCRIPTION
            "Proving period timer normal timer."
    ::= { cItpSpScalars  9 }

cItpSpMtp2T05                     OBJECT-TYPE
    SYNTAX                        CItpTcTimerMtp2T05
    UNITS                         "milliseconds"
    MAX-ACCESS                    read-write
    STATUS                        current
    DESCRIPTION
            "Sending SIB timer."
    ::= { cItpSpScalars  10 }

cItpSpMtp2T06                     OBJECT-TYPE
    SYNTAX                        CItpTcTimerMtp2T06
    UNITS                         "milliseconds"
    MAX-ACCESS                    read-write
    STATUS                        current
    DESCRIPTION
            "Remote congestion timer. "
    ::= { cItpSpScalars  11 }

cItpSpMtp2T07                     OBJECT-TYPE
    SYNTAX                        CItpTcTimerMtp2T07
    UNITS                         "milliseconds"
    MAX-ACCESS                    read-write
    STATUS                        current
    DESCRIPTION
            "Excessive delay of acknowledgement timer."
    ::= { cItpSpScalars  12 }

cItpSpMtp3T01                     OBJECT-TYPE
    SYNTAX                        CItpTcTimerMtp3T01
    UNITS                         "milliseconds"
    MAX-ACCESS                    read-write
    STATUS                        current
    DESCRIPTION
            "Delay to avoid message mis-sequencing on changeover."
    ::= { cItpSpScalars  13 }

cItpSpMtp3T02                     OBJECT-TYPE
    SYNTAX                        CItpTcTimerMtp3T02
    UNITS                         "milliseconds"
    MAX-ACCESS                    read-write
    STATUS                        current
    DESCRIPTION
            "Waiting for changeover acknowledgement."
    ::= { cItpSpScalars  14 }

cItpSpMtp3T03                     OBJECT-TYPE
    SYNTAX                        CItpTcTimerMtp3T03
    UNITS                         "milliseconds"
    MAX-ACCESS                    read-write
    STATUS                        current
    DESCRIPTION
            "Time controlled diversion-delay to avoid
            mis-sequencing on change back."
    ::= { cItpSpScalars  15 }

cItpSpMtp3T04                     OBJECT-TYPE
    SYNTAX                        CItpTcTimerMtp3T04
    UNITS                         "milliseconds"
    MAX-ACCESS                    read-write
    STATUS                        current
    DESCRIPTION
            "Waiting for change back acknowledgement (first
            attempt)."
    ::= { cItpSpScalars  16 }

cItpSpMtp3T05                     OBJECT-TYPE
    SYNTAX                        CItpTcTimerMtp3T05
    UNITS                         "milliseconds"
    MAX-ACCESS                    read-write
    STATUS                        current
    DESCRIPTION
            "Waiting for change back acknowledgement (second
             attempt)."
    ::= { cItpSpScalars  17 }

cItpSpMtp3T06                     OBJECT-TYPE
    SYNTAX                        CItpTcTimerMtp3T06
    UNITS                         "milliseconds"
    MAX-ACCESS                    read-write
    STATUS                        current
    DESCRIPTION
            "Delay to avoid message mis-sequencing on controlled
             rerouting."
    ::= { cItpSpScalars  18 }

cItpSpMtp3T07                     OBJECT-TYPE
    SYNTAX                        CItpTcTimerMtp3T07
    UNITS                         "milliseconds"
    MAX-ACCESS                    read-write
    STATUS                        current
    DESCRIPTION
            "Waiting for Signalling data link connection
             acknowledgement."
    ::= { cItpSpScalars  19 }
            
cItpSpMtp3T08                     OBJECT-TYPE
    SYNTAX                        CItpTcTimerMtp3T08
    UNITS                         "milliseconds"
    MAX-ACCESS                    read-write
    STATUS                        current
    DESCRIPTION
            "Transfer prohibited inhibition timer (transient
             solution)."
    ::= { cItpSpScalars  20 }

cItpSpMtp3T10                     OBJECT-TYPE
    SYNTAX                        CItpTcTimerMtp3T10
    UNITS                         "milliseconds"
    MAX-ACCESS                    read-write
    STATUS                        current
    DESCRIPTION
            "Waiting to repeat Signalling routeset test message."
    ::= { cItpSpScalars  21 }

cItpSpMtp3T11                     OBJECT-TYPE
    SYNTAX                        CItpTcTimerMtp3T11
    UNITS                         "milliseconds"
    MAX-ACCESS                    read-write
    STATUS                        current
    DESCRIPTION
            "Transfer restricted timer. (This is one way of
            implementing the function described in 13.4/Q.704 and
            mainly intended to simplify SPs.)."
    ::= { cItpSpScalars  22 }

cItpSpMtp3T12                     OBJECT-TYPE
    SYNTAX                        CItpTcTimerMtp3T12
    UNITS                         "milliseconds"
    MAX-ACCESS                    read-write
    STATUS                        current
    DESCRIPTION                   
            "Waiting for uninhibit acknowledgement."
    ::= { cItpSpScalars  23 }

cItpSpMtp3T13                     OBJECT-TYPE
    SYNTAX                        CItpTcTimerMtp3T13
    UNITS                         "milliseconds"
    MAX-ACCESS                    read-write
    STATUS                        current
    DESCRIPTION
            "Waiting for force uninhibit."
    ::= { cItpSpScalars  24 }

cItpSpMtp3T14                     OBJECT-TYPE
    SYNTAX                        CItpTcTimerMtp3T14
    UNITS                         "milliseconds"
    MAX-ACCESS                    read-write
    STATUS                        current
    DESCRIPTION
            "Waiting for inhibition acknowledgement."
    ::= { cItpSpScalars  25 }

cItpSpMtp3T15                     OBJECT-TYPE
    SYNTAX                        CItpTcTimerMtp3T15
    UNITS                         "milliseconds"
    MAX-ACCESS                    read-write
    STATUS                        current
    DESCRIPTION
            "Waiting to start Signalling routeset congestion
             test."
    ::= { cItpSpScalars  26 }

cItpSpMtp3T16                     OBJECT-TYPE
    SYNTAX                        CItpTcTimerMtp3T16
    UNITS                         "milliseconds"
    MAX-ACCESS                    read-write
    STATUS                        current
    DESCRIPTION
            "Waiting for routeset congestion status update."
    ::= { cItpSpScalars  27 }

cItpSpMtp3T17                     OBJECT-TYPE
    SYNTAX                        CItpTcTimerMtp3T17
    UNITS                         "milliseconds"
    MAX-ACCESS                    read-write
    STATUS                        current
    DESCRIPTION
            "Delay to avoid oscillation of initial alignment
            failure and link restart."
    ::= { cItpSpScalars  28 }

cItpSpMtp3T18                     OBJECT-TYPE
    SYNTAX                        CItpTcTimerMtp3T18
    UNITS                         "milliseconds"
    MAX-ACCESS                    read-write
    STATUS                        current
    DESCRIPTION
            "This timers servers different function based on the 
             variant.
             
             ANSI: Repeat TFR once by response method
             ITU:  MTP restart link supervision"
    ::= { cItpSpScalars  29 }

cItpSpMtp3T19                     OBJECT-TYPE
    SYNTAX                        CItpTcTimerMtp3T19
    UNITS                         "milliseconds"
    MAX-ACCESS                    read-write
    STATUS                        current
    DESCRIPTION
            "This timers servers different function based on the 
             variant.
             
             ANSI: failed craft timer referral timer
             ITU:  supervision timer during MTP restart"
    ::= { cItpSpScalars  30 }

cItpSpMtp3T20                     OBJECT-TYPE
    SYNTAX                        CItpTcTimerMtp3T20
    UNITS                         "milliseconds"
    MAX-ACCESS                    read-write
    STATUS                        current
    DESCRIPTION
            "This timers servers different function based on the 
             variant.
             
             ANSI: waiting to repeat local inhibit test
             ITU:  MTP restart timer at the Signalling point"
    ::= { cItpSpScalars  31 }

cItpSpMtp3T21                     OBJECT-TYPE
    SYNTAX                        CItpTcTimerMtp3T21
    UNITS                         "milliseconds"
    MAX-ACCESS                    read-write
    STATUS                        current
    DESCRIPTION
            "This timers servers different function based on the 
             variant.
             
             ANSI: waiting to repeat remote inhibit test)       
             ITU:  MTP restart timer at adjacent Signalling point"
    ::= { cItpSpScalars  32 }

cItpSpMtp3T22                     OBJECT-TYPE
    SYNTAX                        CItpTcTimerMtp3T22
    UNITS                         "milliseconds"
    MAX-ACCESS                    read-write
    STATUS                        current
    DESCRIPTION
            "This timers servers different function based on the 
             variant.
             
             ANSI: restarting SP waiting for Signalling links avail
             ITU:  local inhibit test timer" 
    ::= { cItpSpScalars  33 }

cItpSpMtp3T23                     OBJECT-TYPE
    SYNTAX                        CItpTcTimerMtp3T23  
    UNITS                         "milliseconds"
    MAX-ACCESS                    read-write
    STATUS                        current
    DESCRIPTION
            "This timers servers different function based on the 
             variant.
             
             ANSI: restarting SP waiting to receive all TRA msgs
             ITU:  remote inhibit test timer"
    ::= { cItpSpScalars  34 }

cItpSpMtp3T24                     OBJECT-TYPE
    SYNTAX                        CItpTcTimerMtp3T24
    UNITS                         "milliseconds"
    MAX-ACCESS                    read-write
    STATUS                        current
    DESCRIPTION
            "This timers servers different function based on the 
             variant.
             
             ANSI: restarting SP waiting to broadcast all TRA msgs
             ITU:  stabilizing timer after local processor outage"
    ::= { cItpSpScalars  35 }

cItpSpMtp3T25                     OBJECT-TYPE
    SYNTAX                        CItpTcTimerMtp3T25
    UNITS                         "milliseconds"
    MAX-ACCESS                    read-write
    STATUS                        current
    DESCRIPTION
            "Timer at Signalling point (SP) adjacent to restarting
            SP, waiting for traffic restart allowed message."
    ::= { cItpSpScalars  36 }

cItpSpMtp3T26                     OBJECT-TYPE
    SYNTAX                        CItpTcTimerMtp3T26
    UNITS                         "milliseconds"
    MAX-ACCESS                    read-write
    STATUS                        current
    DESCRIPTION
            "Timer at restarting SP waiting to repeat traffic
            restart waiting message."
    ::= { cItpSpScalars  37 }

cItpSpMtp3T27                     OBJECT-TYPE
    SYNTAX                        CItpTcTimerMtp3T27
    UNITS                         "milliseconds"
    MAX-ACCESS                    read-write
    STATUS                        current
    DESCRIPTION
            "Minimum duration of unavailability for full restart."
    ::= { cItpSpScalars  38 }

cItpSpMtp3T28                     OBJECT-TYPE
    SYNTAX                        CItpTcTimerMtp3T28
    UNITS                         "milliseconds"
    MAX-ACCESS                    read-write
    STATUS                        current
    DESCRIPTION
            "Timer at SP adjacent to restarting SP waiting for
            traffic restart waiting message."
    ::= { cItpSpScalars  39 }

cItpSpMtp3T29                     OBJECT-TYPE
    SYNTAX                        CItpTcTimerMtp3T29
    UNITS                         "milliseconds"
    MAX-ACCESS                    read-write
    STATUS                        current
    DESCRIPTION
            "Timer started when TRA sent in response to unexpected
            TRA or TRW."
    ::= { cItpSpScalars  40 }

cItpSpMtp3T30                     OBJECT-TYPE
    SYNTAX                        CItpTcTimerMtp3T30
    UNITS                         "milliseconds"
    MAX-ACCESS                    read-write
    STATUS                        current
    DESCRIPTION                   
            "Timer to limit sending of TFPs and TFRs in response
            to unexpected TRA or TRW."
    ::= { cItpSpScalars  41 }

cItpSpMtp3T31                     OBJECT-TYPE
    SYNTAX                        CItpTcTimerMtp3T31
    UNITS                         "milliseconds"
    MAX-ACCESS                    read-write
    STATUS                        current
    DESCRIPTION
            "False link congestion detection timer."
    ::= { cItpSpScalars  42 }

cItpSpMtp3T32                     OBJECT-TYPE
    SYNTAX                        CItpTcTimerMtp3T32
    UNITS                         "milliseconds"
    MAX-ACCESS                    read-write
    STATUS                        current
    DESCRIPTION
            "Link oscillation timer - Procedure A."
    ::= { cItpSpScalars  43 }

cItpSpMtp3T33                     OBJECT-TYPE
    SYNTAX                        CItpTcTimerMtp3T33 
    UNITS                         "milliseconds"
    MAX-ACCESS                    read-write
    STATUS                        current
    DESCRIPTION
            "Probation timer for link oscillation - Procedure B."
    ::= { cItpSpScalars  44 }
                           
cItpSpMtp3T34                     OBJECT-TYPE
    SYNTAX                        CItpTcTimerMtp3T34
    UNITS                         "milliseconds"
    MAX-ACCESS                    read-write
    STATUS                        current
    DESCRIPTION                   
            "Suspension timer for link oscillation - Procedure B."
    ::= { cItpSpScalars  45 }
        
cItpSpTimerLinkTest               OBJECT-TYPE
    SYNTAX                        CItpTcTimerLinkTest  
    UNITS                         "milliseconds"
    MAX-ACCESS                    read-write
    STATUS                        current
    DESCRIPTION
            "Signalling Link test acknowledgement timer."
    ::= { cItpSpScalars  46 }

cItpSpTimerLinkMessage            OBJECT-TYPE
    SYNTAX                        CItpTcTimerLinkMessage  
    UNITS                         "milliseconds"
    MAX-ACCESS                    read-write
    STATUS                        current
    DESCRIPTION
            "Interval timer for sending test messages."
    ::= { cItpSpScalars  47 }
        
cItpSpTimerLinkActRetry           OBJECT-TYPE
    SYNTAX                        CItpTcTimerLinkActRetry  
    UNITS                         "milliseconds"
    MAX-ACCESS                    read-write
    STATUS                        current
    DESCRIPTION                   
            "Link activation retry timer."
    ::= { cItpSpScalars  48 }
    
cItpSpTFR                        OBJECT-TYPE
    SYNTAX                       TruthValue
    MAX-ACCESS                   read-write
    STATUS                       current
    DESCRIPTION
            "Allow transfer restricted messages.
            'true'  TFR are allowed.
            'false' TFR are disabled."
    DEFVAL { false }
    ::= { cItpSpScalars  49 }
    
cItpSpCongestionsLevels          OBJECT-TYPE
    SYNTAX                       TruthValue
    MAX-ACCESS                   read-write
    STATUS                       current
    DESCRIPTION
            "Allow multiple congestion levels.
            'true'  multiple congestion levels are allowed.
            'false' multiple congestion levels are disabled."
    DEFVAL { false }
    ::= { cItpSpScalars  50 }
    
cItpSpFastRestart                OBJECT-TYPE
    SYNTAX                       TruthValue
    MAX-ACCESS                   read-write
    STATUS                       current
    DESCRIPTION
            "The support for fast restarts as follows. 
            'true'  fast restart is enabled.
            'false' fast restart is disabled."
    DEFVAL { false }
    ::= { cItpSpScalars  51 }
    
cItpSpDistSccpUnseq              OBJECT-TYPE
    SYNTAX                       TruthValue
    MAX-ACCESS                   read-write
    STATUS                       current
    DESCRIPTION
            "Evenly distribute Class 0 SCCP messages as follows. 
            'true'   Evenly distribute 0 SCCP messages is enabled.
            'false'  Evenly distribute 0 SCCP messages is disabled."
    DEFVAL { false }
    ::= { cItpSpScalars  52 }
    
cItpSpSummaryRoutingException    OBJECT-TYPE
    SYNTAX                       TruthValue
    MAX-ACCESS                   read-write
    STATUS                       current
    DESCRIPTION
            "This object is used to control the usage of the summary
             route when both a summary route (or ANSI cluster route)
             and a full point-code route (within that summary) are
             configured.  The object is used to indicate whether
             the summary route is to be used when the full
             point-code destination is inaccessible as follows.
              'true'   Use summary routing.
              'false'  Do not use summary routing."
    DEFVAL { true }
    ::= { cItpSpScalars  53 }
    
cItpSpUtilSampleInterval         OBJECT-TYPE
    SYNTAX                       CItpSpSampleInterval
    UNITS                        "seconds"
    MAX-ACCESS                   read-write
    STATUS                       current
    DESCRIPTION
        "This object specifies the time interval used to monitor
         the utilization of SS7 links.  This object in combination
         with cItpSpUtilThreshold, cItpSpLinkPlanCapacitySent and
         cItpSpLinkPlanCapacityRcvd will be used to calculate 
         utilization of SS7 links.  Changes to the polling interval
         will take effect after the completion of the current 
         sample interval."
     DEFVAL { 300 }
    ::= { cItpSpScalars  54 }
    
cItpSpUtilThreshold             OBJECT-TYPE
    SYNTAX                      CItpSpPercentThreshold
    UNITS                       "percent"
    MAX-ACCESS                  read-write
    STATUS                      current
    DESCRIPTION
        "This object specifies the threshold of usage for all
         SS7 links in SP.  This object is used to determine when
         to generate the cItpSpLinkRcvdUtilChange or 
         cItpSpLinkSentUtilChange notifications.
         
         A value of zero indicates that no default threshold
         is specified.  Therefore, only links with non-zero
         values for cItpSpLinkUtilThresholdRcvd or 
         cItpSpLinkUtilThresholdSent will generate notifications
         based on link utilization.
         
         Changes to the utilization threshold will take effect
         at the end of the current interval."
     DEFVAL { 40 }
    ::= { cItpSpScalars  55 }
    
cItpSpUtilAbateDelta            OBJECT-TYPE
    SYNTAX                      CItpSpPercentThreshold
    UNITS                       "percent"
    MAX-ACCESS                  read-write
    STATUS                      current
    DESCRIPTION
        "This object allows the falling threshold to be lower 
         than the rising theshold when calculating whether to 
         generate the cItpSpLinkUtilThresholdRcvd or 
         cItpSpLinkUtilThresholdSent notifications.  This is done
         to prevent generating notifications for slight changes
         in traffic."
     DEFVAL { 0 }
    ::= { cItpSpScalars  56 }
    
--  *************************************************************
--  *                                                           *
--  * SP - Point Code Table                                     *
--  *                                                           *
--  *************************************************************
cItpSpPointCodeTable    OBJECT-TYPE
    SYNTAX          SEQUENCE OF CItpSpPointCodeTableEntry 
    MAX-ACCESS      not-accessible
    STATUS          current
    DESCRIPTION
            "A table that contain the varies types of point
            code defined for this Signalling point.'
            Entries are added to this table via
            cItpSpRowStatus  in accordance with the RowStatus
            convention."
    ::= { cItpSpPointCode  1 }

cItpSpPointCodeTableEntry        OBJECT-TYPE
    SYNTAX          CItpSpPointCodeTableEntry 
    MAX-ACCESS      not-accessible
    STATUS          current
    DESCRIPTION
            "A list of SP attributes."
    INDEX   {
              cItpSpPointCodeNi,
              cItpSpPointCodeBin 
            }
    ::= { cItpSpPointCodeTable  1 }

CItpSpPointCodeTableEntry  ::= SEQUENCE {
    cItpSpPointCodeNi                  CItpTcNetworkIndicator,
    cItpSpPointCodeBin                 CItpTcPointCode,
    cItpSpPointCodeType                CItpTcPointCodeType,
    cItpSpPointCodeDisplay             CItpTcDisplayPC,
    cItpSpPointCodeRowStatus           RowStatus
}

cItpSpPointCodeNi                 OBJECT-TYPE
    SYNTAX                        CItpTcNetworkIndicator 
    MAX-ACCESS                    not-accessible 
    STATUS                        current
    DESCRIPTION
            "The network Indicator for this pointcode."
    ::= { cItpSpPointCodeTableEntry 1 }

cItpSpPointCodeBin                OBJECT-TYPE
    SYNTAX                        CItpTcPointCode 
    MAX-ACCESS                    not-accessible 
    STATUS                        current
    DESCRIPTION
            "The point code for this SP."
    ::= { cItpSpPointCodeTableEntry 2 }
              
cItpSpPointCodeType               OBJECT-TYPE
    SYNTAX                        CItpTcPointCodeType 
    MAX-ACCESS                    read-create
    STATUS                        current
    DESCRIPTION
            "The function of this point code"
    ::= { cItpSpPointCodeTableEntry 3 }

cItpSpPointCodeDisplay            OBJECT-TYPE
    SYNTAX                        CItpTcDisplayPC 
    MAX-ACCESS                    read-only
    STATUS                        current
    DESCRIPTION
            "The point code for this SP."
    ::= { cItpSpPointCodeTableEntry 4 }

cItpSpPointCodeRowStatus          OBJECT-TYPE
    SYNTAX                        RowStatus
    MAX-ACCESS                    read-create
    STATUS                        current
    DESCRIPTION
            "The object is used by a management station to 
             create or delete the row entry in cItpSpPointCodeTable  
            following the RowStatus textual convention."
    ::= { cItpSpPointCodeTableEntry 5 }


--  *************************************************************
--  *                                                           *
--  * SP - Linkset Table                                        *
--  *                                                           *
--  *************************************************************

cItpSpLinksetTable                OBJECT-TYPE
    SYNTAX                        SEQUENCE OF CItpSpLinksetTableEntry 
    MAX-ACCESS                    not-accessible
    STATUS                        current
    DESCRIPTION
            "A table of linksets for this SP. "
    ::= { cItpSpLinkset  1 }

cItpSpLinksetTableEntry           OBJECT-TYPE
    SYNTAX                        CItpSpLinksetTableEntry 
    MAX-ACCESS                    not-accessible
    STATUS                        current
    DESCRIPTION
            "A list of SP linkset attributes for a particular SP
            entity."
    INDEX   { 
              cItpSpLinksetName }
    ::= { cItpSpLinksetTable  1 }

CItpSpLinksetTableEntry  ::= SEQUENCE {
    cItpSpLinksetName                   CItpTcLinksetId,
    cItpSpLinksetSourcePointCode        CItpTcPointCode,
    cItpSpLinksetSourceDisplayPC        CItpTcDisplayPC,
    cItpSpLinksetAdjacentPointCode      CItpTcPointCode,
    cItpSpLinksetAdjacentDisplayPC      CItpTcDisplayPC,
    cItpSpLinksetState                  INTEGER,
    cItpSpLinksetInboundAcl             CItpTcAclId,
    cItpSpLinksetOutboundAcl            CItpTcAclId,
    cItpSpLinksetSnmmRTN                CItpTcRouteTableName,
    cItpSpLinksetSntmRTN                CItpTcRouteTableName,
    cItpSpLinksetSpare2RTN              CItpTcRouteTableName,
    cItpSpLinksetSccpRTN                CItpTcRouteTableName,
    cItpSpLinksetTupRTN                 CItpTcRouteTableName,
    cItpSpLinksetIsupRTN                CItpTcRouteTableName,
    cItpSpLinksetDupcRTN                CItpTcRouteTableName,
    cItpSpLinksetDupfRTN                CItpTcRouteTableName,
    cItpSpLinksetMtupRTN                CItpTcRouteTableName,
    cItpSpLinksetBisupRTN               CItpTcRouteTableName,
    cItpSpLinksetSisupRTN               CItpTcRouteTableName,
    cItpSpLinksetSpare11RTN             CItpTcRouteTableName,
    cItpSpLinksetSpare12RTN             CItpTcRouteTableName,
    cItpSpLinksetSpare13RTN             CItpTcRouteTableName,
    cItpSpLinksetSpare14RTN             CItpTcRouteTableName,
    cItpSpLinksetSpare15RTN             CItpTcRouteTableName,
    cItpSpLinksetAccountingEnabled      TruthValue,
    cItpSpLinksetNumLinks               Unsigned32,
    cItpSpLinksetDurationInService      TimeTicks, 
    cItpSpLinksetDurationOutService     TimeTicks, -- Q752/4.2
    cItpSpLinksetMtp2T01                CItpTcTimerMtp2T01,
    cItpSpLinksetMtp2T02                CItpTcTimerMtp2T02,
    cItpSpLinksetMtp2T03                CItpTcTimerMtp2T03,
    cItpSpLinksetMtp2T04E               CItpTcTimerMtp2T04E,
    cItpSpLinksetMtp2T04N               CItpTcTimerMtp2T04N,
    cItpSpLinksetMtp2T05                CItpTcTimerMtp2T05,
    cItpSpLinksetMtp2T06                CItpTcTimerMtp2T06,
    cItpSpLinksetMtp2T07                CItpTcTimerMtp2T07,
    cItpSpLinksetMtp3T01                CItpTcTimerMtp3T01,
    cItpSpLinksetMtp3T02                CItpTcTimerMtp3T02,
    cItpSpLinksetMtp3T03                CItpTcTimerMtp3T03,
    cItpSpLinksetMtp3T04                CItpTcTimerMtp3T04,
    cItpSpLinksetMtp3T05                CItpTcTimerMtp3T05,
    cItpSpLinksetMtp3T06                CItpTcTimerMtp3T06,
    cItpSpLinksetMtp3T07                CItpTcTimerMtp3T07,
    cItpSpLinksetMtp3T08                CItpTcTimerMtp3T08,
    cItpSpLinksetMtp3T10                CItpTcTimerMtp3T10,
    cItpSpLinksetMtp3T11                CItpTcTimerMtp3T11,
    cItpSpLinksetMtp3T12                CItpTcTimerMtp3T12,
    cItpSpLinksetMtp3T13                CItpTcTimerMtp3T13,
    cItpSpLinksetMtp3T14                CItpTcTimerMtp3T14,
    cItpSpLinksetMtp3T15                CItpTcTimerMtp3T15,
    cItpSpLinksetMtp3T16                CItpTcTimerMtp3T16,
    cItpSpLinksetMtp3T17                CItpTcTimerMtp3T17,
    cItpSpLinksetMtp3T18                CItpTcTimerMtp3T18,
    cItpSpLinksetMtp3T19                CItpTcTimerMtp3T19,
    cItpSpLinksetMtp3T20                CItpTcTimerMtp3T20,
    cItpSpLinksetMtp3T21                CItpTcTimerMtp3T21,
    cItpSpLinksetMtp3T22                CItpTcTimerMtp3T22,
    cItpSpLinksetMtp3T23                CItpTcTimerMtp3T23,
    cItpSpLinksetMtp3T24                CItpTcTimerMtp3T24,
    cItpSpLinksetMtp3T25                CItpTcTimerMtp3T25,
    cItpSpLinksetMtp3T26                CItpTcTimerMtp3T26,
    cItpSpLinksetMtp3T27                CItpTcTimerMtp3T27,
    cItpSpLinksetMtp3T28                CItpTcTimerMtp3T28,
    cItpSpLinksetMtp3T29                CItpTcTimerMtp3T29,
    cItpSpLinksetMtp3T30                CItpTcTimerMtp3T30,
    cItpSpLinksetMtp3T31                CItpTcTimerMtp3T31,
    cItpSpLinksetMtp3T32                CItpTcTimerMtp3T32,
    cItpSpLinksetMtp3T33                CItpTcTimerMtp3T33,
    cItpSpLinksetMtp3T34                CItpTcTimerMtp3T34,
    cItpSpLinksetTimerLinkTest          CItpTcTimerLinkTest,     
    cItpSpLinksetTimerLinkMessage       CItpTcTimerLinkMessage,  
    cItpSpLinksetTimerLinkActRetry      CItpTcTimerLinkActRetry, 
    cItpSpLinksetPlanCapacity           Integer32, 
    cItpSpLinksetActPriority            Unsigned32,
    cItpSpLinksetType                   INTEGER,
    cItpSpLinksetRowStatus              RowStatus,
    cItpSpLinksetNi                     CItpTcNetworkIndicator,
    cItpSpLinksetDisplayName            SnmpAdminString,
    cItpSpLinksetDescription            SnmpAdminString,
    cItpSpLinksetVariant                CItpTcSs7Variant
    
}

cItpSpLinksetName                 OBJECT-TYPE
    SYNTAX                        CItpTcLinksetId 
    MAX-ACCESS                    not-accessible 
    STATUS                        current
    DESCRIPTION
            "The name of the linkset."
    ::= { cItpSpLinksetTableEntry 1 }
        
cItpSpLinksetSourcePointCode      OBJECT-TYPE
    SYNTAX                        CItpTcPointCode 
    MAX-ACCESS                    read-create
    STATUS                        current
    DESCRIPTION
            "The point code to which this linkset is connected."
    ::= { cItpSpLinksetTableEntry 2 }
        
cItpSpLinksetSourceDisplayPC      OBJECT-TYPE
    SYNTAX                        CItpTcDisplayPC 
    MAX-ACCESS                    read-only
    STATUS                        current
    DESCRIPTION
            "The point code to which this linkset is connected."
    ::= { cItpSpLinksetTableEntry 3 }

cItpSpLinksetAdjacentPointCode    OBJECT-TYPE
    SYNTAX                        CItpTcPointCode 
    MAX-ACCESS                    read-create
    STATUS                        current
    DESCRIPTION
            "The point code to which this linkset is connected."
    ::= { cItpSpLinksetTableEntry 4 }
        
cItpSpLinksetAdjacentDisplayPC    OBJECT-TYPE
    SYNTAX                        CItpTcDisplayPC 
    MAX-ACCESS                    read-only
    STATUS                        current
    DESCRIPTION
            "The point code to which this linkset is connected."
    ::= { cItpSpLinksetTableEntry 5 }

cItpSpLinksetState                OBJECT-TYPE
    SYNTAX                        INTEGER {
                                    available(1),
                                    shutdown(2),
                                    unavailable(3)
    }
    MAX-ACCESS                    read-only
    STATUS                        current
    DESCRIPTION
           "The list of possible linkset states.
            'available'  : Traffic may flow over this linkset
            'shutdown'   : This linkset has been forced to an
                           unavailable state by an administrative
                           action.
            'unavailable': The linkset is currently unable to support
                           traffic. Activation of this linkset will 
                           occur as required by protocol."
    ::= { cItpSpLinksetTableEntry 6 }

cItpSpLinksetInboundAcl           OBJECT-TYPE
    SYNTAX                        CItpTcAclId 
    MAX-ACCESS                    read-create
    STATUS                        current
    DESCRIPTION
            "Packets are filtered against this access control list 
             before they are passed to the routing function.  A
             value of zero indicates that no access control list
             is present."
    ::= { cItpSpLinksetTableEntry 7 }

cItpSpLinksetOutboundAcl          OBJECT-TYPE
    SYNTAX                        CItpTcAclId 
    MAX-ACCESS                    read-create
    STATUS                        current
    DESCRIPTION
            "Packets are filtered against this access control list 
             after they have passed through the routing function.  
             A value of zero indicates that no access control list
             is present."
    ::= { cItpSpLinksetTableEntry 8 }

cItpSpLinksetSnmmRTN              OBJECT-TYPE
    SYNTAX                        CItpTcRouteTableName 
    MAX-ACCESS                    read-create
    STATUS                        current
    DESCRIPTION
            "The routing table for Signalling network management
            messages."
    REFERENCE
            "ITU Q.704 Signalling network functions and messages,
            section 14.2.1."
    ::= { cItpSpLinksetTableEntry 9 }

cItpSpLinksetSntmRTN              OBJECT-TYPE
    SYNTAX                        CItpTcRouteTableName 
    MAX-ACCESS                    read-create
    STATUS                        current
    DESCRIPTION
            "The routing table for Signalling network test and
            maintenance messages."
    REFERENCE
            "ITU Q.704 Signalling network functions and messages,
            section 14.2.1."
    ::= { cItpSpLinksetTableEntry 10 }

cItpSpLinksetSpare2RTN            OBJECT-TYPE
    SYNTAX                        CItpTcRouteTableName 
    MAX-ACCESS                    read-create
    STATUS                        current
    DESCRIPTION
            "This routing table has been defined as a spare
            routing table by the standards committee."
    REFERENCE
            "ITU Q.704 Signalling network functions and messages,
            section 14.2.1."
    ::= { cItpSpLinksetTableEntry 11 }

cItpSpLinksetSccpRTN              OBJECT-TYPE
    SYNTAX                        CItpTcRouteTableName 
    MAX-ACCESS                    read-create
    STATUS                        current
    DESCRIPTION
            "The routing table for SS7 Signalling Connection
            Control Part(SCCP) messages."
    REFERENCE
            "ITU Q.704 Signalling network functions and messages,
            section 14.2.1."
    ::= { cItpSpLinksetTableEntry 12 }

cItpSpLinksetTupRTN               OBJECT-TYPE
    SYNTAX                        CItpTcRouteTableName 
    MAX-ACCESS                    read-create
    STATUS                        current
    DESCRIPTION
            "The routing table for Telephone User Part(TUP) 
             messages."
    REFERENCE
            "ITU Q.704 Signalling network functions and messages,
            section 14.2.1."
    ::= { cItpSpLinksetTableEntry 13 }

cItpSpLinksetIsupRTN              OBJECT-TYPE
    SYNTAX                        CItpTcRouteTableName 
    MAX-ACCESS                    read-create
    STATUS                        current
    DESCRIPTION
            "The routing table for ISDN User Part messages."
    REFERENCE
            "ITU Q.704 Signalling network functions and messages,
            section 14.2.1."
    ::= { cItpSpLinksetTableEntry 14 }

cItpSpLinksetDupcRTN              OBJECT-TYPE
    SYNTAX                        CItpTcRouteTableName 
    MAX-ACCESS                    read-create
    STATUS                        current
    DESCRIPTION
            "The routing table for Data User Part (call and
            circuit-related messages)."
    REFERENCE
            "ITU Q.704 Signalling network functions and messages,
            section 14.2.1."
    ::= { cItpSpLinksetTableEntry 15 }

cItpSpLinksetDupfRTN              OBJECT-TYPE
    SYNTAX                        CItpTcRouteTableName 
    MAX-ACCESS                    read-create
    STATUS                        current
    DESCRIPTION
            "The routing table for Data User Part (facility
            registration and cancellation messages)."
    REFERENCE
            "ITU Q.704 Signalling network functions and messages,
            section 14.2.1."
    ::= { cItpSpLinksetTableEntry 16 }

cItpSpLinksetMtupRTN              OBJECT-TYPE
    SYNTAX                        CItpTcRouteTableName 
    MAX-ACCESS                    read-create
    STATUS                        current
    DESCRIPTION
            "The routing table for MTP Testing User Part
            messages."
    REFERENCE
            "ITU Q.704 Signalling network functions and messages,
            section 14.2.1."
    ::= { cItpSpLinksetTableEntry 17 }

cItpSpLinksetBisupRTN             OBJECT-TYPE
    SYNTAX                        CItpTcRouteTableName 
    MAX-ACCESS                    read-create
    STATUS                        current
    DESCRIPTION
            "The routing table for Broadband ISDN User Part(BISUP)
            messages."
    REFERENCE
            "ITU Q.704 Signalling network functions and messages,
            section 14.2.1."
    ::= { cItpSpLinksetTableEntry 18 }

cItpSpLinksetSisupRTN             OBJECT-TYPE
    SYNTAX                        CItpTcRouteTableName 
    MAX-ACCESS                    read-create
    STATUS                        current
    DESCRIPTION
            "The routing table for Satellite ISDN User Part(SISUP)
            messages."
    REFERENCE
            "ITU Q.704 Signalling network functions and messages,
            section 14.2.1."
    ::= { cItpSpLinksetTableEntry 19 }

cItpSpLinksetSpare11RTN           OBJECT-TYPE
    SYNTAX                        CItpTcRouteTableName 
    MAX-ACCESS                    read-create
    STATUS                        current
    DESCRIPTION
            "This routing table has been defined as a spare
            routing table by the standards committee."
    REFERENCE
            "ITU Q.704 Signalling network functions and messages,
            section 14.2.1."
    ::= { cItpSpLinksetTableEntry 20 }

cItpSpLinksetSpare12RTN           OBJECT-TYPE
    SYNTAX                        CItpTcRouteTableName 
    MAX-ACCESS                    read-create
    STATUS                        current
    DESCRIPTION
            "This routing table has been defined as a spare
            routing table by the standards committee."
    REFERENCE
            "ITU Q.704 Signalling network functions and messages,
            section 14.2.1."
    ::= { cItpSpLinksetTableEntry 21 }

cItpSpLinksetSpare13RTN           OBJECT-TYPE
    SYNTAX                        CItpTcRouteTableName 
    MAX-ACCESS                    read-create
    STATUS                        current
    DESCRIPTION
            "This routing table has been defined as a spare
            routing table by the standards committee."
    REFERENCE
            "ITU Q.704 Signalling network functions and messages,
            section 14.2.1."
    ::= { cItpSpLinksetTableEntry 22 }

cItpSpLinksetSpare14RTN           OBJECT-TYPE
    SYNTAX                        CItpTcRouteTableName 
    MAX-ACCESS                    read-create
    STATUS                        current
    DESCRIPTION
            "This routing table has been defined as a spare
            routing table by the standards committee."
    REFERENCE
            "ITU Q.704 Signalling network functions and messages,
            section 14.2.1."
    ::= { cItpSpLinksetTableEntry 23 }

cItpSpLinksetSpare15RTN           OBJECT-TYPE
    SYNTAX                        CItpTcRouteTableName 
    MAX-ACCESS                    read-create
    STATUS                        current
    DESCRIPTION
            "This routing table has been defined as a spare
            routing table by the standards committee."
    REFERENCE
            "ITU Q.704 Signalling network functions and messages,
            section 14.2.1."
    ::= { cItpSpLinksetTableEntry 24 }

cItpSpLinksetAccountingEnabled    OBJECT-TYPE
    SYNTAX                        TruthValue
    MAX-ACCESS                    read-create
    STATUS                        current
    DESCRIPTION 
            "This indicates if accounting for this linkset is
            enabled.

            'true'  Indicates that the accounting function is
                    enabled for this linkset and is being
                    accumulated in cItpSpAccountingTable.

            'false' Indicates that the accounting function is 
                    disabled."
    DEFVAL { false }
    ::= { cItpSpLinksetTableEntry 25 }

cItpSpLinksetNumLinks             OBJECT-TYPE
    SYNTAX                        Unsigned32
    MAX-ACCESS                    read-only
    STATUS                        current
    DESCRIPTION
            "The number of links in this linkset."
    ::= { cItpSpLinksetTableEntry 26 }

cItpSpLinksetDurationInService    OBJECT-TYPE
    SYNTAX                        TimeTicks
    MAX-ACCESS                    read-only
    STATUS                        current
    DESCRIPTION
         "Time linkset was providing service related to 
          Q752/Table 4.2."

    ::= { cItpSpLinksetTableEntry 27 }

cItpSpLinksetDurationOutService   OBJECT-TYPE
    SYNTAX                        TimeTicks
    MAX-ACCESS                    read-only
    STATUS                        current
    DESCRIPTION
         "Time linkset was Out-of-Service as required for 
          Q752/Table 4.2."

    ::= { cItpSpLinksetTableEntry 28 }

cItpSpLinksetMtp2T01              OBJECT-TYPE
    SYNTAX                        CItpTcTimerMtp2T01  
    UNITS                         "milliseconds"
    MAX-ACCESS                    read-create
    STATUS                        current
    DESCRIPTION
            "Alignment ready timer." 
    ::= { cItpSpLinksetTableEntry 29 }

cItpSpLinksetMtp2T02              OBJECT-TYPE
    SYNTAX                        CItpTcTimerMtp2T02  
    UNITS                         "milliseconds"
    MAX-ACCESS                    read-create
    STATUS                        current
    DESCRIPTION
            "Not aligned timer."
    ::= { cItpSpLinksetTableEntry 30 }

cItpSpLinksetMtp2T03              OBJECT-TYPE
    SYNTAX                        CItpTcTimerMtp2T03
    UNITS                         "milliseconds"
    MAX-ACCESS                    read-create
    STATUS                        current
    DESCRIPTION
            "Aligned timer."
    ::= { cItpSpLinksetTableEntry 31 }

cItpSpLinksetMtp2T04E             OBJECT-TYPE
    SYNTAX                        CItpTcTimerMtp2T04E
    UNITS                         "milliseconds"
    MAX-ACCESS                    read-create
    STATUS                        current   
    DESCRIPTION
            "Proving period timer emergency timer. "
    ::= { cItpSpLinksetTableEntry 32 }

cItpSpLinksetMtp2T04N             OBJECT-TYPE
    SYNTAX                        CItpTcTimerMtp2T04N
    UNITS                         "milliseconds"
    MAX-ACCESS                    read-create
    STATUS                        current
    DESCRIPTION
            "Proving period timer normal timer."
    ::= { cItpSpLinksetTableEntry 33 }

cItpSpLinksetMtp2T05              OBJECT-TYPE
    SYNTAX                        CItpTcTimerMtp2T05
    UNITS                         "milliseconds"
    MAX-ACCESS                    read-create
    STATUS                        current
    DESCRIPTION
            "Sending SIB timer."
    ::= { cItpSpLinksetTableEntry 34 }

cItpSpLinksetMtp2T06              OBJECT-TYPE
    SYNTAX                        CItpTcTimerMtp2T06
    UNITS                         "milliseconds"
    MAX-ACCESS                    read-create
    STATUS                        current
    DESCRIPTION
            "Remote congestion timer. "
    ::= { cItpSpLinksetTableEntry 35 }

cItpSpLinksetMtp2T07              OBJECT-TYPE
    SYNTAX                        CItpTcTimerMtp2T07
    UNITS                         "milliseconds"
    MAX-ACCESS                    read-create
    STATUS                        current
    DESCRIPTION
            "Excessive delay of acknowledgement timer."
    ::= { cItpSpLinksetTableEntry 36 }

cItpSpLinksetMtp3T01              OBJECT-TYPE
    SYNTAX                        CItpTcTimerMtp3T01
    UNITS                         "milliseconds"
    MAX-ACCESS                    read-create
    STATUS                        current
    DESCRIPTION
            "Delay to avoid message mis-sequencing on changeover."
    ::= { cItpSpLinksetTableEntry 37 }

cItpSpLinksetMtp3T02              OBJECT-TYPE
    SYNTAX                        CItpTcTimerMtp3T02
    UNITS                         "milliseconds"
    MAX-ACCESS                    read-create
    STATUS                        current
    DESCRIPTION
            "Waiting for changeover acknowledgement."
    ::= { cItpSpLinksetTableEntry 38 }

cItpSpLinksetMtp3T03              OBJECT-TYPE
    SYNTAX                        CItpTcTimerMtp3T03
    UNITS                         "milliseconds"
    MAX-ACCESS                    read-create
    STATUS                        current
    DESCRIPTION
            "Time controlled diversion-delay to avoid
            mis-sequencing on change back."
    ::= { cItpSpLinksetTableEntry 39 }

cItpSpLinksetMtp3T04              OBJECT-TYPE
    SYNTAX                        CItpTcTimerMtp3T04
    UNITS                         "milliseconds"
    MAX-ACCESS                    read-create
    STATUS                        current
    DESCRIPTION
            "Waiting for change back acknowledgement (first
            attempt)."
    ::= { cItpSpLinksetTableEntry 40 }

cItpSpLinksetMtp3T05              OBJECT-TYPE
    SYNTAX                        CItpTcTimerMtp3T05
    UNITS                         "milliseconds"
    MAX-ACCESS                    read-create
    STATUS                        current
    DESCRIPTION
            "Waiting for change back acknowledgement (second
             attempt)."
    ::= { cItpSpLinksetTableEntry 41 }

cItpSpLinksetMtp3T06              OBJECT-TYPE
    SYNTAX                        CItpTcTimerMtp3T06
    UNITS                         "milliseconds"
    MAX-ACCESS                    read-create
    STATUS                        current
    DESCRIPTION
            "Delay to avoid message mis-sequencing on controlled
             rerouting."
    ::= { cItpSpLinksetTableEntry 42 }

cItpSpLinksetMtp3T07              OBJECT-TYPE
    SYNTAX                        CItpTcTimerMtp3T07
    UNITS                         "milliseconds"
    MAX-ACCESS                    read-create
    STATUS                        current
    DESCRIPTION
            "Waiting for Signalling data link connection
             acknowledgement."
    ::= { cItpSpLinksetTableEntry 43 }
            
cItpSpLinksetMtp3T08              OBJECT-TYPE
    SYNTAX                        CItpTcTimerMtp3T08
    UNITS                         "milliseconds"
    MAX-ACCESS                    read-create
    STATUS                        current
    DESCRIPTION
            "Transfer prohibited inhibition timer (transient
             solution)."
    ::= { cItpSpLinksetTableEntry 44 }

cItpSpLinksetMtp3T10              OBJECT-TYPE
    SYNTAX                        CItpTcTimerMtp3T10
    UNITS                         "milliseconds"
    MAX-ACCESS                    read-create
    STATUS                        current
    DESCRIPTION
            "Waiting to repeat Signalling routeset test message."
    ::= { cItpSpLinksetTableEntry 45 }

cItpSpLinksetMtp3T11              OBJECT-TYPE
    SYNTAX                        CItpTcTimerMtp3T11
    UNITS                         "milliseconds"
    MAX-ACCESS                    read-create
    STATUS                        current
    DESCRIPTION
            "Transfer restricted timer. (This is one way of
            implementing the function described in 13.4/Q.704 and
            mainly intended to simplify SPs.)."
    ::= { cItpSpLinksetTableEntry 46 }

cItpSpLinksetMtp3T12              OBJECT-TYPE
    SYNTAX                        CItpTcTimerMtp3T12
    UNITS                         "milliseconds"
    MAX-ACCESS                    read-create
    STATUS                        current
    DESCRIPTION
            "Waiting for uninhibit acknowledgement."
    ::= { cItpSpLinksetTableEntry 47 }

cItpSpLinksetMtp3T13              OBJECT-TYPE
    SYNTAX                        CItpTcTimerMtp3T13
    UNITS                         "milliseconds"
    MAX-ACCESS                    read-create
    STATUS                        current
    DESCRIPTION
            "Waiting for force uninhibit."
    ::= { cItpSpLinksetTableEntry 48 }

cItpSpLinksetMtp3T14              OBJECT-TYPE
    SYNTAX                        CItpTcTimerMtp3T14
    UNITS                         "milliseconds"
    MAX-ACCESS                    read-create
    STATUS                        current
    DESCRIPTION
            "Waiting for inhibition acknowledgement."
    ::= { cItpSpLinksetTableEntry 49 }

cItpSpLinksetMtp3T15              OBJECT-TYPE
    SYNTAX                        CItpTcTimerMtp3T15
    UNITS                         "milliseconds"
    MAX-ACCESS                    read-create
    STATUS                        current
    DESCRIPTION
            "Waiting to start Signalling routeset congestion
             test."
    ::= { cItpSpLinksetTableEntry 50 }

cItpSpLinksetMtp3T16              OBJECT-TYPE
    SYNTAX                        CItpTcTimerMtp3T16
    UNITS                         "milliseconds"
    MAX-ACCESS                    read-create
    STATUS                        current
    DESCRIPTION
            "Waiting for routeset congestion status update."
    ::= { cItpSpLinksetTableEntry 51 }

cItpSpLinksetMtp3T17              OBJECT-TYPE
    SYNTAX                        CItpTcTimerMtp3T17
    UNITS                         "milliseconds"
    MAX-ACCESS                    read-create
    STATUS                        current
    DESCRIPTION
            "Delay to avoid oscillation of initial alignment
            failure and link restart."
    ::= { cItpSpLinksetTableEntry 52 }

cItpSpLinksetMtp3T18              OBJECT-TYPE
    SYNTAX                        CItpTcTimerMtp3T18
    UNITS                         "milliseconds"
    MAX-ACCESS                    read-create
    STATUS                        current
    DESCRIPTION
            "This timers servers different function based on the 
             variant.
             
             ANSI: Repeat TFR once by response method
             ITU:  MTP restart link supervision"
    ::= { cItpSpLinksetTableEntry 53 }

cItpSpLinksetMtp3T19              OBJECT-TYPE
    SYNTAX                        CItpTcTimerMtp3T19
    UNITS                         "milliseconds"
    MAX-ACCESS                    read-create
    STATUS                        current
    DESCRIPTION
            "This timers servers different function based on the 
             variant.
             
             ANSI: failed craft timer referral timer
             ITU:  supervision timer during MTP restart"
    ::= { cItpSpLinksetTableEntry 54 }

cItpSpLinksetMtp3T20              OBJECT-TYPE
    SYNTAX                        CItpTcTimerMtp3T20
    UNITS                         "milliseconds"
    MAX-ACCESS                    read-create
    STATUS                        current
    DESCRIPTION
            "This timers servers different function based on the 
             variant.
             
             ANSI: waiting to repeat local inhibit test
             ITU:  MTP restart timer at the Signalling point"
    ::= { cItpSpLinksetTableEntry 55 }

cItpSpLinksetMtp3T21              OBJECT-TYPE
    SYNTAX                        CItpTcTimerMtp3T21
    UNITS                         "milliseconds"
    MAX-ACCESS                    read-create
    STATUS                        current
    DESCRIPTION
            "This timers servers different function based on the 
             variant.
             
             ANSI: waiting to repeat remote inhibit test)       
             ITU:  MTP restart timer at adjacent Signalling point"
    ::= { cItpSpLinksetTableEntry 56 }

cItpSpLinksetMtp3T22              OBJECT-TYPE
    SYNTAX                        CItpTcTimerMtp3T22
    UNITS                         "milliseconds"
    MAX-ACCESS                    read-create
    STATUS                        current
    DESCRIPTION
            "This timers servers different function based on the 
             variant.
             
             ANSI: restarting SP waiting for Signalling links avail
             ITU:  local inhibit test timer" 
    ::= { cItpSpLinksetTableEntry 57 }

cItpSpLinksetMtp3T23              OBJECT-TYPE
    SYNTAX                        CItpTcTimerMtp3T23  
    UNITS                         "milliseconds"
    MAX-ACCESS                    read-create
    STATUS                        current
    DESCRIPTION
            "This timers servers different function based on the 
             variant.
             
             ANSI: restarting SP waiting to receive all TRA msgs
             ITU:  remote inhibit test timer"
    ::= { cItpSpLinksetTableEntry 58 }

cItpSpLinksetMtp3T24              OBJECT-TYPE
    SYNTAX                        CItpTcTimerMtp3T24
    UNITS                         "milliseconds"
    MAX-ACCESS                    read-create
    STATUS                        current
    DESCRIPTION
            "This timers servers different function based on the 
             variant.
             
             ANSI: restarting SP waiting to broadcast all TRA msgs
             ITU:  stabilizing timer after local processor outage"
    ::= { cItpSpLinksetTableEntry 59 }

cItpSpLinksetMtp3T25              OBJECT-TYPE
    SYNTAX                        CItpTcTimerMtp3T25
    UNITS                         "milliseconds"
    MAX-ACCESS                    read-create
    STATUS                        current
    DESCRIPTION
            "Timer at Signalling Point (SP) adjacent to restarting
            SP, waiting for traffic restart allowed message."
    ::= { cItpSpLinksetTableEntry 60 }

cItpSpLinksetMtp3T26              OBJECT-TYPE
    SYNTAX                        CItpTcTimerMtp3T26
    UNITS                         "milliseconds"
    MAX-ACCESS                    read-create
    STATUS                        current
    DESCRIPTION
            "Timer at restarting SP waiting to repeat traffic
            restart waiting message."
    ::= { cItpSpLinksetTableEntry 61 }

cItpSpLinksetMtp3T27              OBJECT-TYPE
    SYNTAX                        CItpTcTimerMtp3T27
    UNITS                         "milliseconds"
    MAX-ACCESS                    read-create
    STATUS                        current
    DESCRIPTION
            "Minimum duration of unavailability for full restart."
    ::= { cItpSpLinksetTableEntry 62 }

cItpSpLinksetMtp3T28              OBJECT-TYPE
    SYNTAX                        CItpTcTimerMtp3T28
    UNITS                         "milliseconds"
    MAX-ACCESS                    read-create
    STATUS                        current
    DESCRIPTION
            "Timer at SP adjacent to restarting SP waiting for
            traffic restart waiting message."
    ::= { cItpSpLinksetTableEntry 63 }

cItpSpLinksetMtp3T29              OBJECT-TYPE
    SYNTAX                        CItpTcTimerMtp3T29
    UNITS                         "milliseconds"
    MAX-ACCESS                    read-create
    STATUS                        current
    DESCRIPTION
            "Timer started when TRA sent in response to unexpected
            TRA or TRW."
    ::= { cItpSpLinksetTableEntry 64 }

cItpSpLinksetMtp3T30              OBJECT-TYPE
    SYNTAX                        CItpTcTimerMtp3T30
    UNITS                         "milliseconds"
    MAX-ACCESS                    read-create
    STATUS                        current
    DESCRIPTION
            "Timer to limit sending of TFPs and TFRs in response
            to unexpected TRA or TRW."
    ::= { cItpSpLinksetTableEntry 65 }

cItpSpLinksetMtp3T31              OBJECT-TYPE
    SYNTAX                        CItpTcTimerMtp3T31
    UNITS                         "milliseconds"
    MAX-ACCESS                    read-create
    STATUS                        current
    DESCRIPTION
            "False link congestion detection timer."
    ::= { cItpSpLinksetTableEntry 66 }

cItpSpLinksetMtp3T32              OBJECT-TYPE
    SYNTAX                        CItpTcTimerMtp3T32
    UNITS                         "milliseconds"
    MAX-ACCESS                    read-create
    STATUS                        current
    DESCRIPTION
            "Link oscillation timer - Procedure A."
    ::= { cItpSpLinksetTableEntry 67 }

cItpSpLinksetMtp3T33              OBJECT-TYPE
    SYNTAX                        CItpTcTimerMtp3T33 
    UNITS                         "milliseconds"
    MAX-ACCESS                    read-create
    STATUS                        current
    DESCRIPTION
            "Probation timer for link oscillation - Procedure B."
    ::= { cItpSpLinksetTableEntry 68 }

cItpSpLinksetMtp3T34              OBJECT-TYPE
    SYNTAX                        CItpTcTimerMtp3T34
    UNITS                         "milliseconds"
    MAX-ACCESS                    read-create
    STATUS                        current
    DESCRIPTION
            "Suspension timer for link oscillation - Procedure B."
    ::= { cItpSpLinksetTableEntry 69 }

cItpSpLinksetTimerLinkTest        OBJECT-TYPE  
    SYNTAX                        CItpTcTimerLinkTest  
    UNITS                         "milliseconds"
    MAX-ACCESS                    read-create
    STATUS                        current
    DESCRIPTION
            "Signalling Link test acknowledgement timer."
    ::= { cItpSpLinksetTableEntry 70 }

cItpSpLinksetTimerLinkMessage     OBJECT-TYPE
    SYNTAX                        CItpTcTimerLinkMessage  
    UNITS                         "milliseconds"
    MAX-ACCESS                    read-create
    STATUS                        current
    DESCRIPTION
            "Interval timer for sending test messages."
    ::= { cItpSpLinksetTableEntry 71 }
        
cItpSpLinksetTimerLinkActRetry    OBJECT-TYPE
    SYNTAX                        CItpTcTimerLinkActRetry  
    UNITS                         "milliseconds"
    MAX-ACCESS                    read-create
    STATUS                        current
    DESCRIPTION
            "Link activation retry timer."
    ::= { cItpSpLinksetTableEntry 72 }
             
cItpSpLinksetPlanCapacity         OBJECT-TYPE
    SYNTAX                        Integer32 (0 | 56000..2147483647)
    UNITS                         "bps"
    MAX-ACCESS                    read-create
    STATUS                        deprecated 
    DESCRIPTION
         "An estimate of the number of bits per second that is
          expected to be transmitted over a linkset.  This 
          attribute will be used by network management stations
          to generate traps and maintain statistics on linksets
          based on Stream Control Transmission Protocol. 
          The information for this attribute is specified via 
          CLI by the system administrator. A value of zero 
          for this object indicates that a planning capacity
          has not been specified. 
          
          This objects has been deprecated and replaced by 
          cItpSpLinkPlanCapacityRcvd and 
          cItpSpLinkPlanCapacitySent objects.
          " 
    ::= { cItpSpLinksetTableEntry 73 }
     
cItpSpLinksetActPriority          OBJECT-TYPE
    SYNTAX                        Unsigned32 (0..255) 
    MAX-ACCESS                    read-create
    STATUS                        current
    DESCRIPTION
          "Defines the activation priority for linksets. Each 
           linkset can be defined a priority. The linkset with
           the lowest values will be activated first.  If two 
           linksets share the same values they will be 
           activated in the order they were defined." 
     ::= { cItpSpLinksetTableEntry 74 }
     
cItpSpLinksetType                 OBJECT-TYPE
    SYNTAX INTEGER {
            access(1),
            bridge(2),
            cross(3),
            diagonal(4),
            fullyAssoc(5)
    }
    MAX-ACCESS                   read-create
    STATUS                       current
    DESCRIPTION
           "The list of possible Signalling link types.  All links
            in the same linkset will be of the same type.
           'A-link'     : Access link
           'B-link'     : Bridge link
           'C-link'     : Cross link
           'D-link'     : Diagonal link
           'E-link'     : Fully associated link"
      ::= { cItpSpLinksetTableEntry 75 }
      
cItpSpLinksetRowStatus            OBJECT-TYPE
    SYNTAX                        RowStatus
    MAX-ACCESS                    read-create
    STATUS                        current
    DESCRIPTION                   
         "The object is used by a management station to 
          create or delete the row entry in cItpSpLinksetTable  
          following the RowStatus textual convention."
      ::= { cItpSpLinksetTableEntry 76 }
      
cItpSpLinksetNi                   OBJECT-TYPE
    SYNTAX                        CItpTcNetworkIndicator
    MAX-ACCESS                    read-create
    STATUS                        current
    DESCRIPTION                   
         "The Network Indicator in which the Linkset resides." 
      ::= { cItpSpLinksetTableEntry 77 }
      
cItpSpLinksetDisplayName         OBJECT-TYPE
    SYNTAX                       SnmpAdminString ( SIZE ( 0..30 ) )
    MAX-ACCESS                   read-create
    STATUS                       current
    DESCRIPTION
            "A short identifier for each linkset.
             This value can be set by system administrator
             or defaults to the linkset name."
    ::= { cItpSpLinksetTableEntry 78 }

cItpSpLinksetDescription         OBJECT-TYPE
       SYNTAX                    SnmpAdminString ( SIZE ( 0..254 ) )
       MAX-ACCESS                read-create
       STATUS                    current
       DESCRIPTION
               "A textual description for the Signalling point."
      ::= { cItpSpLinksetTableEntry 79 }

cItpSpLinksetVariant             OBJECT-TYPE
    SYNTAX                       CItpTcSs7Variant 
    MAX-ACCESS                   read-create
    STATUS                       current
    DESCRIPTION
            "The SS7 variant used to format data transmitted 
             on this linkset."
      ::= { cItpSpLinksetTableEntry 80 }
      
      
--  *************************************************************
--  *                                                           *
--  * SP - Link Table                                           *
--  *                                                           *
--  *************************************************************

cItpSpLinkTable                   OBJECT-TYPE
    SYNTAX                        SEQUENCE OF CItpSpLinkTableEntry 
    MAX-ACCESS                    not-accessible
    STATUS                        current
    DESCRIPTION
            "A table of SP links for this SP." 
    ::= { cItpSpLink  1 }

cItpSpLinkTableEntry              OBJECT-TYPE
    SYNTAX                        CItpSpLinkTableEntry 
    MAX-ACCESS                    not-accessible
    STATUS                        current
    DESCRIPTION
            "A list of SP link attributes."
    INDEX   {
              cItpSpLinksetName, -- shared index
              cItpSpLinkSlc 
    }
    ::= { cItpSpLinkTable  1 }

CItpSpLinkTableEntry  ::= SEQUENCE {
    cItpSpLinkSlc                      CItpTcLinkSLC,
    cItpSpLinkDescription              SnmpAdminString,
    cItpSpLinkState                    INTEGER,
    cItpSpLinkType                     CItpTcLinkType,
    cItpSpLinkifIndex                  InterfaceIndexOrZero,
    cItpSpLinkSctpAssociation          Integer32,
    cItpSpLinkMtp3PacketsRcvd          Counter32,
    cItpSpLinkMtp3PacketsSent          Counter32,
    cItpSpLinkMtp3BytesRcvd            Counter32,
    cItpSpLinkMtp3BytesSent            Counter32,
    cItpSpLinkMtp2T01                  CItpTcTimerMtp2T01,
    cItpSpLinkMtp2T02                  CItpTcTimerMtp2T02,
    cItpSpLinkMtp2T03                  CItpTcTimerMtp2T03,
    cItpSpLinkMtp2T04E                 CItpTcTimerMtp2T04E,
    cItpSpLinkMtp2T04N                 CItpTcTimerMtp2T04N,
    cItpSpLinkMtp2T05                  CItpTcTimerMtp2T05,
    cItpSpLinkMtp2T06                  CItpTcTimerMtp2T06,
    cItpSpLinkMtp2T07                  CItpTcTimerMtp2T07,
    cItpSpLinkMtp3T01                  CItpTcTimerMtp3T01,
    cItpSpLinkMtp3T02                  CItpTcTimerMtp3T02,
    cItpSpLinkMtp3T03                  CItpTcTimerMtp3T03,
    cItpSpLinkMtp3T04                  CItpTcTimerMtp3T04,
    cItpSpLinkMtp3T05                  CItpTcTimerMtp3T05,
    cItpSpLinkMtp3T06                  CItpTcTimerMtp3T06,
    cItpSpLinkMtp3T07                  CItpTcTimerMtp3T07,
    cItpSpLinkMtp3T08                  CItpTcTimerMtp3T08,
    cItpSpLinkMtp3T10                  CItpTcTimerMtp3T10,
    cItpSpLinkMtp3T11                  CItpTcTimerMtp3T11,
    cItpSpLinkMtp3T12                  CItpTcTimerMtp3T12,
    cItpSpLinkMtp3T13                  CItpTcTimerMtp3T13,
    cItpSpLinkMtp3T14                  CItpTcTimerMtp3T14,
    cItpSpLinkMtp3T15                  CItpTcTimerMtp3T15,
    cItpSpLinkMtp3T16                  CItpTcTimerMtp3T16,
    cItpSpLinkMtp3T17                  CItpTcTimerMtp3T17,
    cItpSpLinkMtp3T18                  CItpTcTimerMtp3T18,
    cItpSpLinkMtp3T19                  CItpTcTimerMtp3T19,
    cItpSpLinkMtp3T20                  CItpTcTimerMtp3T20,
    cItpSpLinkMtp3T21                  CItpTcTimerMtp3T21,
    cItpSpLinkMtp3T22                  CItpTcTimerMtp3T22,
    cItpSpLinkMtp3T23                  CItpTcTimerMtp3T23,
    cItpSpLinkMtp3T24                  CItpTcTimerMtp3T24,
    cItpSpLinkMtp3T25                  CItpTcTimerMtp3T25,
    cItpSpLinkMtp3T26                  CItpTcTimerMtp3T26,
    cItpSpLinkMtp3T27                  CItpTcTimerMtp3T27,
    cItpSpLinkMtp3T28                  CItpTcTimerMtp3T28,
    cItpSpLinkMtp3T29                  CItpTcTimerMtp3T29,
    cItpSpLinkMtp3T30                  CItpTcTimerMtp3T30,
    cItpSpLinkMtp3T31                  CItpTcTimerMtp3T31,
    cItpSpLinkMtp3T32                  CItpTcTimerMtp3T32,
    cItpSpLinkMtp3T33                  CItpTcTimerMtp3T33,
    cItpSpLinkMtp3T34                  CItpTcTimerMtp3T34,
    cItpSpLinkTimerLinkTest            CItpTcTimerLinkTest,     
    cItpSpLinkTimerLinkMessage         CItpTcTimerLinkMessage,  
    cItpSpLinkTimerLinkActRetry        CItpTcTimerLinkActRetry, 
    cItpSpLinkXmitQueueDepth           Gauge32,
    cItpSpLinkXmitQueueDepthHigh       Unsigned32,
    cItpSpLinkXmitQueueDepthHighRT     TimeStamp,
    cItpSpLinkCongestionState          Unsigned32,
    cItpSpLinkCongestionAbate1         Unsigned32,
    cItpSpLinkCongestionAbate2         Unsigned32,
    cItpSpLinkCongestionAbate3         Unsigned32,
    cItpSpLinkCongestionOnset1         Unsigned32,
    cItpSpLinkCongestionOnset2         Unsigned32,
    cItpSpLinkCongestionOnset3         Unsigned32,
    cItpSpLinkSigLinkTest              TruthValue,
    cItpSpLinkQ752T1E1                 TimeTicks, 
    cItpSpLinkQ752T1E2                 Counter32,
    cItpSpLinkQ752T1E3                 Counter32,
    cItpSpLinkQ752T1E4                 Counter32,
    cItpSpLinkQ752T1E5                 Counter32,
    cItpSpLinkQ752T1E6                 Counter32,
    cItpSpLinkQ752T1E7                 Counter32, 
    cItpSpLinkQ752T1E8                 Counter32, 
    cItpSpLinkQ752T1E9                 Counter32,
    cItpSpLinkQ752T1E10                Counter32,
    cItpSpLinkQ752T1E11                Counter32,
    cItpSpLinkQ752T2E1                 TimeTicks, 
    cItpSpLinkQ752T2E5                 TimeTicks,  
    cItpSpLinkQ752T2E6                 TimeTicks,  
    cItpSpLinkQ752T2E7                 TimeTicks,  
    cItpSpLinkQ752T2E9                 TimeTicks,  
    cItpSpLinkQ752T2E10                Counter32,
    cItpSpLinkQ752T2E15                TimeTicks,  
    cItpSpLinkQ752T2E16                Counter32,
    cItpSpLinkQ752T2E18                Counter32,
    cItpSpLinkMtp3PacketsRetrans       Counter32, -- Q752/3.2
    cItpSpLinkMtp3BytesRetrans         Counter32, -- Q752/3.2
    cItpSpLinkQ752T3E6                 Counter32, 
    cItpSpLinkQ752T3E7                 TimeTicks, 
    cItpSpLinkQ752T3E10L1              Counter32, 
    cItpSpLinkQ752T3E10L2              Counter32, 
    cItpSpLinkQ752T3E10L3              Counter32, 
    cItpSpLinkQ752T3E11L1              Counter32, 
    cItpSpLinkQ752T3E11L2              Counter32, 
    cItpSpLinkQ752T3E11L3              Counter32,
    cItpSpLinkIPType1                  InetAddressType,
    cItpSpLinkIPType2                  InetAddressType,
    cItpSpLinkIPType3                  InetAddressType,
    cItpSpLinkIPType4                  InetAddressType,
    cItpSpLinkIPAddr1                  InetAddress,
    cItpSpLinkIPAddr2                  InetAddress,
    cItpSpLinkIPAddr3                  InetAddress,
    cItpSpLinkIPAddr4                  InetAddress,
    cItpSpLinkLocalPort                Unsigned32,
    cItpSpLinkRemotePort               Unsigned32,
    cItpSpLinkQosClass                 CItpTcQos,
    cItpSpLinkRowStatus                RowStatus,
    cItpSpLinkStateReason              BITS,
    cItpSpLinkDisplayName              SnmpAdminString,
    cItpSpLinkDroppedPkts              Counter32,
    cItpSpLinkTransmittedLssu          Counter32,
    cItpSpLinkReceivedLssu             Counter32,
    cItpSpLinkProtocolDetails          BITS,
    cItpSpLinkLsacState                INTEGER,
    cItpSpLinkTsrcState                INTEGER, 
    cItpSpLinkTcocState                INTEGER, 
    cItpSpLinkTcocLocalBSNT            CItpSpSequenceNumber,
    cItpSpLinkTcocRemoteBSNT           CItpSpSequenceNumber,
    cItpSpLinkTcbcState                INTEGER,
    cItpSpLinkReceivedSIB              Counter32, 
    cItpSpLinkTransmittedSIB           Counter32,
    cItpSpLinkMtp2ExpiredT01           Counter32,
    cItpSpLinkMtp2ExpiredT02           Counter32,
    cItpSpLinkMtp2ExpiredT03           Counter32,
    cItpSpLinkMtp2ExpiredT04           Counter32,
    cItpSpLinkMtp2ExpiredT05           Counter32,
    cItpSpLinkMtp2ExpiredT06           Counter32,
    cItpSpLinkMtp2ExpiredT07           Counter32,
    cItpSpLinkOMAERMCount              Counter32,
    cItpSpLinkOMAERMFailCount          Counter32,
    cItpSpLinkOMSURMCount              Counter32,
    cItpSpLinkOMSURMFailCount          Counter32,
    cItpSpLinkPlanCapacityRcvd         CItpSpLinkCapacity,
    cItpSpLinkUtilThresholdRcvd        CItpSpPercentThreshold,
    cItpSpLinkUtilizationRcvd          CItpSpLinkUtilization,
    cItpSpLinkUtilStateRcvd            CItpSpLinkUtilizationState,
    cItpSpLinkL2BytesRcvd              Counter32,
    cItpSpLinkPlanCapacitySent         CItpSpLinkCapacity,
    cItpSpLinkUtilThresholdSent        CItpSpPercentThreshold,
    cItpSpLinkUtilizationSent          CItpSpLinkUtilization,
    cItpSpLinkUtilStateSent            CItpSpLinkUtilizationState,
    cItpSpLinkL2BytesSent              Counter32
}

cItpSpLinkSlc                     OBJECT-TYPE
    SYNTAX                        CItpTcLinkSLC
    MAX-ACCESS                    not-accessible 
    STATUS                        current
    DESCRIPTION
            "The Signalling Link Code for this link."
    REFERENCE
            "ITU Q.704 Signalling network functions and messages.
            ANSI T1.111 Telecommunications - Signalling system
            No. 7 (SS7)-Message Transfer Part (MTP)."
    ::= { cItpSpLinkTableEntry  1 }

cItpSpLinkDescription             OBJECT-TYPE
    SYNTAX                        SnmpAdminString (SIZE(0..254))
    MAX-ACCESS                    read-create
    STATUS                        current
    DESCRIPTION
            "A textual description for this link."
    ::= { cItpSpLinkTableEntry  2 }
    
cItpSpLinkState                   OBJECT-TYPE
    SYNTAX                        INTEGER {
                                    available(1),
                                    failed(2),
                                    shutdown(3),
                                    unavailable(4)
    }
    MAX-ACCESS                    read-only
    STATUS                        current
    DESCRIPTION
           "The list of possible links states.
            'available'  : Traffic may flow over this linkset
            'failed'     : Traffic management has detected a failure
                           that prevents activating this linkset. 
            'shutdown'   : This linkset has been forced to an
                           unavailable state by an administrative
                           action.
            'unavailable': The linkset is currently unable to support
                           traffic. Activation of this linkset will 
                           occur as required by protocol."
    
    ::= { cItpSpLinkTableEntry  3 }

cItpSpLinkType                    OBJECT-TYPE
    SYNTAX                        CItpTcLinkType 
    MAX-ACCESS                    read-create
    STATUS                        current
    DESCRIPTION
            "The link type."
    REFERENCE "For SCTP see RFC 2960."
    ::= { cItpSpLinkTableEntry  4 }

cItpSpLinkifIndex                 OBJECT-TYPE
    SYNTAX                        InterfaceIndexOrZero
    MAX-ACCESS                    read-create
    STATUS                        current
    DESCRIPTION
           "If the link type specified by cItpSpLinkType is serial 
            or hsl, this is the ifIndex specified in IF-MIB, 
            otherwise no significance is to be placed on this value."
    REFERENCE "RFC1213.txt"
    ::= { cItpSpLinkTableEntry  5 }

cItpSpLinkSctpAssociation         OBJECT-TYPE
    SYNTAX                        Integer32 (0..65535) 
    MAX-ACCESS                    read-only
    STATUS                        current
    DESCRIPTION
           "If the link type specified by cItpSpLinkType is 'sctpIp',
            this is the association identifier defined in the  
            Stream Control Transmission Protocol(SCTP) MIB.
            Where value greater than zero indicates
            a valid association and zero one indicates an 
            invalid association. This value will always be set to 
            zero one when cItpSpLinkType is not equal to the 
            'sctpIp' value."
            
    ::= { cItpSpLinkTableEntry  6 }

cItpSpLinkMtp3PacketsRcvd         OBJECT-TYPE
    SYNTAX                        Counter32
    UNITS                         "packets"
    MAX-ACCESS                    read-only
    STATUS                        current
    DESCRIPTION
            "The number of MTP3 packets received by this link.
            This measurement is specified in Q752/3.5"
    ::= { cItpSpLinkTableEntry  7 }

cItpSpLinkMtp3PacketsSent         OBJECT-TYPE
    SYNTAX                        Counter32
    UNITS                         "packets"
    MAX-ACCESS                    read-only
    STATUS                        current
    DESCRIPTION
            "The number of MTP3 packets sent by this link.
            This measurement is specified in Q752/3.3"
    ::= { cItpSpLinkTableEntry  8 }

cItpSpLinkMtp3BytesRcvd           OBJECT-TYPE
    SYNTAX                        Counter32
    UNITS                         "bytes"
    MAX-ACCESS                    read-only
    STATUS                        current
    DESCRIPTION
            "The number of MTP3 bytes received by this link.
             This measurement is specified in Q752/3.4"
    ::= { cItpSpLinkTableEntry  9 }

cItpSpLinkMtp3BytesSent           OBJECT-TYPE
    SYNTAX                        Counter32
    UNITS                         "bytes"
    MAX-ACCESS                    read-only
    STATUS                        current
    DESCRIPTION
            "The number of MTP3 bytes sent by this link.
             This measurement is specified in Q752/3.1"
    ::= { cItpSpLinkTableEntry  10 }

cItpSpLinkMtp2T01                 OBJECT-TYPE
    SYNTAX                        CItpTcTimerMtp2T01  
    UNITS                         "milliseconds"
    MAX-ACCESS                    read-create
    STATUS                        current
    DESCRIPTION
            "Alignment ready timer." 
    ::= { cItpSpLinkTableEntry 11 }

cItpSpLinkMtp2T02                 OBJECT-TYPE
    SYNTAX                        CItpTcTimerMtp2T02  
    UNITS                         "milliseconds"
    MAX-ACCESS                    read-create
    STATUS                        current
    DESCRIPTION
            "Not aligned timer."
    ::= { cItpSpLinkTableEntry 12 }

cItpSpLinkMtp2T03                 OBJECT-TYPE
    SYNTAX                        CItpTcTimerMtp2T03
    UNITS                         "milliseconds"
    MAX-ACCESS                    read-create
    STATUS                        current
    DESCRIPTION
            "Aligned timer."
    ::= { cItpSpLinkTableEntry 13 }

cItpSpLinkMtp2T04E                OBJECT-TYPE
    SYNTAX                        CItpTcTimerMtp2T04E
    UNITS                         "milliseconds"
    MAX-ACCESS                    read-create
    STATUS                        current   
    DESCRIPTION
            "Proving period timer emergency timer. "
    ::= { cItpSpLinkTableEntry 14 }

cItpSpLinkMtp2T04N                OBJECT-TYPE
    SYNTAX                        CItpTcTimerMtp2T04N
    UNITS                         "milliseconds"
    MAX-ACCESS                    read-create
    STATUS                        current
    DESCRIPTION
            "Proving period timer normal timer."
    ::= { cItpSpLinkTableEntry 15 }

cItpSpLinkMtp2T05                 OBJECT-TYPE
    SYNTAX                        CItpTcTimerMtp2T05
    UNITS                         "milliseconds"
    MAX-ACCESS                    read-create
    STATUS                        current
    DESCRIPTION
            "Sending SIB timer."
    ::= { cItpSpLinkTableEntry 16 }

cItpSpLinkMtp2T06                 OBJECT-TYPE
    SYNTAX                        CItpTcTimerMtp2T06
    UNITS                         "milliseconds"
    MAX-ACCESS                    read-create
    STATUS                        current
    DESCRIPTION
            "Remote congestion timer. "
    ::= { cItpSpLinkTableEntry 17 }

cItpSpLinkMtp2T07                 OBJECT-TYPE
    SYNTAX                        CItpTcTimerMtp2T07
    UNITS                         "milliseconds"
    MAX-ACCESS                    read-create
    STATUS                        current
    DESCRIPTION
            "Excessive delay of acknowledgement timer."
    ::= { cItpSpLinkTableEntry 18 }

cItpSpLinkMtp3T01                 OBJECT-TYPE
    SYNTAX                        CItpTcTimerMtp3T01
    UNITS                         "milliseconds"
    MAX-ACCESS                    read-create
    STATUS                        current
    DESCRIPTION
            "Delay to avoid message mis-sequencing on changeover."
    ::= { cItpSpLinkTableEntry  19 }

cItpSpLinkMtp3T02                 OBJECT-TYPE
    SYNTAX                        CItpTcTimerMtp3T02
    UNITS                         "milliseconds"
    MAX-ACCESS                    read-create
    STATUS                        current
    DESCRIPTION
            "Waiting for changeover acknowledgement."
    ::= { cItpSpLinkTableEntry  20 }

cItpSpLinkMtp3T03                 OBJECT-TYPE
    SYNTAX                        CItpTcTimerMtp3T03
    UNITS                         "milliseconds"
    MAX-ACCESS                    read-create
    STATUS                        current
    DESCRIPTION
            "Time controlled diversion-delay to avoid
            mis-sequencing on change back."
    ::= { cItpSpLinkTableEntry  21 }

cItpSpLinkMtp3T04                 OBJECT-TYPE
    SYNTAX                        CItpTcTimerMtp3T04
    UNITS                         "milliseconds"
    MAX-ACCESS                    read-create
    STATUS                        current
    DESCRIPTION
            "Waiting for change back acknowledgement (first
            attempt)."
    ::= { cItpSpLinkTableEntry  22 }

cItpSpLinkMtp3T05                 OBJECT-TYPE
    SYNTAX                        CItpTcTimerMtp3T05
    UNITS                         "milliseconds"
    MAX-ACCESS                    read-create
    STATUS                        current
    DESCRIPTION
            "Waiting for change back acknowledgement (second
             attempt)."
    ::= { cItpSpLinkTableEntry  23 }

cItpSpLinkMtp3T06                 OBJECT-TYPE
    SYNTAX                        CItpTcTimerMtp3T06
    UNITS                         "milliseconds"
    MAX-ACCESS                    read-create
    STATUS                        current
    DESCRIPTION
            "Delay to avoid message mis-sequencing on controlled
             rerouting."
    ::= { cItpSpLinkTableEntry  24 }

cItpSpLinkMtp3T07                 OBJECT-TYPE
    SYNTAX                        CItpTcTimerMtp3T07
    UNITS                         "milliseconds"
    MAX-ACCESS                    read-create
    STATUS                        current
    DESCRIPTION
            "Waiting for Signalling data link connection
             acknowledgement."
    ::= { cItpSpLinkTableEntry  25 }
                
cItpSpLinkMtp3T08                 OBJECT-TYPE
    SYNTAX                        CItpTcTimerMtp3T08
    UNITS                         "milliseconds"
    MAX-ACCESS                    read-create
    STATUS                        current
    DESCRIPTION
            "Transfer prohibited inhibition timer (transient
             solution)."
    ::= { cItpSpLinkTableEntry  26 }

cItpSpLinkMtp3T10                 OBJECT-TYPE
    SYNTAX                        CItpTcTimerMtp3T10
    UNITS                         "milliseconds"
    MAX-ACCESS                    read-create
    STATUS                        current
    DESCRIPTION
            "Waiting to repeat Signalling routeset test message."
    ::= { cItpSpLinkTableEntry  27 }

cItpSpLinkMtp3T11    OBJECT-TYPE
    SYNTAX                        CItpTcTimerMtp3T11
    UNITS                         "milliseconds"
    MAX-ACCESS                    read-create
    STATUS                        current
    DESCRIPTION                   
            "Transfer restricted timer. (This is one way of
            implementing the function described in 13.4/Q.704 and
            mainly intended to simplify SPs.)."
    ::= { cItpSpLinkTableEntry  28 }

cItpSpLinkMtp3T12                 OBJECT-TYPE
    SYNTAX                        CItpTcTimerMtp3T12
    UNITS                         "milliseconds"
    MAX-ACCESS                    read-create
    STATUS                        current
    DESCRIPTION
            "Waiting for uninhibit acknowledgement."
    ::= { cItpSpLinkTableEntry  29 }

cItpSpLinkMtp3T13                 OBJECT-TYPE
    SYNTAX                        CItpTcTimerMtp3T13
    UNITS                         "milliseconds"
    MAX-ACCESS                    read-create
    STATUS                        current
    DESCRIPTION
            "Waiting for force uninhibit."
    ::= { cItpSpLinkTableEntry  30 }

cItpSpLinkMtp3T14                 OBJECT-TYPE
    SYNTAX                        CItpTcTimerMtp3T14
    UNITS                         "milliseconds"
    MAX-ACCESS                    read-create
    STATUS                        current
    DESCRIPTION
            "Waiting for inhibition acknowledgement."
    ::= { cItpSpLinkTableEntry  31 }

cItpSpLinkMtp3T15                 OBJECT-TYPE
    SYNTAX                        CItpTcTimerMtp3T15
    UNITS                         "milliseconds"
    MAX-ACCESS                    read-create
    STATUS                        current
    DESCRIPTION
            "Waiting to start Signalling routeset congestion
             test."
    ::= { cItpSpLinkTableEntry  32 }

cItpSpLinkMtp3T16                 OBJECT-TYPE
    SYNTAX                        CItpTcTimerMtp3T16
    UNITS                         "milliseconds"
    MAX-ACCESS                    read-create
    STATUS                        current
    DESCRIPTION
            "Waiting for routeset congestion status update."
    ::= { cItpSpLinkTableEntry  33 }

cItpSpLinkMtp3T17                 OBJECT-TYPE
    SYNTAX                        CItpTcTimerMtp3T17
    UNITS                         "milliseconds"
    MAX-ACCESS                    read-create
    STATUS                        current
    DESCRIPTION
            "Delay to avoid oscillation of initial alignment
            failure and link restart."
    ::= { cItpSpLinkTableEntry  34 }

cItpSpLinkMtp3T18                 OBJECT-TYPE
    SYNTAX                        CItpTcTimerMtp3T18
    UNITS                         "milliseconds"
    MAX-ACCESS                    read-create
    STATUS                        current
    DESCRIPTION
            "This timers servers different function based on the 
             variant.
             
             ANSI: Repeat TFR once by response method
             ITU:  MTP restart link supervision"
    ::= { cItpSpLinkTableEntry  35 }

cItpSpLinkMtp3T19                 OBJECT-TYPE
    SYNTAX                        CItpTcTimerMtp3T19
    UNITS                         "milliseconds"
    MAX-ACCESS                    read-create
    STATUS                        current
    DESCRIPTION
            "This timers servers different function based on the 
             variant.
             
             ANSI: failed craft timer referral timer
             ITU:  supervision timer during MTP restart"
    ::= { cItpSpLinkTableEntry  36 }

cItpSpLinkMtp3T20                 OBJECT-TYPE
    SYNTAX                        CItpTcTimerMtp3T20
    UNITS                         "milliseconds"
    MAX-ACCESS                    read-create
    STATUS                        current
    DESCRIPTION
            "This timers servers different function based on the 
             variant.
             
             ANSI: waiting to repeat local inhibit test
             ITU:  MTP restart timer at the Signalling point"
    ::= { cItpSpLinkTableEntry  37 }

cItpSpLinkMtp3T21                 OBJECT-TYPE
    SYNTAX                        CItpTcTimerMtp3T21
    UNITS                         "milliseconds"
    MAX-ACCESS                    read-create
    STATUS                        current
    DESCRIPTION
            "This timers servers different function based on the 
             variant.
             
             ANSI: waiting to repeat remote inhibit test)       
             ITU:  MTP restart timer at adjacent Signalling point"
    ::= { cItpSpLinkTableEntry  38 }

cItpSpLinkMtp3T22                 OBJECT-TYPE
    SYNTAX                        CItpTcTimerMtp3T22
    UNITS                         "milliseconds"
    MAX-ACCESS                    read-create
    STATUS                        current
    DESCRIPTION
            "This timers servers different function based on the 
             variant.
             
             ANSI: restarting SP waiting for Signalling links avail
             ITU:  local inhibit test timer" 
    ::= { cItpSpLinkTableEntry  39 }

cItpSpLinkMtp3T23                 OBJECT-TYPE
    SYNTAX                        CItpTcTimerMtp3T23  
    UNITS                         "milliseconds"
    MAX-ACCESS                    read-create
    STATUS                        current
    DESCRIPTION
            "This timers servers different function based on the 
             variant.
             
             ANSI: restarting SP waiting to receive all TRA msgs
             ITU:  remote inhibit test timer"
    ::= { cItpSpLinkTableEntry  40 }

cItpSpLinkMtp3T24                 OBJECT-TYPE
    SYNTAX                        CItpTcTimerMtp3T24
    UNITS                         "milliseconds"
    MAX-ACCESS                    read-create
    STATUS                        current
    DESCRIPTION
            "This timers servers different function based on the 
             variant.
             
             ANSI: restarting SP waiting to broadcast all TRA msgs
             ITU:  stabilizing timer after local processor outage"
    ::= { cItpSpLinkTableEntry  41 }

cItpSpLinkMtp3T25                 OBJECT-TYPE
    SYNTAX                        CItpTcTimerMtp3T25
    UNITS                         "milliseconds"
    MAX-ACCESS                    read-create
    STATUS                        current
    DESCRIPTION
            "Timer at Signalling Point (SP) adjacent to restarting
            SP, waiting for traffic restart allowed message."
    ::= { cItpSpLinkTableEntry  42 }

cItpSpLinkMtp3T26                 OBJECT-TYPE
    SYNTAX                        CItpTcTimerMtp3T26
    UNITS                         "milliseconds"
    MAX-ACCESS                    read-create
    STATUS                        current
    DESCRIPTION
            "Timer at restarting SP waiting to repeat traffic
            restart waiting message."
    ::= { cItpSpLinkTableEntry  43 }

cItpSpLinkMtp3T27                 OBJECT-TYPE
    SYNTAX                        CItpTcTimerMtp3T27
    UNITS                         "milliseconds"
    MAX-ACCESS                    read-create
    STATUS                        current
    DESCRIPTION
            "Minimum duration of unavailability for full restart."
    ::= { cItpSpLinkTableEntry  44 }

cItpSpLinkMtp3T28                 OBJECT-TYPE
    SYNTAX                        CItpTcTimerMtp3T28
    UNITS                         "milliseconds"
    MAX-ACCESS                    read-create
    STATUS                        current
    DESCRIPTION
            "Timer at SP adjacent to restarting SP waiting for
            traffic restart waiting message."
    ::= { cItpSpLinkTableEntry  45 }

cItpSpLinkMtp3T29                 OBJECT-TYPE
    SYNTAX                        CItpTcTimerMtp3T29
    UNITS                         "milliseconds"
    MAX-ACCESS                    read-create
    STATUS                        current
    DESCRIPTION
            "Timer started when TRA sent in response to unexpected
            TRA or TRW."
    ::= { cItpSpLinkTableEntry  46 }

cItpSpLinkMtp3T30                 OBJECT-TYPE
    SYNTAX                        CItpTcTimerMtp3T30
    UNITS                         "milliseconds"
    MAX-ACCESS                    read-create
    STATUS                        current
    DESCRIPTION
            "Timer to limit sending of TFPs and TFRs in response
            to unexpected TRA or TRW."
    ::= { cItpSpLinkTableEntry  47 }

cItpSpLinkMtp3T31                 OBJECT-TYPE
    SYNTAX                        CItpTcTimerMtp3T31
    UNITS                         "milliseconds"
    MAX-ACCESS                    read-create
    STATUS                        current
    DESCRIPTION
            "False link congestion detection timer."
    ::= { cItpSpLinkTableEntry  48 }

cItpSpLinkMtp3T32                 OBJECT-TYPE
    SYNTAX                        CItpTcTimerMtp3T32
    UNITS                         "milliseconds"
    MAX-ACCESS                    read-create
    STATUS                        current
    DESCRIPTION
            "Link oscillation timer - Procedure A."
    ::= { cItpSpLinkTableEntry  49 }

cItpSpLinkMtp3T33                 OBJECT-TYPE
    SYNTAX                        CItpTcTimerMtp3T33 
    UNITS                         "milliseconds"
    MAX-ACCESS                    read-create
    STATUS                        current
    DESCRIPTION
            "Probation timer for link oscillation - Procedure B."
    ::= { cItpSpLinkTableEntry  50 }

cItpSpLinkMtp3T34                 OBJECT-TYPE
    SYNTAX                        CItpTcTimerMtp3T34
    UNITS                         "milliseconds"
    MAX-ACCESS                    read-create
    STATUS                        current
    DESCRIPTION
            "Suspension timer for link oscillation - Procedure B."
    ::= { cItpSpLinkTableEntry  51 }
        
cItpSpLinkTimerLinkTest           OBJECT-TYPE  
    SYNTAX                        CItpTcTimerLinkTest  
    UNITS                         "milliseconds"
    MAX-ACCESS                    read-create
    STATUS                        current
    DESCRIPTION
            "Signalling Link test acknowledgement timer."
    ::= { cItpSpLinkTableEntry 52 }

cItpSpLinkTimerLinkMessage        OBJECT-TYPE
    SYNTAX                        CItpTcTimerLinkMessage  
    UNITS                         "milliseconds"
    MAX-ACCESS                    read-create
    STATUS                        current
    DESCRIPTION
            "Interval timer for sending test messages."
    ::= { cItpSpLinkTableEntry 53 }
    
cItpSpLinkTimerLinkActRetry       OBJECT-TYPE
    SYNTAX                        CItpTcTimerLinkActRetry  
    UNITS                         "milliseconds"
    MAX-ACCESS                    read-create
    STATUS                        current
    DESCRIPTION
            "Link activation retry timer."
    ::= { cItpSpLinkTableEntry 54 }
    
cItpSpLinkXmitQueueDepth          OBJECT-TYPE
    SYNTAX                        Gauge32
    MAX-ACCESS                    read-only
    STATUS                        current
    DESCRIPTION
            "Number of packets waiting to be sent over this link."
    ::= { cItpSpLinkTableEntry 55 }

cItpSpLinkXmitQueueDepthHigh      OBJECT-TYPE
    SYNTAX                        Unsigned32
    MAX-ACCESS                    read-create
    STATUS                        current
    DESCRIPTION
            "This is the maximum number of packets waiting
             to be sent over this link since the last time this
             value was reset as indicated by 
             cItpSpLinkXmitQueueDepthHighReset. 
             Resetting this object is achieved by setting this
             object to 0. Attempting to set this object to any
             other value will result in a wrongValue error."
    ::= { cItpSpLinkTableEntry 56 }
    
cItpSpLinkXmitQueueDepthHighRT    OBJECT-TYPE
    SYNTAX                        TimeStamp
    MAX-ACCESS                    read-only
    STATUS                        current
    DESCRIPTION
            "This indicates when cItpSpLinkXmitQueueDepthHigh
            was set to 0."
    ::= { cItpSpLinkTableEntry 57 }

cItpSpLinkCongestionState         OBJECT-TYPE
    SYNTAX                        Unsigned32 (0..3)
    MAX-ACCESS                    read-only
    STATUS                        current
    DESCRIPTION
            "The Signalling link congestion status of this link. 0
            is the least congestion level, 3 is the highest
            congestion level."
    REFERENCE
            "ITU Q.704 Signalling network functions and messages.
            ANSI T1.111 Telecommunications - Signalling system
            No. 7 (SS7)-Signalling network functions and messages
            2.3.5.2."
    ::= { cItpSpLinkTableEntry 58 }

cItpSpLinkCongestionAbate1        OBJECT-TYPE
    SYNTAX                        Unsigned32 (0..65535)
    MAX-ACCESS                    read-create
    STATUS                        current
    DESCRIPTION
    "Threshold used to abate congestion level 1."
    
    ::= { cItpSpLinkTableEntry 59 }
       
cItpSpLinkCongestionAbate2        OBJECT-TYPE
    SYNTAX                        Unsigned32 (0..65535) 
    MAX-ACCESS                    read-create
    STATUS                        current
    DESCRIPTION
    "Threshold used to abate congestion level 2."

    ::= { cItpSpLinkTableEntry 60 }

cItpSpLinkCongestionAbate3        OBJECT-TYPE
    SYNTAX                        Unsigned32 (0..65535) 
    MAX-ACCESS                    read-create
    STATUS                        current
    DESCRIPTION
    "Threshold used to abate congestion level 3."
    
    ::= { cItpSpLinkTableEntry 61 }

cItpSpLinkCongestionOnset1        OBJECT-TYPE
    SYNTAX                        Unsigned32 (0..65535) 
    MAX-ACCESS                    read-create
    STATUS                        current
    DESCRIPTION
    "Threshold used to mark onset of congestion level 1."
    
    ::= { cItpSpLinkTableEntry 62 }
      
cItpSpLinkCongestionOnset2        OBJECT-TYPE
    SYNTAX                        Unsigned32 (0..65535) 
    MAX-ACCESS                    read-create
    STATUS                        current
    DESCRIPTION
    "Threshold used to mark onset of congestion level 2."
    
    ::= { cItpSpLinkTableEntry 63 }
      
cItpSpLinkCongestionOnset3        OBJECT-TYPE
    SYNTAX                        Unsigned32 (0..65535) 
    MAX-ACCESS                    read-create
    STATUS                        current
    DESCRIPTION
    "Threshold used to mark onset of congestion level 3."
    
    ::= { cItpSpLinkTableEntry 64 }

cItpSpLinkSigLinkTest             OBJECT-TYPE
    SYNTAX                        TruthValue
    MAX-ACCESS                    read-create
    STATUS                        current
    DESCRIPTION
            "Indicated if Signalling link test is enabled on this
            link.
            
            true  : Signalling link test is enabled.
            false : Signalling link test not enabled."
    DEFVAL          { true }
    ::= { cItpSpLinkTableEntry 65 }
        
cItpSpLinkQ752T1E1                OBJECT-TYPE
    SYNTAX                        TimeTicks
    MAX-ACCESS                    read-only
    STATUS                        current
    DESCRIPTION
         "Duration of link in the In-Service state Q752/1.1."

    ::= { cItpSpLinkTableEntry 66 }
        
cItpSpLinkQ752T1E2                 OBJECT-TYPE
    SYNTAX                         Counter32
    MAX-ACCESS                     read-only
    STATUS                         current
    DESCRIPTION
         "Count of Signalling Link failures - All reasons Q752/1.2."
    ::= { cItpSpLinkTableEntry 67 }
        
cItpSpLinkQ752T1E3                 OBJECT-TYPE
    SYNTAX                         Counter32
    UNITS                          "occurrences"
    MAX-ACCESS                     read-only
    STATUS                         current
    DESCRIPTION
         "Count of Signalling Link failures - Abnormal FIBR/BSNR 
          Q752/1.4."
    ::= { cItpSpLinkTableEntry 68 }
    
cItpSpLinkQ752T1E4                OBJECT-TYPE
    SYNTAX                        Counter32
    UNITS                         "occurrences"
    MAX-ACCESS                    read-only
    STATUS                        current
    DESCRIPTION
         "Count of Signalling Link failures - Excessive delay of 
          acknowledgement Q752/1.4."
    ::= { cItpSpLinkTableEntry 69 }
    
cItpSpLinkQ752T1E5                OBJECT-TYPE
    SYNTAX                        Counter32
    UNITS                         "occurrences"
    MAX-ACCESS                    read-only
    STATUS                        current
    DESCRIPTION
         "Count of Signalling Link failures - Excessive error rate 
          Q752/1.5."
    ::= { cItpSpLinkTableEntry 70 }
        
cItpSpLinkQ752T1E6                OBJECT-TYPE
    SYNTAX                        Counter32
    UNITS                         "occurrences"
    MAX-ACCESS                    read-only
    STATUS                        current
    DESCRIPTION
         "Count of Signalling Link failures - Excessive duration 
          of congestion Q752/1.6."
    ::= { cItpSpLinkTableEntry 71 }
    
cItpSpLinkQ752T1E7                OBJECT-TYPE
    SYNTAX                        Counter32
    UNITS                         "occurrences"
    MAX-ACCESS                    read-only
    STATUS                        current
    DESCRIPTION
         "Count of alignment or proving errors Q752/1.7."
    ::= { cItpSpLinkTableEntry 72 }
        
cItpSpLinkQ752T1E8                OBJECT-TYPE
    SYNTAX                        Counter32
    UNITS                         "occurrences"
    MAX-ACCESS                    read-only
    STATUS                        current
    DESCRIPTION
         "Count of signal units received in error Q752/1.8."
    ::= { cItpSpLinkTableEntry 73 }
        
cItpSpLinkQ752T1E9                OBJECT-TYPE
    SYNTAX                        Counter32
    UNITS                         "negative acknowledgements"
    MAX-ACCESS                    read-only
    STATUS                        current
    DESCRIPTION
         "Count of negative acknowledgements received Q752/1.9."
    ::= { cItpSpLinkTableEntry 74 }
        
cItpSpLinkQ752T1E10               OBJECT-TYPE
    SYNTAX                        Counter32
    UNITS                         "occurrences"
    MAX-ACCESS                    read-only
    STATUS                        current
    DESCRIPTION
         "Count of 'local automatic changeover' events
             Q752/1.10."
    ::= { cItpSpLinkTableEntry 75 }

cItpSpLinkQ752T1E11               OBJECT-TYPE
    SYNTAX                        Counter32
    UNITS                         "occurrences"
    MAX-ACCESS                    read-only
    STATUS                        current
    DESCRIPTION
         "Count of 'local automatic changeback' events Q752/1.11."
    ::= { cItpSpLinkTableEntry 76 }

-- Q752.12 Signalling Link Restoration  The standard only requires 
-- that an event be issued when this occurs. 

cItpSpLinkQ752T2E1                OBJECT-TYPE
    SYNTAX                        TimeTicks
    MAX-ACCESS                    read-only
    STATUS                        current
    DESCRIPTION
         "Duration of Signalling Link unavailable(for any reason)
          Q752/2.1."
    ::= { cItpSpLinkTableEntry 77 }
        
-- Q752/2.2 - Q752/2.4 deleted        

cItpSpLinkQ752T2E5                OBJECT-TYPE
    SYNTAX                        TimeTicks
    MAX-ACCESS                    read-only
    STATUS                        current
    DESCRIPTION
         "Duration of Signalling Link unavailable due to local 
          management actions Q752/2.5."
    ::= { cItpSpLinkTableEntry 78 }
    

cItpSpLinkQ752T2E6                OBJECT-TYPE
    SYNTAX                        TimeTicks
    MAX-ACCESS                    read-only
    STATUS                        current
    DESCRIPTION
         "Duration of Signalling Link unavailable due to remote 
          management actions Q752/2.6."
    ::= { cItpSpLinkTableEntry 79 }
        
cItpSpLinkQ752T2E7                OBJECT-TYPE
    SYNTAX                        TimeTicks
    MAX-ACCESS                    read-only
    STATUS                        current
    DESCRIPTION
         "Duration of Signalling Link unavailable due to link 
          failure Q752/2.7."     
    ::= { cItpSpLinkTableEntry 80 }
        
-- Q752/2.8 deleted        

cItpSpLinkQ752T2E9                OBJECT-TYPE
    SYNTAX                        TimeTicks
    MAX-ACCESS                    read-only
    STATUS                        current
    DESCRIPTION
         "Duration of Signalling Link unavailable due to remote 
          processor outage Q752/2.9."
    ::= { cItpSpLinkTableEntry 81 }

cItpSpLinkQ752T2E10               OBJECT-TYPE
     SYNTAX                       Counter32
     UNITS                        "occurrences"
     MAX-ACCESS                   read-only
     STATUS                       current
     DESCRIPTION
          "Count of 'remote processor outage' events Q752/2.10 and
           Q752/2.11.  The standard only requires that events are
           issued.  The entries have been combined into a single 
           entry to track all occurrences of these event types."

    ::= { cItpSpLinkTableEntry 82 }
     

-- Q752/2.12 Deleted
-- Q752/2.13 and Q752/2.14.  These values can be calculated from
-- information provided by Q752/2.15, Q752/2.16, Q752/2.17
-- and Q752/2.18        
        
cItpSpLinkQ752T2E15               OBJECT-TYPE
     SYNTAX                       TimeTicks
     MAX-ACCESS                   read-only
     STATUS                       current
     DESCRIPTION
           "Duration of local busy Q752/2.15."

    ::= { cItpSpLinkTableEntry 83 }
     
cItpSpLinkQ752T2E16               OBJECT-TYPE
     SYNTAX                       Counter32
     UNITS                        "occurrences"
     MAX-ACCESS                   read-only
     STATUS                       current
     DESCRIPTION
           "Count of local inhibition Q752/2.16 and Q752/2.17.
            The standard only requires that events are issued.
            The entries have been combined into a single 
            entry to track all occurrences of these event types."

    ::= { cItpSpLinkTableEntry 84 }
     
cItpSpLinkQ752T2E18               OBJECT-TYPE
     SYNTAX                       Counter32
     UNITS                        "occurrences"
     MAX-ACCESS                   read-only
     STATUS                       current
     DESCRIPTION
           "Count of remote inhibition Q752/2.18 and Q752/2.19.
            The standard only requires that events are issued.
            The entries have been combined into a single 
            entry to track all occurrences of these event types."

    ::= { cItpSpLinkTableEntry 85 }

cItpSpLinkMtp3PacketsRetrans      OBJECT-TYPE
     SYNTAX                       Counter32
     UNITS                        "packets"
     MAX-ACCESS                   read-only
     STATUS                       current
     DESCRIPTION
           "The number of MTP3 packets retransmitted on this link.
            This measurement is specified in Q752/3.2"
    ::= { cItpSpLinkTableEntry 86 }

cItpSpLinkMtp3BytesRetrans        OBJECT-TYPE
     SYNTAX                       Counter32
     UNITS                        "bytes"
     MAX-ACCESS                   read-only
     STATUS                       current
     DESCRIPTION
           "The number of MTP3 bytes retransmitted on this link.
            This measurement is specified in Q752/3.2"
    ::= { cItpSpLinkTableEntry 87 }

cItpSpLinkQ752T3E6                OBJECT-TYPE
     SYNTAX                       Counter32
     UNITS                        "events"
     MAX-ACCESS                   read-only
     STATUS                       current
     DESCRIPTION
           "The number times this Signalling link was marked
            congested. This measurement is specified in Q752/3.6"
    ::= { cItpSpLinkTableEntry 88 }
                   
cItpSpLinkQ752T3E7               OBJECT-TYPE
     SYNTAX                      TimeTicks
     MAX-ACCESS                  read-only
     STATUS                      current
     DESCRIPTION             
           "Cumulative duration of Signalling link congestion 
             Q752/3.7."
    ::= { cItpSpLinkTableEntry 89 }

cItpSpLinkQ752T3E10L1             OBJECT-TYPE
     SYNTAX                       Counter32
     UNITS                        "Packets"
     MAX-ACCESS                   read-only
     STATUS                       current
     DESCRIPTION
           "The number of packets(MSUs) discarded due to Signalling 
            link level 1 congestion Q752/3.10"
    ::= { cItpSpLinkTableEntry  90 }
     
cItpSpLinkQ752T3E10L2             OBJECT-TYPE
     SYNTAX                       Counter32
     UNITS                        "Packets"
     MAX-ACCESS                   read-only
     STATUS                       current
     DESCRIPTION
           "The number of packets(MSUs) discard due to Signalling 
            link level 2 congestion Q752/3.10"
     ::= { cItpSpLinkTableEntry 91 }
     
cItpSpLinkQ752T3E10L3             OBJECT-TYPE
     SYNTAX                       Counter32
     UNITS                        "Packets"
     MAX-ACCESS                   read-only
     STATUS                       current
     DESCRIPTION
           "The number of packets(MSUs) discard due to Signalling 
            link level 3 congestion Q752/3.10"
     ::= { cItpSpLinkTableEntry 92 }

cItpSpLinkQ752T3E11L1             OBJECT-TYPE
     SYNTAX                       Counter32
     UNITS                        "bytes"
     MAX-ACCESS                   read-only
     STATUS                       current
     DESCRIPTION
           "The number times this Signalling link entered congestion
            level 1 and packets were discarded. This measurement is 
            specified in Q752/3.11"
     ::= { cItpSpLinkTableEntry 93 }
     
cItpSpLinkQ752T3E11L2             OBJECT-TYPE
     SYNTAX                       Counter32
     UNITS                        "bytes"
     MAX-ACCESS                   read-only
     STATUS                       current
     DESCRIPTION
           "The number times this Signalling link entered congestion
            level 2 and packets were discarded. This measurement is 
            specified in Q752/3.11"
     ::= { cItpSpLinkTableEntry 94 }

cItpSpLinkQ752T3E11L3             OBJECT-TYPE
     SYNTAX                       Counter32
     UNITS                        "bytes"
     MAX-ACCESS                   read-only
     STATUS                       current
     DESCRIPTION
           "The number times this Signalling link entered congestion
            level 3 and packets were discarded. This measurement is 
            specified in Q752/3.11"
     ::= { cItpSpLinkTableEntry 95 }
                                           
cItpSpLinkIPType1                 OBJECT-TYPE
     SYNTAX                       InetAddressType
     MAX-ACCESS                   read-create
     STATUS                       current
     DESCRIPTION
          "When cItpSpLinkType is set to sctpIp then this object 
           contains the type of the first of four possible local 
           IP addresses used to create the association supporting
           this link. When cItpSpLinkType is not set to sctpIp 
           then no significance is to be placed on this value."
     ::= { cItpSpLinkTableEntry 96 }
           
cItpSpLinkIPType2                 OBJECT-TYPE
     SYNTAX                       InetAddressType
     MAX-ACCESS                   read-create
     STATUS                       current
     DESCRIPTION
          "When cItpSpLinkType is set to sctpIp then this object 
           contains the type of the second of four possible local 
           IP addresses used to create the association supporting
           this link. When cItpSpLinkType is not set to sctpIp 
           then no significance is to be placed on this value."
     ::= { cItpSpLinkTableEntry 97 }
           
cItpSpLinkIPType3                 OBJECT-TYPE
     SYNTAX                       InetAddressType
     MAX-ACCESS                   read-create
     STATUS                       current
     DESCRIPTION
          "When cItpSpLinkType is set to sctpIp then this object 
           contains the type of the third of four possible local 
           IP addresses used to create the association supporting
           this link. When cItpSpLinkType is not set to sctpIp 
           then no significance is to be placed on this value."
     ::= { cItpSpLinkTableEntry 98 }
           
cItpSpLinkIPType4                 OBJECT-TYPE
     SYNTAX                       InetAddressType
     MAX-ACCESS                   read-create
     STATUS                       current
     DESCRIPTION
          "When cItpSpLinkType is set to sctpIp then this object 
           contains the type of the fourth of four possible local 
           IP addresses used to create the association supporting
           this link. When cItpSpLinkType is not set to sctpIp 
           then no significance is to be placed on this value."
     ::= { cItpSpLinkTableEntry 99 }
           
cItpSpLinkIPAddr1                 OBJECT-TYPE
     SYNTAX                       InetAddress
     MAX-ACCESS                   read-create
     STATUS                       current
     DESCRIPTION
          "When cItpSpLinkType is set to sctpIp then this object 
           contains the first of four possible local IP addresses 
           used to create the association supporting this link.
           When cItpSpLinkType is not set to sctpIp then no
           significance is to be placed on this value."
     
     ::= { cItpSpLinkTableEntry 100 }

cItpSpLinkIPAddr2                 OBJECT-TYPE
     SYNTAX                       InetAddress
     MAX-ACCESS                   read-create
     STATUS                       current
     DESCRIPTION
          "When cItpSpLinkType is set to sctpIp then this object 
           contains the second of four possible local IP addresses 
           used to create the association supporting this link.
           When cItpSpLinkType is not set to sctpIp then no
           significance is to be placed on this value."
     
     ::= { cItpSpLinkTableEntry 101 }
                                  
cItpSpLinkIPAddr3                 OBJECT-TYPE
     SYNTAX                       InetAddress
     MAX-ACCESS                   read-create
     STATUS                       current
     DESCRIPTION
          "When cItpSpLinkType is set to sctpIp then this object 
           contains the third of four possible local IP addresses 
           used to create the association supporting this link.
           When cItpSpLinkType is not set to sctpIp then no
           significance is to be placed on this value."
     
     ::= { cItpSpLinkTableEntry 102 }

cItpSpLinkIPAddr4                 OBJECT-TYPE
     SYNTAX                       InetAddress
     MAX-ACCESS                   read-create
     STATUS                       current
     DESCRIPTION
          "When cItpSpLinkType is set to sctpIp then this object 
           contains the fourth of four possible local IP addresses 
           used to create the association supporting this link.
           When cItpSpLinkType is not set to sctpIp then no
           significance is to be placed on this value."
     
     ::= { cItpSpLinkTableEntry 103 }
    
cItpSpLinkLocalPort               OBJECT-TYPE
     SYNTAX                       Unsigned32 (0..65535) 
     MAX-ACCESS                   read-create
     STATUS                       current
     DESCRIPTION
          "When cItpSpLinkType is set to sctpIp then this object 
           contains the local port number used to create the
           association supporting this link.
           When cItpSpLinkType is not set to sctpIp then no
           significance is to be placed on this value."
     ::= { cItpSpLinkTableEntry 104 }
     
cItpSpLinkRemotePort             OBJECT-TYPE
     SYNTAX                      Unsigned32 (0..65535) 
     MAX-ACCESS                  read-create
     STATUS                      current
     DESCRIPTION
          "When cItpSpLinkType is set to sctpIp then this object 
           contains the remote port number used to create the
           association supporting this link.
           When cItpSpLinkType is not set to sctpIp then no
           significance is to be placed on this value."
     ::= { cItpSpLinkTableEntry 105 }
      
cItpSpLinkQosClass               OBJECT-TYPE
     SYNTAX                      CItpTcQos
     MAX-ACCESS                  read-create
     STATUS                      current
     DESCRIPTION
          "When cItpSpLinkType is set to sctpIp then this object 
           contains the quality of service class to be assigned
           to packets sent on this association.
           When cItpSpLinkType is not set to sctpIp then no
           significance is to be placed on this value."
     ::= { cItpSpLinkTableEntry 106 }
     
cItpSpLinkRowStatus               OBJECT-TYPE
    SYNTAX                        RowStatus
    MAX-ACCESS                    read-create
    STATUS                        current
    DESCRIPTION                   
         "The object is used by a management station to 
          create or delete the row entry in cItpSpLinkTable  
          following the RowStatus textual convention."
      ::= { cItpSpLinkTableEntry 107 }
      
cItpSpLinkStateReason            OBJECT-TYPE
    SYNTAX                        BITS {  
                                    localInhibit(0),
                                    remoteInhibit(1),
                                    blocked(2)
                                  }
    MAX-ACCESS                    read-only
    STATUS                        current
    DESCRIPTION                   
        "This object provides additional information
         on the state of a link as follows.
          
         'localInhibit'  : Link has been inhibited by a local 
                           management operation.
         'remoteInhibit' : LInk has been inhibited by a remote
                           management operation.
         'blocked'       : Link is blocked because of a remote 
                           processor outage."
      ::= { cItpSpLinkTableEntry 108 }

cItpSpLinkDisplayName            OBJECT-TYPE
    SYNTAX                       SnmpAdminString ( SIZE ( 0..30 ) )
    MAX-ACCESS                   read-create
    STATUS                       current
    DESCRIPTION
            "A short identifier for each link linkset.
             This value can be set by system administrator
             or defaults to the linkset name and SLC 
             formatted as an ASCII string."
    ::= { cItpSpLinkTableEntry 109 }
    
cItpSpLinkDroppedPkts             OBJECT-TYPE
     SYNTAX                       Counter32
     UNITS                        "packets"
     MAX-ACCESS                   read-only
     STATUS                       current
     DESCRIPTION
           "The number of packets that were dropped by this link."
     ::= { cItpSpLinkTableEntry 110 }
     
cItpSpLinkTransmittedLssu         OBJECT-TYPE
     SYNTAX                       Counter32
     UNITS                        "LSSU"
     MAX-ACCESS                   read-only
     STATUS                       current
     DESCRIPTION
           "The number of Link Status Signal Units sent on this 
            link."
     ::= { cItpSpLinkTableEntry 111 }
     
cItpSpLinkReceivedLssu            OBJECT-TYPE
     SYNTAX                       Counter32
     UNITS                        "LSSU"
     MAX-ACCESS                   read-only
     STATUS                       current
     DESCRIPTION
           "The number of Link Status Signal Units received on this
            link."
     ::= { cItpSpLinkTableEntry 112 }

cItpSpLinkProtocolDetails         OBJECT-TYPE
    SYNTAX                        BITS {
                                    tcbcBuffering(0),
                                    tcocBuffering(1),
                                    tlacAdjacentSpRestarting(2),
                                    tlacEmergencyCoInProgress(3),
                                    tlacChangebackInProgress(4),
                                    tlacChangeoverInProgress(5),
                                    tlacChangeoverFailed(6),
                                    tlacInhibitRetry(7),
                                    tlacManagementRequest(8),
                                    tlacSpRestarting(9),
                                    tsrcChangeOverComplete(10),
                                    tsrcAdjacentSpRestart(11)
                                  }
    MAX-ACCESS                    read-only
    STATUS                        current
    DESCRIPTION                   
        "This object provide details on the protocol states
         for this link as follows.
         
         Changeback control(TCBC)         
               'tcbcBuffering': Changeback control is buffering data 
                                on this link.
               
         Changeover control(TCOC)
               'tcocBuffering': Changeover control is buffering data 
                                on this link
               
         Link availability control(TLAC)
               'tlacAdjacentSpRestarting': Adjacent Signalling point 
                                is restarting. 
               
               'tlacEmergencyCoInProgress': Emergency changeover is in
                                progress on this link.
                                
               'tlacChangebackInProgress': Changeback is in progress 
                                on this link.
                                
               'tlacChangeoverInProgress': Changeover is in progress 
                                on this link.
                       
               'tlacChangeoverFailed': The last changeover operation
                                failed on this link.
                                
               'tlacInhibitRetry': Inhibit command will be retried.
               
               'tlacManagementRequest': Management request in progress
                                for this link.
                                 
               'tlacSpRestarting': Signalling point is in the process 
                                of a restart.
               
         Signalling routing control(TSRC)
               'tsrcChangeOverComplete': Changeove request is complete.
               
               'tsrcAdjacentSpRestart': Adjacent Signalling Point is
                                restarting."
         
     ::= { cItpSpLinkTableEntry 113 }
      
cItpSpLinkLsacState              OBJECT-TYPE
    SYNTAX INTEGER {
                    undefined(1),
                    inactive(2),
                    active(3),
                    activatingRestoring(4),
                    failed(5),
                    actT17wait(6),
                    actAnsiWaitDeloaded(7),
                    actItuWaitStmReady(8) 
    }
    MAX-ACCESS                   read-only
    STATUS                       current
    DESCRIPTION
        "Signalling link activity control state:
         'undefined(1)' - link is an undefined state
         'inactive(2)' - A Signalling link that is not in 
                         operation.
         'active(3)' - A Signalling link that is in 
                         operation.           
         'activatingRestoring(4)' - A Signalling that is not operational
                         and is being activated or restored.
         'failed(5)' - A Signalling link which is available 
                         (not blocked) is marked by level 3 as 
                         failed when a changeover order is 
                         received.            
         'actT17wait(6)' - Link activation has failed.  Link is 
                         placed into this state to wait for timer 
                         T17 to expire in order to avoid the 
                         oscillation of initial alignment failure
                         and link restart.       
         'actAnsiWaitDeloaded(7) - Waiting for change back 
                         acknowledgement (second attempt).
         'actItuWaitStmReady(8)' Wait for Signalling Traffic 
                         Management ready event."
    REFERENCE
           "Figure 37/Q.704 - Signalling link management;
            Signalling link activity control (LSAC)"
       
    ::= { cItpSpLinkTableEntry 114 }
    
cItpSpLinkTsrcState              OBJECT-TYPE
    SYNTAX INTEGER {
                    undefined(1),
                    idle(2),
                    wait5(3)
    }
    MAX-ACCESS                   read-only 
    STATUS                       current
    DESCRIPTION
           "Signalling traffic management routing control state:
              'undefined(1)' - link is an undefined state
              'idle(2)'      - traffic mangement is idle
              'wait5(3)'     - traffic management is active and 
                               in the sending status phase"
    REFERENCE
           "Figure 29/Q.704 - Signalling traffic management;
            Signalling routing control (TSRC)"
            
    ::= { cItpSpLinkTableEntry 115 }
    
cItpSpLinkTcocState              OBJECT-TYPE
    SYNTAX INTEGER {
              undefined(1),
              idle(2),
              wait2(3),
              waitForAck(4),
              retrieving(5),
              wait5(6),
              wait7(7),
              wait8(8)
    }
    MAX-ACCESS                   read-only 
    STATUS                       current
    DESCRIPTION
           " Changeover control State:
              'undefined(1)'  - Link is an undefined state.
              'idle(2)'       - Link is available and idle.
              'wait2(3)'      - Wait for MTP2 to initialize link.
              'waitForAck(4)' - Waiting for changeover 
                                acknowledgement.
              'retrieving(5)' - Packets are being retrieved from 
                                link.
              'wait5(6)'      - Wait state when transitioning from 
                                idle state.
              'wait7(7)'      - Delay to avoid message mis-sequencing
                                on changeover
              'wait8(8)'      - Wait state prior to processing 
                                changeover order or emergency 
                                changeover order events."
    REFERENCE
           " Figure 30/Q.704 - Signalling traffic management;
             changeover control (TCOC)"
    ::= { cItpSpLinkTableEntry 116 }
    
cItpSpLinkTcocLocalBSNT           OBJECT-TYPE
    SYNTAX                        CItpSpSequenceNumber
    MAX-ACCESS                    read-only
    STATUS                        current
    DESCRIPTION
            "The local backward sequence number to be transmitted."
    ::= { cItpSpLinkTableEntry 117}
    
cItpSpLinkTcocRemoteBSNT          OBJECT-TYPE
    SYNTAX                        CItpSpSequenceNumber
    MAX-ACCESS                    read-only
    STATUS                        current
    DESCRIPTION
            "The remote backward sequence number to be transmitted."
    ::= { cItpSpLinkTableEntry 118 }
    
cItpSpLinkTcbcState              OBJECT-TYPE
    SYNTAX INTEGER {
              undefined(1),
              idle(2),
              firstAttempt(3),
              secondAttempt(4),
              timeControlledDiversion(5)
    }
    MAX-ACCESS                   read-only 
    STATUS                       current
    DESCRIPTION
           " Changeback control State:
              'undefined(1)'     - link is an undefined state.
              'idle(2)'          - Link is available and idle.
              'firstAttempt(3)'  - First attempt at changeback.
              'secondAttempt(4)' - Second attempt at changeback
              'timeControlledDiversion(5)' - Changeback using 
                                 time controlled Diversion."
    ::= { cItpSpLinkTableEntry 119 }
    
cItpSpLinkReceivedSIB             OBJECT-TYPE
     SYNTAX                       Counter32
     UNITS                        "SIB"
     MAX-ACCESS                   read-only
     STATUS                       current
     DESCRIPTION
           "The number of status indicator 'busy' link status signal
            units received on this link. The SIB indicates that
            level two is congested at the transmitting Signalling
            point."
     ::= { cItpSpLinkTableEntry 120 }
     

cItpSpLinkTransmittedSIB          OBJECT-TYPE
     SYNTAX                       Counter32
     UNITS                        "SIB"
     MAX-ACCESS                   read-only
     STATUS                       current
     DESCRIPTION
           "The number of status indicator 'busy' link status signal
            units transmitted on this link. The SIB indicates that
            level two is congested at the transmitting Signalling
            point."
     ::= { cItpSpLinkTableEntry 121 }
     
cItpSpLinkMtp2ExpiredT01          OBJECT-TYPE
     SYNTAX                       Counter32
     MAX-ACCESS                   read-only
     STATUS                       current
     DESCRIPTION
           "The number of times the alignment ready timer has 
            expired on this link."
     ::= { cItpSpLinkTableEntry 122 }
     
cItpSpLinkMtp2ExpiredT02          OBJECT-TYPE
     SYNTAX                       Counter32
     MAX-ACCESS                   read-only
     STATUS                       current
     DESCRIPTION
           "The number of times the not alignment ready timer has
            expired on this link."
     ::= { cItpSpLinkTableEntry 123 }
     
cItpSpLinkMtp2ExpiredT03          OBJECT-TYPE
     SYNTAX                       Counter32
     MAX-ACCESS                   read-only
     STATUS                       current
     DESCRIPTION
           "The number of times the aligned timer has
            expired on this link."
     ::= { cItpSpLinkTableEntry 124 }

cItpSpLinkMtp2ExpiredT04          OBJECT-TYPE
     SYNTAX                       Counter32
     MAX-ACCESS                   read-only
     STATUS                       current
     DESCRIPTION
           "The number of times the proving period timer
            has expired on this link."
     ::= { cItpSpLinkTableEntry 125 }

cItpSpLinkMtp2ExpiredT05          OBJECT-TYPE
     SYNTAX                       Counter32
     MAX-ACCESS                   read-only
     STATUS                       current
     DESCRIPTION
           "The number of times the sending status indicator
            busy timer has expired on this link."
     ::= { cItpSpLinkTableEntry 126 }

cItpSpLinkMtp2ExpiredT06          OBJECT-TYPE
     SYNTAX                       Counter32
     MAX-ACCESS                   read-only
     STATUS                       current
     DESCRIPTION
           "The number of times the remote congestion
            timer has expired on this link."
     ::= { cItpSpLinkTableEntry 127 }


cItpSpLinkMtp2ExpiredT07          OBJECT-TYPE
     SYNTAX                       Counter32
     MAX-ACCESS                   read-only
     STATUS                       current
     DESCRIPTION
           "The number of times the excessive delay of 
            acknowledgement timer has expired on this link."
     ::= { cItpSpLinkTableEntry 128 }

cItpSpLinkOMAERMCount             OBJECT-TYPE
     SYNTAX                       Counter32
     MAX-ACCESS                   read-only
     STATUS                       current
     DESCRIPTION
           "The number of times the Alignment Error Rate Monitor
            procedure was started on this link."
     ::= { cItpSpLinkTableEntry 129 }
     
cItpSpLinkOMAERMFailCount         OBJECT-TYPE
     SYNTAX                       Counter32
     MAX-ACCESS                   read-only
     STATUS                       current
     DESCRIPTION
           "The number of times the Alignment Error Rate Monitor
            procedure failed on this link."
     ::= { cItpSpLinkTableEntry 130 }

cItpSpLinkOMSURMCount             OBJECT-TYPE
     SYNTAX                       Counter32
     MAX-ACCESS                   read-only
     STATUS                       current
     DESCRIPTION
           "The number of times the Signal Unit Error Rate Monitor
            procedure was started on this link."
     ::= { cItpSpLinkTableEntry 131 }
     
cItpSpLinkOMSURMFailCount         OBJECT-TYPE
     SYNTAX                       Counter32
     MAX-ACCESS                   read-only
     STATUS                       current
     DESCRIPTION
           "The number of times the Signal Unit Error Rate Monitor
            procedure failed on this link."
     ::= { cItpSpLinkTableEntry 132 }

cItpSpLinkPlanCapacityRcvd        OBJECT-TYPE
    SYNTAX                        CItpSpLinkCapacity
    UNITS                         "bits per second"
    MAX-ACCESS                    read-create
    STATUS                        current
    DESCRIPTION
         "An estimate of the number of bits per second that is
          expected to be received from this link.  This 
          object will be used in combination with 
          cItpSpUtilSampleInterval, cItpSpUtilThreshold, 
          cItpSpUtilThreshold and cItpSpLinkUtilThresholdRcvd
          to generate the cItpSpLinkRcvdUtilChange notification."
   ::= { cItpSpLinkTableEntry 133 }

cItpSpLinkUtilThresholdRcvd     OBJECT-TYPE
    SYNTAX                      CItpSpPercentThreshold
    UNITS                       "percent"
    MAX-ACCESS                  read-create
    STATUS                      current
    DESCRIPTION
        "This object specifies the threshold used to 
         to generate the cItpSpLinkRcvdUtilChange notification.  
         The value of zero indicates the threshold has not been
         defined at the link level and the value from the 
         cItpSpUtilThreshold object will be used to generate
         the cItpSpLinkRcvdUtilChange notification."
     DEFVAL { 0 }
   ::= { cItpSpLinkTableEntry 134 }
     
cItpSpLinkUtilizationRcvd         OBJECT-TYPE
    SYNTAX                        CItpSpLinkUtilization
    UNITS                         "percent"
    MAX-ACCESS                    read-only
    STATUS                        current
    DESCRIPTION
         "An estimate of the utilization of this link for traffic
          received on this link in the prior time period defined 
          by the cItpSpUtilSampleInterval object."
   ::= { cItpSpLinkTableEntry 135 }

cItpSpLinkUtilStateRcvd           OBJECT-TYPE
    SYNTAX                        CItpSpLinkUtilizationState 
    MAX-ACCESS                    read-only 
    STATUS                        current
    DESCRIPTION
         "Link Utilization State for in bound traffic."
   ::= { cItpSpLinkTableEntry 136 }

cItpSpLinkL2BytesRcvd             OBJECT-TYPE
     SYNTAX                       Counter32
     MAX-ACCESS                   read-only
     STATUS                       current
     DESCRIPTION
           "A count of the bytes received on the link including the 
            additional bytes required by underlying protocols.
            This provides a transport independent mechanism 
            for collection information on link utilization."
     ::= { cItpSpLinkTableEntry 137 }
     
cItpSpLinkPlanCapacitySent        OBJECT-TYPE
    SYNTAX                        CItpSpLinkCapacity
    UNITS                         "bits per second"
    MAX-ACCESS                    read-create
    STATUS                        current
    DESCRIPTION
         "An estimate of the number of bits per second that is
          expected to be sent on this link.  This object will 
          be used in combination with  cItpSpUtilSampleInterval, 
          cItpSpUtilThreshold and cItpSpLinkUtilThresholdRcvd to 
          generate the cItpSpLinkSentUtilChange notification."
   ::= { cItpSpLinkTableEntry 138 }

cItpSpLinkUtilThresholdSent     OBJECT-TYPE
    SYNTAX                      CItpSpPercentThreshold
    UNITS                       "percent"
    MAX-ACCESS                  read-create
    STATUS                      current
    DESCRIPTION
        "This object specifies the threshold used to generate the
         cItpSpLinkRcvdUtilChange notification.  The value of zero
         indicates the threshold has not been defined at the link 
         level and the value from the cItpSpUtilThreshold object
         will be used to generate the cItpSpLinkRcvdUtilChange 
         notification."
     DEFVAL { 0 }
   ::= { cItpSpLinkTableEntry 139 }
   
cItpSpLinkUtilizationSent         OBJECT-TYPE
    SYNTAX                        CItpSpLinkUtilization
    UNITS                         "percent"
    MAX-ACCESS                    read-only
    STATUS                        current
    DESCRIPTION
         "An estimate of the utilization of this link for traffic
          sent on this link in the prior time period defined 
          by the cItpSpUtilSampleInterval object."
   ::= { cItpSpLinkTableEntry 140 }

cItpSpLinkUtilStateSent           OBJECT-TYPE
    SYNTAX                        CItpSpLinkUtilizationState 
    MAX-ACCESS                    read-only 
    STATUS                        current
    DESCRIPTION
         "Link Utilization State for out bound traffic."
   ::= { cItpSpLinkTableEntry 141 }

cItpSpLinkL2BytesSent             OBJECT-TYPE
     SYNTAX                       Counter32
     MAX-ACCESS                   read-only
     STATUS                       current
     DESCRIPTION
           "A count of the bytes sent on the link including the 
            additional bytes required by underlying protocols.
            This provides a transport independent mechanism 
            for collection information on link utilization."
     ::= { cItpSpLinkTableEntry 142 }
-- *************************************************************
-- *                                                           *
-- * SP - Notification Enable     Objects                      *
-- *                                                           *
-- *************************************************************

cItpSpLsStateChangeNotifEnabled  OBJECT-TYPE
     SYNTAX                      TruthValue
     MAX-ACCESS                  read-write
     STATUS                      current
     DESCRIPTION          
             "The SP linkset notification truth value.
             'true'  Indicates that cItpSpLinksetStateChange
                     notification is to be generated when the state
                     changes. That is, the notification generation 
                     is enabled.
             'false' Indicates that cItpSpLinksetStateChange
                     notification generation is disabled."
     DEFVAL { false }
     ::= { cItpSpNotificationsEnable  1 }
 
cItpSpLnkStateChangeNotifEnabled  OBJECT-TYPE
     SYNTAX                       TruthValue
     MAX-ACCESS                   read-write
     STATUS                       current
     DESCRIPTION 
             "The SP link notification truth value.
             'true'  Indicates that cItpSpLinkStateChange
                     notification is to be generated when the state
                     changes. That is, the notification generation 
                     is enabled.
             'false' Indicates that cItpSpLinkStateChange
                     notification generation is disabled."
     DEFVAL { false }
     ::= { cItpSpNotificationsEnable  2 }
     
cItpSpCongestionNotifEnabled      OBJECT-TYPE
     SYNTAX                       TruthValue
     MAX-ACCESS                   read-write
     STATUS                       current
     DESCRIPTION 
             "The SP Congestion  notification truth value.
             'true'  Indicates that cItpSpCongestionChange
                     notification is to be generated when the state
                     changes. That is, the notification generation 
                     is enabled.
             'false' Indicates that cItpSpCongestionChange
                     notification generation is disabled."
     DEFVAL { false }
     ::= { cItpSpNotificationsEnable  3 }
     
cItpSpLinkUtilNotifEnabled        OBJECT-TYPE
     SYNTAX                       TruthValue
     MAX-ACCESS                   read-write
     STATUS                       current
     DESCRIPTION 
             "The SP link utilization  notification truth value.
             'true'  Indicates that the notification of link 
                     utilization has been enabled.  That is, 
                     the notification generation is enabled.
                     
             'false' Indicates that the notification link 
                     utilization has been disabled."
     DEFVAL { false }
     ::= { cItpSpNotificationsEnable  4 }

     

-- *************************************************************
-- *                                                           *
-- * Notifications                                             *
-- *                                                           *
-- *************************************************************
cItpSpNotifications OBJECT IDENTIFIER 
                    ::= { cItpSpMIBNotifs 0} 

cItpSpLinksetStateChange NOTIFICATION-TYPE
     OBJECTS {
             cItpSpCLLICode,
             cItpSpLinksetState,
             cItpSpLinksetDisplayName,
             cItpSpLinksetSourceDisplayPC,  
             cItpSpLinksetAdjacentDisplayPC
     }
     STATUS  current
     DESCRIPTION
             "The notification generated when a linkset
              changes to a new state.  The value of
              cItpSpLinksetState  indicates the new state."
     ::= { cItpSpNotifications 1 }

cItpSpLinkStateChange NOTIFICATION-TYPE
     OBJECTS {
             cItpSpCLLICode,
             cItpSpLinkState,
             cItpSpLinkDisplayName,
             cItpSpLinksetSourceDisplayPC,  
             cItpSpLinksetAdjacentDisplayPC,
             cItpSpLinkStateReason
     }        
     STATUS  current
     DESCRIPTION
             "The notification generated when a link
              changes to a new state.  The value of
              cItpSpLinkState  indicates the new state."
     ::= { cItpSpNotifications 2 }
     

cItpSpCongestionChange NOTIFICATION-TYPE
     OBJECTS {
             cItpSpCLLICode,
             cItpSpLinkCongestionState,
             cItpSpLinkDisplayName,
             cItpSpLinksetSourceDisplayPC,  
             cItpSpLinksetAdjacentDisplayPC
     }        
     STATUS  current
     DESCRIPTION
             "The notification generated when a link
              changes to a new congestion level as specified
              by cItpSpLinkCongestionState object."
     ::= { cItpSpNotifications 3 }
     

cItpSpLinkRcvdUtilChange NOTIFICATION-TYPE
     OBJECTS {
             cItpSpCLLICode,
             cItpSpLinkUtilStateRcvd,
             cItpSpLinkDisplayName,
             cItpSpLinksetSourceDisplayPC,  
             cItpSpLinksetAdjacentDisplayPC,
             cItpSpLinkUtilizationRcvd
     }        
     STATUS  current
     DESCRIPTION
             "The notification provide is generated when 
              the cItpSpLinkUtilStateRcvd changes states."
              
     ::= { cItpSpNotifications 4 }

cItpSpLinkSentUtilChange NOTIFICATION-TYPE
     OBJECTS {
             cItpSpCLLICode,
             cItpSpLinkUtilStateSent,
             cItpSpLinkDisplayName,
             cItpSpLinksetSourceDisplayPC,  
             cItpSpLinksetAdjacentDisplayPC,
             cItpSpLinkUtilizationSent
     }        
     STATUS  current
     DESCRIPTION
             "The notification provide is generated when 
              the cItpSpLinkUtilStateSent changes states."
              
     ::= { cItpSpNotifications 5 }

--
-- Conformance Information
--
cItpSpMIBCompliances OBJECT IDENTIFIER ::=
        { cItpSpMIBConformance 1 }
cItpSpMIBGroups      OBJECT IDENTIFIER ::=
        { cItpSpMIBConformance 2 }

-- Compliance

cItpSpMIBCompliance MODULE-COMPLIANCE
        STATUS deprecated -- superceded by cItpSpMIBComplianceRev1
        DESCRIPTION
                "The compliance statement for entities which implement
                the Cisco SP MIB"
        MODULE -- this module
                MANDATORY-GROUPS {
                        cItpSpScalarsGroup,
                        cItpSpPointCodeGroup,
                        cItpSpLinksetGroup,
                        cItpSpLinkGroup,
                        cItpSpNotificationsEnableGroup,
                        cItpSpNotificationsGroup
                }
                
         
         OBJECT           cItpSpVariant                   
         MIN-ACCESS       read-only
         DESCRIPTION      "Create/Write access is not required."
         
         OBJECT           cItpSpCLLICode                  
         MIN-ACCESS       read-only
         DESCRIPTION      "Create/Write access is not required."
         
         OBJECT           cItpSpDisplayName               
         MIN-ACCESS       read-only
         DESCRIPTION      "Create/Write access is not required."
         
         OBJECT           cItpSpDescription               
         MIN-ACCESS       read-only
         DESCRIPTION      "Create/Write access is not required."
         
         OBJECT           cItpSpMtp2T01                   
         MIN-ACCESS       read-only
         DESCRIPTION      "Create/Write access is not required."
         
         OBJECT           cItpSpMtp2T02                   
         MIN-ACCESS       read-only
         DESCRIPTION      "Create/Write access is not required."
         
         OBJECT           cItpSpMtp2T03                   
         MIN-ACCESS       read-only
         DESCRIPTION      "Create/Write access is not required."
         
         OBJECT           cItpSpMtp2T04E                  
         MIN-ACCESS       read-only
         DESCRIPTION      "Create/Write access is not required."
         
         OBJECT           cItpSpMtp2T04N                  
         MIN-ACCESS       read-only
         DESCRIPTION      "Create/Write access is not required."
         
         OBJECT           cItpSpMtp2T05                   
         MIN-ACCESS       read-only
         DESCRIPTION      "Create/Write access is not required."
         
         OBJECT           cItpSpMtp2T06                   
         MIN-ACCESS       read-only
         DESCRIPTION      "Create/Write access is not required."
         
         OBJECT           cItpSpMtp2T07                   
         MIN-ACCESS       read-only
         DESCRIPTION      "Create/Write access is not required."
         
         OBJECT           cItpSpMtp3T01                   
         MIN-ACCESS       read-only
         DESCRIPTION      "Create/Write access is not required."
         
         OBJECT           cItpSpMtp3T02                   
         MIN-ACCESS       read-only
         DESCRIPTION      "Create/Write access is not required."
         
         OBJECT           cItpSpMtp3T03                   
         MIN-ACCESS       read-only
         DESCRIPTION      "Create/Write access is not required."
         
         OBJECT           cItpSpMtp3T04                   
         MIN-ACCESS       read-only
         DESCRIPTION      "Create/Write access is not required."
         
         OBJECT           cItpSpMtp3T05                   
         MIN-ACCESS       read-only
         DESCRIPTION      "Create/Write access is not required."
         
         OBJECT           cItpSpMtp3T06                   
         MIN-ACCESS       read-only
         DESCRIPTION      "Create/Write access is not required."
         
         OBJECT           cItpSpMtp3T07                   
         MIN-ACCESS       read-only
         DESCRIPTION      "Create/Write access is not required."
         
         OBJECT           cItpSpMtp3T08                   
         MIN-ACCESS       read-only
         DESCRIPTION      "Create/Write access is not required."
         
         OBJECT           cItpSpMtp3T10                   
         MIN-ACCESS       read-only
         DESCRIPTION      "Create/Write access is not required."
         
         OBJECT           cItpSpMtp3T11                   
         MIN-ACCESS       read-only
         DESCRIPTION      "Create/Write access is not required."
         
         OBJECT           cItpSpMtp3T12                   
         MIN-ACCESS       read-only
         DESCRIPTION      "Create/Write access is not required."
         
         OBJECT           cItpSpMtp3T13                   
         MIN-ACCESS       read-only
         DESCRIPTION      "Create/Write access is not required."
         
         OBJECT           cItpSpMtp3T14                   
         MIN-ACCESS       read-only
         DESCRIPTION      "Create/Write access is not required."
         
         OBJECT           cItpSpMtp3T15                   
         MIN-ACCESS       read-only
         DESCRIPTION      "Create/Write access is not required."
         
         OBJECT           cItpSpMtp3T16                   
         MIN-ACCESS       read-only
         DESCRIPTION      "Create/Write access is not required."
         
         OBJECT           cItpSpMtp3T17                   
         MIN-ACCESS       read-only
         DESCRIPTION      "Create/Write access is not required."
         
         OBJECT           cItpSpMtp3T18                   
         MIN-ACCESS       read-only
         DESCRIPTION      "Create/Write access is not required."
         
         OBJECT           cItpSpMtp3T19                   
         MIN-ACCESS       read-only
         DESCRIPTION      "Create/Write access is not required."
         
         OBJECT           cItpSpMtp3T20                   
         MIN-ACCESS       read-only
         DESCRIPTION      "Create/Write access is not required."
         
         OBJECT           cItpSpMtp3T21                   
         MIN-ACCESS       read-only
         DESCRIPTION      "Create/Write access is not required."
         
         OBJECT           cItpSpMtp3T22                   
         MIN-ACCESS       read-only
         DESCRIPTION      "Create/Write access is not required."
         
         OBJECT           cItpSpMtp3T23                   
         MIN-ACCESS       read-only
         DESCRIPTION      "Create/Write access is not required."
         
         OBJECT           cItpSpMtp3T24                   
         MIN-ACCESS       read-only
         DESCRIPTION      "Create/Write access is not required."
         
         OBJECT           cItpSpMtp3T25                   
         MIN-ACCESS       read-only
         DESCRIPTION      "Create/Write access is not required."
         
         OBJECT           cItpSpMtp3T26                   
         MIN-ACCESS       read-only
         DESCRIPTION      "Create/Write access is not required."
         
         OBJECT           cItpSpMtp3T27                   
         MIN-ACCESS       read-only
         DESCRIPTION      "Create/Write access is not required."
         
         OBJECT           cItpSpMtp3T28                   
         MIN-ACCESS       read-only
         DESCRIPTION      "Create/Write access is not required."
         
         OBJECT           cItpSpMtp3T29                   
         MIN-ACCESS       read-only
         DESCRIPTION      "Create/Write access is not required."
         
         OBJECT           cItpSpMtp3T30                   
         MIN-ACCESS       read-only
         DESCRIPTION      "Create/Write access is not required."
         
         OBJECT           cItpSpMtp3T31                   
         MIN-ACCESS       read-only
         DESCRIPTION      "Create/Write access is not required."
         
         OBJECT           cItpSpMtp3T32                   
         MIN-ACCESS       read-only
         DESCRIPTION      "Create/Write access is not required."
         
         OBJECT           cItpSpMtp3T33                   
         MIN-ACCESS       read-only
         DESCRIPTION      "Create/Write access is not required."
         
         OBJECT           cItpSpMtp3T34                   
         MIN-ACCESS       read-only
         DESCRIPTION      "Create/Write access is not required."
         
         OBJECT           cItpSpTimerLinkTest             
         MIN-ACCESS       read-only
         DESCRIPTION      "Create/Write access is not required."
         
         OBJECT           cItpSpTimerLinkMessage          
         MIN-ACCESS       read-only
         DESCRIPTION      "Create/Write access is not required."
         
         OBJECT           cItpSpTimerLinkActRetry         
         MIN-ACCESS       read-only
         DESCRIPTION      "Create/Write access is not required."
         
         OBJECT           cItpSpTFR
         MIN-ACCESS       read-only
         DESCRIPTION      "Create/Write access is not required."
         
         OBJECT           cItpSpCongestionsLevels
         MIN-ACCESS       read-only
         DESCRIPTION      "Create/Write access is not required."
         
         OBJECT           cItpSpFastRestart 
         MIN-ACCESS       read-only
         DESCRIPTION      "Create/Write access is not required."
         
         OBJECT           cItpSpPointCodeType       
         MIN-ACCESS       read-only
         DESCRIPTION      "Create/Write access is not required."
         
         OBJECT           cItpSpPointCodeRowStatus       
         MIN-ACCESS       read-only
         DESCRIPTION      "Create/Write access is not required."
         
         OBJECT           cItpSpLinksetSourcePointCode    
         MIN-ACCESS       read-only
         DESCRIPTION      "Create/Write access is not required."
         
         OBJECT           cItpSpLinksetAdjacentPointCode  
         MIN-ACCESS       read-only
         DESCRIPTION      "Create/Write access is not required."
         
         OBJECT           cItpSpLinksetInboundAcl         
         MIN-ACCESS       read-only
         DESCRIPTION      "Create/Write access is not required."
         
         OBJECT           cItpSpLinksetOutboundAcl        
         MIN-ACCESS       read-only
         DESCRIPTION      "Create/Write access is not required."
         
         OBJECT           cItpSpLinksetSnmmRTN            
         MIN-ACCESS       read-only
         DESCRIPTION      "Create/Write access is not required."
         
         OBJECT           cItpSpLinksetSntmRTN            
         MIN-ACCESS       read-only
         DESCRIPTION      "Create/Write access is not required."
         
         OBJECT           cItpSpLinksetSpare2RTN          
         MIN-ACCESS       read-only
         DESCRIPTION      "Create/Write access is not required."
         
         OBJECT           cItpSpLinksetSccpRTN            
         MIN-ACCESS       read-only
         DESCRIPTION      "Create/Write access is not required."
         
         OBJECT           cItpSpLinksetTupRTN             
         MIN-ACCESS       read-only
         DESCRIPTION      "Create/Write access is not required."
         
         OBJECT           cItpSpLinksetIsupRTN            
         MIN-ACCESS       read-only
         DESCRIPTION      "Create/Write access is not required."
         
         OBJECT           cItpSpLinksetDupcRTN            
         MIN-ACCESS       read-only
         DESCRIPTION      "Create/Write access is not required."
         
         OBJECT           cItpSpLinksetDupfRTN            
         MIN-ACCESS       read-only
         DESCRIPTION      "Create/Write access is not required."
         
         OBJECT           cItpSpLinksetMtupRTN            
         MIN-ACCESS       read-only
         DESCRIPTION      "Create/Write access is not required."
         
         OBJECT           cItpSpLinksetBisupRTN           
         MIN-ACCESS       read-only
         DESCRIPTION      "Create/Write access is not required."
         
         OBJECT           cItpSpLinksetSisupRTN           
         MIN-ACCESS       read-only
         DESCRIPTION      "Create/Write access is not required."
         
         OBJECT           cItpSpLinksetSpare11RTN         
         MIN-ACCESS       read-only
         DESCRIPTION      "Create/Write access is not required."
         
         OBJECT           cItpSpLinksetSpare12RTN         
         MIN-ACCESS       read-only
         DESCRIPTION      "Create/Write access is not required."
         
         OBJECT           cItpSpLinksetSpare13RTN         
         MIN-ACCESS       read-only
         DESCRIPTION      "Create/Write access is not required."
         
         OBJECT           cItpSpLinksetSpare14RTN         
         MIN-ACCESS       read-only
         DESCRIPTION      "Create/Write access is not required."
         
         OBJECT           cItpSpLinksetSpare15RTN         
         MIN-ACCESS       read-only
         DESCRIPTION      "Create/Write access is not required."
         
         OBJECT           cItpSpLinksetAccountingEnabled  
         MIN-ACCESS       read-only
         DESCRIPTION      "Create/Write access is not required."
         
         OBJECT           cItpSpLinksetMtp2T01            
         MIN-ACCESS       read-only
         DESCRIPTION      "Create/Write access is not required."
         
         OBJECT           cItpSpLinksetMtp2T02            
         MIN-ACCESS       read-only
         DESCRIPTION      "Create/Write access is not required."
         
         OBJECT           cItpSpLinksetMtp2T03            
         MIN-ACCESS       read-only
         DESCRIPTION      "Create/Write access is not required."
         
         OBJECT           cItpSpLinksetMtp2T04E           
         MIN-ACCESS       read-only
         DESCRIPTION      "Create/Write access is not required."
         
         OBJECT           cItpSpLinksetMtp2T04N           
         MIN-ACCESS       read-only
         DESCRIPTION      "Create/Write access is not required."
         
         OBJECT           cItpSpLinksetMtp2T05            
         MIN-ACCESS       read-only
         DESCRIPTION      "Create/Write access is not required."
         
         OBJECT           cItpSpLinksetMtp2T06            
         MIN-ACCESS       read-only
         DESCRIPTION      "Create/Write access is not required."
         
         OBJECT           cItpSpLinksetMtp2T07            
         MIN-ACCESS       read-only
         DESCRIPTION      "Create/Write access is not required."
         
         OBJECT           cItpSpLinksetMtp3T01            
         MIN-ACCESS       read-only
         DESCRIPTION      "Create/Write access is not required."
         
         OBJECT           cItpSpLinksetMtp3T02            
         MIN-ACCESS       read-only
         DESCRIPTION      "Create/Write access is not required."
         
         OBJECT           cItpSpLinksetMtp3T03            
         MIN-ACCESS       read-only
         DESCRIPTION      "Create/Write access is not required."
         
         OBJECT           cItpSpLinksetMtp3T04            
         MIN-ACCESS       read-only
         DESCRIPTION      "Create/Write access is not required."
         
         OBJECT           cItpSpLinksetMtp3T05            
         MIN-ACCESS       read-only
         DESCRIPTION      "Create/Write access is not required."
         
         OBJECT           cItpSpLinksetMtp3T06            
         MIN-ACCESS       read-only
         DESCRIPTION      "Create/Write access is not required."
         
         OBJECT           cItpSpLinksetMtp3T07            
         MIN-ACCESS       read-only
         DESCRIPTION      "Create/Write access is not required."
         
         OBJECT           cItpSpLinksetMtp3T08            
         MIN-ACCESS       read-only
         DESCRIPTION      "Create/Write access is not required."
         
         OBJECT           cItpSpLinksetMtp3T10            
         MIN-ACCESS       read-only
         DESCRIPTION      "Create/Write access is not required."
         
         OBJECT           cItpSpLinksetMtp3T11            
         MIN-ACCESS       read-only
         DESCRIPTION      "Create/Write access is not required."
         
         OBJECT           cItpSpLinksetMtp3T12            
         MIN-ACCESS       read-only
         DESCRIPTION      "Create/Write access is not required."
         
         OBJECT           cItpSpLinksetMtp3T13            
         MIN-ACCESS       read-only
         DESCRIPTION      "Create/Write access is not required."
         
         OBJECT           cItpSpLinksetMtp3T14            
         MIN-ACCESS       read-only
         DESCRIPTION      "Create/Write access is not required."
         
         OBJECT           cItpSpLinksetMtp3T15            
         MIN-ACCESS       read-only
         DESCRIPTION      "Create/Write access is not required."
         
         OBJECT           cItpSpLinksetMtp3T16            
         MIN-ACCESS       read-only
         DESCRIPTION      "Create/Write access is not required."
         
         OBJECT           cItpSpLinksetMtp3T17            
         MIN-ACCESS       read-only
         DESCRIPTION      "Create/Write access is not required."
         
         OBJECT           cItpSpLinksetMtp3T18            
         MIN-ACCESS       read-only
         DESCRIPTION      "Create/Write access is not required."
         
         OBJECT           cItpSpLinksetMtp3T19            
         MIN-ACCESS       read-only
         DESCRIPTION      "Create/Write access is not required."
         
         OBJECT           cItpSpLinksetMtp3T20            
         MIN-ACCESS       read-only
         DESCRIPTION      "Create/Write access is not required."
         
         OBJECT           cItpSpLinksetMtp3T21            
         MIN-ACCESS       read-only
         DESCRIPTION      "Create/Write access is not required."
         
         OBJECT           cItpSpLinksetMtp3T22            
         MIN-ACCESS       read-only
         DESCRIPTION      "Create/Write access is not required."
         
         OBJECT           cItpSpLinksetMtp3T23            
         MIN-ACCESS       read-only
         DESCRIPTION      "Create/Write access is not required."
         
         OBJECT           cItpSpLinksetMtp3T24            
         MIN-ACCESS       read-only
         DESCRIPTION      "Create/Write access is not required."
         
         OBJECT           cItpSpLinksetMtp3T25            
         MIN-ACCESS       read-only
         DESCRIPTION      "Create/Write access is not required."
         
         OBJECT           cItpSpLinksetMtp3T26            
         MIN-ACCESS       read-only
         DESCRIPTION      "Create/Write access is not required."
         
         OBJECT           cItpSpLinksetMtp3T27            
         MIN-ACCESS       read-only
         DESCRIPTION      "Create/Write access is not required."
         
         OBJECT           cItpSpLinksetMtp3T28            
         MIN-ACCESS       read-only
         DESCRIPTION      "Create/Write access is not required."
         
         OBJECT           cItpSpLinksetMtp3T29            
         MIN-ACCESS       read-only
         DESCRIPTION      "Create/Write access is not required."
         
         OBJECT           cItpSpLinksetMtp3T30            
         MIN-ACCESS       read-only
         DESCRIPTION      "Create/Write access is not required."
         
         OBJECT           cItpSpLinksetMtp3T31            
         MIN-ACCESS       read-only
         DESCRIPTION      "Create/Write access is not required."
         
         OBJECT           cItpSpLinksetMtp3T32            
         MIN-ACCESS       read-only
         DESCRIPTION      "Create/Write access is not required."
         
         OBJECT           cItpSpLinksetMtp3T33            
         MIN-ACCESS       read-only
         DESCRIPTION      "Create/Write access is not required."
         
         OBJECT           cItpSpLinksetMtp3T34            
         MIN-ACCESS       read-only
         DESCRIPTION      "Create/Write access is not required."
         
         OBJECT           cItpSpLinksetTimerLinkTest      
         MIN-ACCESS       read-only
         DESCRIPTION      "Create/Write access is not required."
         
         OBJECT           cItpSpLinksetTimerLinkMessage   
         MIN-ACCESS       read-only
         DESCRIPTION      "Create/Write access is not required."
         
         OBJECT           cItpSpLinksetTimerLinkActRetry  
         MIN-ACCESS       read-only
         DESCRIPTION      "Create/Write access is not required."
         
         OBJECT           cItpSpLinksetPlanCapacity       
         MIN-ACCESS       read-only
         DESCRIPTION      "Create/Write access is not required."
         
         OBJECT           cItpSpLinksetActPriority        
         MIN-ACCESS       read-only
         DESCRIPTION      "Create/Write access is not required."
         
         OBJECT           cItpSpLinksetType               
         MIN-ACCESS       read-only
         DESCRIPTION      "Create/Write access is not required."
         
         OBJECT           cItpSpLinksetRowStatus                  
         MIN-ACCESS       read-only
         DESCRIPTION      "Create/Write access is not required."
         
         OBJECT           cItpSpLinksetNi
         MIN-ACCESS       read-only
         DESCRIPTION      "Create/Write access is not required."
         
         OBJECT           cItpSpLinksetDisplayName
         MIN-ACCESS       read-only
         DESCRIPTION      "Create/Write access is not required."
         
         OBJECT           cItpSpLinksetDescription
         MIN-ACCESS       read-only
         DESCRIPTION      "Create/Write access is not required."
         
         OBJECT           cItpSpLinkDescription                  
         MIN-ACCESS       read-only
         DESCRIPTION      "Create/Write access is not required."
         
         OBJECT           cItpSpLinkType                  
         MIN-ACCESS       read-only
         DESCRIPTION      "Create/Write access is not required."
         
         OBJECT           cItpSpLinkifIndex               
         MIN-ACCESS       read-only
         DESCRIPTION      "Create/Write access is not required."
         
         OBJECT           cItpSpLinkMtp2T01               
         MIN-ACCESS       read-only
         DESCRIPTION      "Create/Write access is not required."
         
         OBJECT           cItpSpLinkMtp2T02               
         MIN-ACCESS       read-only
         DESCRIPTION      "Create/Write access is not required."
         
         OBJECT           cItpSpLinkMtp2T03               
         MIN-ACCESS       read-only
         DESCRIPTION      "Create/Write access is not required."
         
         OBJECT           cItpSpLinkMtp2T04E              
         MIN-ACCESS       read-only
         DESCRIPTION      "Create/Write access is not required."
         
         OBJECT           cItpSpLinkMtp2T04N              
         MIN-ACCESS       read-only
         DESCRIPTION      "Create/Write access is not required."
         
         OBJECT           cItpSpLinkMtp2T05               
         MIN-ACCESS       read-only
         DESCRIPTION      "Create/Write access is not required."
         
         OBJECT           cItpSpLinkMtp2T06               
         MIN-ACCESS       read-only
         DESCRIPTION      "Create/Write access is not required."
         
         OBJECT           cItpSpLinkMtp2T07               
         MIN-ACCESS       read-only
         DESCRIPTION      "Create/Write access is not required."
         
         OBJECT           cItpSpLinkMtp3T01               
         MIN-ACCESS       read-only
         DESCRIPTION      "Create/Write access is not required."
         
         OBJECT           cItpSpLinkMtp3T02               
         MIN-ACCESS       read-only
         DESCRIPTION      "Create/Write access is not required."
         
         OBJECT           cItpSpLinkMtp3T03               
         MIN-ACCESS       read-only
         DESCRIPTION      "Create/Write access is not required."
         
         OBJECT           cItpSpLinkMtp3T04               
         MIN-ACCESS       read-only
         DESCRIPTION      "Create/Write access is not required."
         
         OBJECT           cItpSpLinkMtp3T05               
         MIN-ACCESS       read-only
         DESCRIPTION      "Create/Write access is not required."
         
         OBJECT           cItpSpLinkMtp3T06               
         MIN-ACCESS       read-only
         DESCRIPTION      "Create/Write access is not required."
         
         OBJECT           cItpSpLinkMtp3T07               
         MIN-ACCESS       read-only
         DESCRIPTION      "Create/Write access is not required."
         
         OBJECT           cItpSpLinkMtp3T08               
         MIN-ACCESS       read-only
         DESCRIPTION      "Create/Write access is not required."
         
         OBJECT           cItpSpLinkMtp3T10               
         MIN-ACCESS       read-only
         DESCRIPTION      "Create/Write access is not required."
         
         OBJECT           cItpSpLinkMtp3T11               
         MIN-ACCESS       read-only
         DESCRIPTION      "Create/Write access is not required."
         
         OBJECT           cItpSpLinkMtp3T12               
         MIN-ACCESS       read-only
         DESCRIPTION      "Create/Write access is not required."
         
         OBJECT           cItpSpLinkMtp3T13               
         MIN-ACCESS       read-only
         DESCRIPTION      "Create/Write access is not required."
         
         OBJECT           cItpSpLinkMtp3T14               
         MIN-ACCESS       read-only
         DESCRIPTION      "Create/Write access is not required."
         
         OBJECT           cItpSpLinkMtp3T15               
         MIN-ACCESS       read-only
         DESCRIPTION      "Create/Write access is not required."
         
         OBJECT           cItpSpLinkMtp3T16               
         MIN-ACCESS       read-only
         DESCRIPTION      "Create/Write access is not required."
         
         OBJECT           cItpSpLinkMtp3T17               
         MIN-ACCESS       read-only
         DESCRIPTION      "Create/Write access is not required."
         
         OBJECT           cItpSpLinkMtp3T18               
         MIN-ACCESS       read-only
         DESCRIPTION      "Create/Write access is not required."
         
         OBJECT           cItpSpLinkMtp3T19               
         MIN-ACCESS       read-only
         DESCRIPTION      "Create/Write access is not required."
         
         OBJECT           cItpSpLinkMtp3T20               
         MIN-ACCESS       read-only
         DESCRIPTION      "Create/Write access is not required."
         
         OBJECT           cItpSpLinkMtp3T21               
         MIN-ACCESS       read-only
         DESCRIPTION      "Create/Write access is not required."
         
         OBJECT           cItpSpLinkMtp3T22               
         MIN-ACCESS       read-only
         DESCRIPTION      "Create/Write access is not required."
         
         OBJECT           cItpSpLinkMtp3T23               
         MIN-ACCESS       read-only
         DESCRIPTION      "Create/Write access is not required."
         
         OBJECT           cItpSpLinkMtp3T24               
         MIN-ACCESS       read-only
         DESCRIPTION      "Create/Write access is not required."
         
         OBJECT           cItpSpLinkMtp3T25               
         MIN-ACCESS       read-only
         DESCRIPTION      "Create/Write access is not required."
         
         OBJECT           cItpSpLinkMtp3T26               
         MIN-ACCESS       read-only
         DESCRIPTION      "Create/Write access is not required."
         
         OBJECT           cItpSpLinkMtp3T27               
         MIN-ACCESS       read-only
         DESCRIPTION      "Create/Write access is not required."
         
         OBJECT           cItpSpLinkMtp3T28               
         MIN-ACCESS       read-only
         DESCRIPTION      "Create/Write access is not required."
         
         OBJECT           cItpSpLinkMtp3T29               
         MIN-ACCESS       read-only
         DESCRIPTION      "Create/Write access is not required."
         
         OBJECT           cItpSpLinkMtp3T30               
         MIN-ACCESS       read-only
         DESCRIPTION      "Create/Write access is not required."
         
         OBJECT           cItpSpLinkMtp3T31               
         MIN-ACCESS       read-only
         DESCRIPTION      "Create/Write access is not required."
         
         OBJECT           cItpSpLinkMtp3T32               
         MIN-ACCESS       read-only
         DESCRIPTION      "Create/Write access is not required."
         
         OBJECT           cItpSpLinkMtp3T33               
         MIN-ACCESS       read-only
         DESCRIPTION      "Create/Write access is not required."
         
         OBJECT           cItpSpLinkMtp3T34               
         MIN-ACCESS       read-only
         DESCRIPTION      "Create/Write access is not required."
         
         OBJECT           cItpSpLinkTimerLinkTest        
         MIN-ACCESS       read-only
         DESCRIPTION      "Create/Write access is not required."
         
         OBJECT           cItpSpLinkTimerLinkMessage     
         MIN-ACCESS       read-only
         DESCRIPTION      "Create/Write access is not required."
         
         OBJECT           cItpSpLinkTimerLinkActRetry    
         MIN-ACCESS       read-only
         DESCRIPTION      "Create/Write access is not required."

         OBJECT           cItpSpLinkXmitQueueDepthHigh
         MIN-ACCESS       read-only
         DESCRIPTION      "Create/Write access is not required."
         
         OBJECT           cItpSpLinkCongestionAbate1      
         MIN-ACCESS       read-only
         DESCRIPTION      "Create/Write access is not required."
         
         OBJECT           cItpSpLinkCongestionAbate2      
         MIN-ACCESS       read-only
         DESCRIPTION      "Create/Write access is not required."
         
         OBJECT           cItpSpLinkCongestionAbate3      
         MIN-ACCESS       read-only
         DESCRIPTION      "Create/Write access is not required."
         
         OBJECT           cItpSpLinkCongestionOnset1      
         MIN-ACCESS       read-only
         DESCRIPTION      "Create/Write access is not required."
         
         OBJECT           cItpSpLinkCongestionOnset2      
         MIN-ACCESS       read-only
         DESCRIPTION      "Create/Write access is not required."
         
         OBJECT           cItpSpLinkCongestionOnset3      
         MIN-ACCESS       read-only
         DESCRIPTION      "Create/Write access is not required."
         
         OBJECT           cItpSpLinkSigLinkTest           
         MIN-ACCESS       read-only
         DESCRIPTION      "Create/Write access is not required."
         
         OBJECT           cItpSpLinkIPType1               
         MIN-ACCESS       read-only
         DESCRIPTION      "Create/Write access is not required."
         
         OBJECT           cItpSpLinkIPType2               
         MIN-ACCESS       read-only
         DESCRIPTION      "Create/Write access is not required."
         
         OBJECT           cItpSpLinkIPType3               
         MIN-ACCESS       read-only
         DESCRIPTION      "Create/Write access is not required."
         
         OBJECT           cItpSpLinkIPType4               
         MIN-ACCESS       read-only
         DESCRIPTION      "Create/Write access is not required."
         
         OBJECT           cItpSpLinkIPAddr1               
         MIN-ACCESS       read-only
         DESCRIPTION      "Create/Write access is not required."
         
         OBJECT           cItpSpLinkIPAddr2               
         MIN-ACCESS       read-only
         DESCRIPTION      "Create/Write access is not required."
         
         OBJECT           cItpSpLinkIPAddr3               
         MIN-ACCESS       read-only
         DESCRIPTION      "Create/Write access is not required."
         
         OBJECT           cItpSpLinkIPAddr4               
         MIN-ACCESS       read-only
         DESCRIPTION      "Create/Write access is not required."
         
         OBJECT           cItpSpLinkLocalPort             
         MIN-ACCESS       read-only
         DESCRIPTION      "Create/Write access is not required."
         
         OBJECT           cItpSpLinkRemotePort            
         MIN-ACCESS       read-only
         DESCRIPTION      "Create/Write access is not required."
         
         OBJECT           cItpSpLinkQosClass                  
         MIN-ACCESS       read-only
         DESCRIPTION      "Create/Write access is not required."
         
         OBJECT           cItpSpLinkRowStatus                  
         MIN-ACCESS       read-only
         DESCRIPTION      "Create/Write access is not required."
         
         OBJECT           cItpSpLinkDisplayName
         MIN-ACCESS       read-only
         DESCRIPTION      "Create/Write access is not required."
         
        ::= { cItpSpMIBCompliances 1 }
        

cItpSpMIBComplianceRev1 MODULE-COMPLIANCE
        STATUS deprecated -- superceded by cItpSpMIBComplianceRev2
        DESCRIPTION
                "The compliance statement for entities which implement
                the Cisco SP MIB"
        MODULE -- this module
                MANDATORY-GROUPS {
                        cItpSpScalarsGroup,
                        cItpSpPointCodeGroup,
                        cItpSpLinksetGroup,
                        cItpSpLinkGroup,
                        cItpSpNotificationsEnableGroup,
                        cItpSpNotificationsGroup,
                        cItpSpStatsGroup
                }
                
         
         OBJECT           cItpSpVariant                   
         MIN-ACCESS       read-only
         DESCRIPTION      "Create/Write access is not required."
         
         OBJECT           cItpSpCLLICode                  
         MIN-ACCESS       read-only
         DESCRIPTION      "Create/Write access is not required."
         
         OBJECT           cItpSpDisplayName               
         MIN-ACCESS       read-only
         DESCRIPTION      "Create/Write access is not required."
         
         OBJECT           cItpSpDescription               
         MIN-ACCESS       read-only
         DESCRIPTION      "Create/Write access is not required."
         
         OBJECT           cItpSpMtp2T01                   
         MIN-ACCESS       read-only
         DESCRIPTION      "Create/Write access is not required."
         
         OBJECT           cItpSpMtp2T02                   
         MIN-ACCESS       read-only
         DESCRIPTION      "Create/Write access is not required."
         
         OBJECT           cItpSpMtp2T03                   
         MIN-ACCESS       read-only
         DESCRIPTION      "Create/Write access is not required."
         
         OBJECT           cItpSpMtp2T04E                  
         MIN-ACCESS       read-only
         DESCRIPTION      "Create/Write access is not required."
         
         OBJECT           cItpSpMtp2T04N                  
         MIN-ACCESS       read-only
         DESCRIPTION      "Create/Write access is not required."
         
         OBJECT           cItpSpMtp2T05                   
         MIN-ACCESS       read-only
         DESCRIPTION      "Create/Write access is not required."
         
         OBJECT           cItpSpMtp2T06                   
         MIN-ACCESS       read-only
         DESCRIPTION      "Create/Write access is not required."
         
         OBJECT           cItpSpMtp2T07                   
         MIN-ACCESS       read-only
         DESCRIPTION      "Create/Write access is not required."
         
         OBJECT           cItpSpMtp3T01                   
         MIN-ACCESS       read-only
         DESCRIPTION      "Create/Write access is not required."
         
         OBJECT           cItpSpMtp3T02                   
         MIN-ACCESS       read-only
         DESCRIPTION      "Create/Write access is not required."
         
         OBJECT           cItpSpMtp3T03                   
         MIN-ACCESS       read-only
         DESCRIPTION      "Create/Write access is not required."
         
         OBJECT           cItpSpMtp3T04                   
         MIN-ACCESS       read-only
         DESCRIPTION      "Create/Write access is not required."
         
         OBJECT           cItpSpMtp3T05                   
         MIN-ACCESS       read-only
         DESCRIPTION      "Create/Write access is not required."
         
         OBJECT           cItpSpMtp3T06                   
         MIN-ACCESS       read-only
         DESCRIPTION      "Create/Write access is not required."
         
         OBJECT           cItpSpMtp3T07                   
         MIN-ACCESS       read-only
         DESCRIPTION      "Create/Write access is not required."
         
         OBJECT           cItpSpMtp3T08                   
         MIN-ACCESS       read-only
         DESCRIPTION      "Create/Write access is not required."
         
         OBJECT           cItpSpMtp3T10                   
         MIN-ACCESS       read-only
         DESCRIPTION      "Create/Write access is not required."
         
         OBJECT           cItpSpMtp3T11                   
         MIN-ACCESS       read-only
         DESCRIPTION      "Create/Write access is not required."
         
         OBJECT           cItpSpMtp3T12                   
         MIN-ACCESS       read-only
         DESCRIPTION      "Create/Write access is not required."
         
         OBJECT           cItpSpMtp3T13                   
         MIN-ACCESS       read-only
         DESCRIPTION      "Create/Write access is not required."
         
         OBJECT           cItpSpMtp3T14                   
         MIN-ACCESS       read-only
         DESCRIPTION      "Create/Write access is not required."
         
         OBJECT           cItpSpMtp3T15                   
         MIN-ACCESS       read-only
         DESCRIPTION      "Create/Write access is not required."
         
         OBJECT           cItpSpMtp3T16                   
         MIN-ACCESS       read-only
         DESCRIPTION      "Create/Write access is not required."
         
         OBJECT           cItpSpMtp3T17                   
         MIN-ACCESS       read-only
         DESCRIPTION      "Create/Write access is not required."
         
         OBJECT           cItpSpMtp3T18                   
         MIN-ACCESS       read-only
         DESCRIPTION      "Create/Write access is not required."
         
         OBJECT           cItpSpMtp3T19                   
         MIN-ACCESS       read-only
         DESCRIPTION      "Create/Write access is not required."
         
         OBJECT           cItpSpMtp3T20                   
         MIN-ACCESS       read-only
         DESCRIPTION      "Create/Write access is not required."
         
         OBJECT           cItpSpMtp3T21                   
         MIN-ACCESS       read-only
         DESCRIPTION      "Create/Write access is not required."
         
         OBJECT           cItpSpMtp3T22                   
         MIN-ACCESS       read-only
         DESCRIPTION      "Create/Write access is not required."
         
         OBJECT           cItpSpMtp3T23                   
         MIN-ACCESS       read-only
         DESCRIPTION      "Create/Write access is not required."
         
         OBJECT           cItpSpMtp3T24                   
         MIN-ACCESS       read-only
         DESCRIPTION      "Create/Write access is not required."
         
         OBJECT           cItpSpMtp3T25                   
         MIN-ACCESS       read-only
         DESCRIPTION      "Create/Write access is not required."
         
         OBJECT           cItpSpMtp3T26                   
         MIN-ACCESS       read-only
         DESCRIPTION      "Create/Write access is not required."
         
         OBJECT           cItpSpMtp3T27                   
         MIN-ACCESS       read-only
         DESCRIPTION      "Create/Write access is not required."
         
         OBJECT           cItpSpMtp3T28                   
         MIN-ACCESS       read-only
         DESCRIPTION      "Create/Write access is not required."
         
         OBJECT           cItpSpMtp3T29                   
         MIN-ACCESS       read-only
         DESCRIPTION      "Create/Write access is not required."
         
         OBJECT           cItpSpMtp3T30                   
         MIN-ACCESS       read-only
         DESCRIPTION      "Create/Write access is not required."
         
         OBJECT           cItpSpMtp3T31                   
         MIN-ACCESS       read-only
         DESCRIPTION      "Create/Write access is not required."
         
         OBJECT           cItpSpMtp3T32                   
         MIN-ACCESS       read-only
         DESCRIPTION      "Create/Write access is not required."
         
         OBJECT           cItpSpMtp3T33                   
         MIN-ACCESS       read-only
         DESCRIPTION      "Create/Write access is not required."
         
         OBJECT           cItpSpMtp3T34                   
         MIN-ACCESS       read-only
         DESCRIPTION      "Create/Write access is not required."
         
         OBJECT           cItpSpTimerLinkTest             
         MIN-ACCESS       read-only
         DESCRIPTION      "Create/Write access is not required."
         
         OBJECT           cItpSpTimerLinkMessage          
         MIN-ACCESS       read-only
         DESCRIPTION      "Create/Write access is not required."
         
         OBJECT           cItpSpTimerLinkActRetry         
         MIN-ACCESS       read-only
         DESCRIPTION      "Create/Write access is not required."
         
         OBJECT           cItpSpTFR
         MIN-ACCESS       read-only
         DESCRIPTION      "Create/Write access is not required."
         
         OBJECT           cItpSpCongestionsLevels
         MIN-ACCESS       read-only
         DESCRIPTION      "Create/Write access is not required."
         
         OBJECT           cItpSpFastRestart 
         MIN-ACCESS       read-only
         DESCRIPTION      "Create/Write access is not required."
         
         OBJECT           cItpSpDistSccpUnseq 
         MIN-ACCESS       read-only
         DESCRIPTION      "Create/Write access is not required."
         
         OBJECT           cItpSpSummaryRoutingException
         MIN-ACCESS       read-only
         DESCRIPTION      "Create/Write access is not required."
                                    
         OBJECT           cItpSpPointCodeType       
         MIN-ACCESS       read-only
         DESCRIPTION      "Create/Write access is not required."
         
         OBJECT           cItpSpPointCodeRowStatus       
         MIN-ACCESS       read-only
         DESCRIPTION      "Create/Write access is not required."
         
         OBJECT           cItpSpLinksetSourcePointCode    
         MIN-ACCESS       read-only
         DESCRIPTION      "Create/Write access is not required."
         
         OBJECT           cItpSpLinksetAdjacentPointCode  
         MIN-ACCESS       read-only
         DESCRIPTION      "Create/Write access is not required."
         
         OBJECT           cItpSpLinksetInboundAcl         
         MIN-ACCESS       read-only
         DESCRIPTION      "Create/Write access is not required."
         
         OBJECT           cItpSpLinksetOutboundAcl        
         MIN-ACCESS       read-only
         DESCRIPTION      "Create/Write access is not required."
         
         OBJECT           cItpSpLinksetSnmmRTN            
         MIN-ACCESS       read-only
         DESCRIPTION      "Create/Write access is not required."
         
         OBJECT           cItpSpLinksetSntmRTN            
         MIN-ACCESS       read-only
         DESCRIPTION      "Create/Write access is not required."
         
         OBJECT           cItpSpLinksetSpare2RTN          
         MIN-ACCESS       read-only
         DESCRIPTION      "Create/Write access is not required."
         
         OBJECT           cItpSpLinksetSccpRTN            
         MIN-ACCESS       read-only
         DESCRIPTION      "Create/Write access is not required."
         
         OBJECT           cItpSpLinksetTupRTN             
         MIN-ACCESS       read-only
         DESCRIPTION      "Create/Write access is not required."
         
         OBJECT           cItpSpLinksetIsupRTN            
         MIN-ACCESS       read-only
         DESCRIPTION      "Create/Write access is not required."
         
         OBJECT           cItpSpLinksetDupcRTN            
         MIN-ACCESS       read-only
         DESCRIPTION      "Create/Write access is not required."
         
         OBJECT           cItpSpLinksetDupfRTN            
         MIN-ACCESS       read-only
         DESCRIPTION      "Create/Write access is not required."
         
         OBJECT           cItpSpLinksetMtupRTN            
         MIN-ACCESS       read-only
         DESCRIPTION      "Create/Write access is not required."
         
         OBJECT           cItpSpLinksetBisupRTN           
         MIN-ACCESS       read-only
         DESCRIPTION      "Create/Write access is not required."
         
         OBJECT           cItpSpLinksetSisupRTN           
         MIN-ACCESS       read-only
         DESCRIPTION      "Create/Write access is not required."
         
         OBJECT           cItpSpLinksetSpare11RTN         
         MIN-ACCESS       read-only
         DESCRIPTION      "Create/Write access is not required."
         
         OBJECT           cItpSpLinksetSpare12RTN         
         MIN-ACCESS       read-only
         DESCRIPTION      "Create/Write access is not required."
         
         OBJECT           cItpSpLinksetSpare13RTN         
         MIN-ACCESS       read-only
         DESCRIPTION      "Create/Write access is not required."
         
         OBJECT           cItpSpLinksetSpare14RTN         
         MIN-ACCESS       read-only
         DESCRIPTION      "Create/Write access is not required."
         
         OBJECT           cItpSpLinksetSpare15RTN         
         MIN-ACCESS       read-only
         DESCRIPTION      "Create/Write access is not required."
         
         OBJECT           cItpSpLinksetAccountingEnabled  
         MIN-ACCESS       read-only
         DESCRIPTION      "Create/Write access is not required."
         
         OBJECT           cItpSpLinksetMtp2T01            
         MIN-ACCESS       read-only
         DESCRIPTION      "Create/Write access is not required."
         
         OBJECT           cItpSpLinksetMtp2T02            
         MIN-ACCESS       read-only
         DESCRIPTION      "Create/Write access is not required."
         
         OBJECT           cItpSpLinksetMtp2T03            
         MIN-ACCESS       read-only
         DESCRIPTION      "Create/Write access is not required."
         
         OBJECT           cItpSpLinksetMtp2T04E           
         MIN-ACCESS       read-only
         DESCRIPTION      "Create/Write access is not required."
         
         OBJECT           cItpSpLinksetMtp2T04N           
         MIN-ACCESS       read-only
         DESCRIPTION      "Create/Write access is not required."
         
         OBJECT           cItpSpLinksetMtp2T05            
         MIN-ACCESS       read-only
         DESCRIPTION      "Create/Write access is not required."
         
         OBJECT           cItpSpLinksetMtp2T06            
         MIN-ACCESS       read-only
         DESCRIPTION      "Create/Write access is not required."
         
         OBJECT           cItpSpLinksetMtp2T07            
         MIN-ACCESS       read-only
         DESCRIPTION      "Create/Write access is not required."
         
         OBJECT           cItpSpLinksetMtp3T01            
         MIN-ACCESS       read-only
         DESCRIPTION      "Create/Write access is not required."
         
         OBJECT           cItpSpLinksetMtp3T02            
         MIN-ACCESS       read-only
         DESCRIPTION      "Create/Write access is not required."
         
         OBJECT           cItpSpLinksetMtp3T03            
         MIN-ACCESS       read-only
         DESCRIPTION      "Create/Write access is not required."
         
         OBJECT           cItpSpLinksetMtp3T04            
         MIN-ACCESS       read-only
         DESCRIPTION      "Create/Write access is not required."
         
         OBJECT           cItpSpLinksetMtp3T05            
         MIN-ACCESS       read-only
         DESCRIPTION      "Create/Write access is not required."
         
         OBJECT           cItpSpLinksetMtp3T06            
         MIN-ACCESS       read-only
         DESCRIPTION      "Create/Write access is not required."
         
         OBJECT           cItpSpLinksetMtp3T07
         MIN-ACCESS       read-only
         DESCRIPTION      "Create/Write access is not required."
         
         OBJECT           cItpSpLinksetMtp3T08            
         MIN-ACCESS       read-only
         DESCRIPTION      "Create/Write access is not required."
         
         OBJECT           cItpSpLinksetMtp3T10            
         MIN-ACCESS       read-only
         DESCRIPTION      "Create/Write access is not required."
         
         OBJECT           cItpSpLinksetMtp3T11            
         MIN-ACCESS       read-only
         DESCRIPTION      "Create/Write access is not required."
         
         OBJECT           cItpSpLinksetMtp3T12            
         MIN-ACCESS       read-only
         DESCRIPTION      "Create/Write access is not required."
         
         OBJECT           cItpSpLinksetMtp3T13            
         MIN-ACCESS       read-only
         DESCRIPTION      "Create/Write access is not required."
         
         OBJECT           cItpSpLinksetMtp3T14            
         MIN-ACCESS       read-only
         DESCRIPTION      "Create/Write access is not required."
         
         OBJECT           cItpSpLinksetMtp3T15            
         MIN-ACCESS       read-only
         DESCRIPTION      "Create/Write access is not required."
         
         OBJECT           cItpSpLinksetMtp3T16            
         MIN-ACCESS       read-only
         DESCRIPTION      "Create/Write access is not required."
         
         OBJECT           cItpSpLinksetMtp3T17            
         MIN-ACCESS       read-only
         DESCRIPTION      "Create/Write access is not required."
         
         OBJECT           cItpSpLinksetMtp3T18            
         MIN-ACCESS       read-only
         DESCRIPTION      "Create/Write access is not required."
         
         OBJECT           cItpSpLinksetMtp3T19            
         MIN-ACCESS       read-only
         DESCRIPTION      "Create/Write access is not required."
         
         OBJECT           cItpSpLinksetMtp3T20            
         MIN-ACCESS       read-only
         DESCRIPTION      "Create/Write access is not required."
         
         OBJECT           cItpSpLinksetMtp3T21            
         MIN-ACCESS       read-only
         DESCRIPTION      "Create/Write access is not required."
         
         OBJECT           cItpSpLinksetMtp3T22            
         MIN-ACCESS       read-only
         DESCRIPTION      "Create/Write access is not required."
         
         OBJECT           cItpSpLinksetMtp3T23            
         MIN-ACCESS       read-only
         DESCRIPTION      "Create/Write access is not required."
         
         OBJECT           cItpSpLinksetMtp3T24            
         MIN-ACCESS       read-only
         DESCRIPTION      "Create/Write access is not required."
         
         OBJECT           cItpSpLinksetMtp3T25            
         MIN-ACCESS       read-only
         DESCRIPTION      "Create/Write access is not required."
         
         OBJECT           cItpSpLinksetMtp3T26            
         MIN-ACCESS       read-only
         DESCRIPTION      "Create/Write access is not required."
         
         OBJECT           cItpSpLinksetMtp3T27            
         MIN-ACCESS       read-only
         DESCRIPTION      "Create/Write access is not required."
         
         OBJECT           cItpSpLinksetMtp3T28            
         MIN-ACCESS       read-only
         DESCRIPTION      "Create/Write access is not required."
         
         OBJECT           cItpSpLinksetMtp3T29            
         MIN-ACCESS       read-only
         DESCRIPTION      "Create/Write access is not required."
         
         OBJECT           cItpSpLinksetMtp3T30            
         MIN-ACCESS       read-only
         DESCRIPTION      "Create/Write access is not required."
         
         OBJECT           cItpSpLinksetMtp3T31            
         MIN-ACCESS       read-only
         DESCRIPTION      "Create/Write access is not required."
         
         OBJECT           cItpSpLinksetMtp3T32            
         MIN-ACCESS       read-only
         DESCRIPTION      "Create/Write access is not required."
         
         OBJECT           cItpSpLinksetMtp3T33            
         MIN-ACCESS       read-only
         DESCRIPTION      "Create/Write access is not required."
         
         OBJECT           cItpSpLinksetMtp3T34            
         MIN-ACCESS       read-only
         DESCRIPTION      "Create/Write access is not required."
         
         OBJECT           cItpSpLinksetTimerLinkTest      
         MIN-ACCESS       read-only
         DESCRIPTION      "Create/Write access is not required."
         
         OBJECT           cItpSpLinksetTimerLinkMessage   
         MIN-ACCESS       read-only
         DESCRIPTION      "Create/Write access is not required."
         
         OBJECT           cItpSpLinksetTimerLinkActRetry  
         MIN-ACCESS       read-only
         DESCRIPTION      "Create/Write access is not required."
         
         OBJECT           cItpSpLinksetPlanCapacity       
         MIN-ACCESS       read-only
         DESCRIPTION      "Create/Write access is not required."
         
         OBJECT           cItpSpLinksetActPriority        
         MIN-ACCESS       read-only
         DESCRIPTION      "Create/Write access is not required."
         
         OBJECT           cItpSpLinksetType               
         MIN-ACCESS       read-only
         DESCRIPTION      "Create/Write access is not required."
         
         OBJECT           cItpSpLinksetRowStatus                  
         MIN-ACCESS       read-only
         DESCRIPTION      "Create/Write access is not required."
         
         OBJECT           cItpSpLinksetNi
         MIN-ACCESS       read-only
         DESCRIPTION      "Create/Write access is not required."
         
         OBJECT           cItpSpLinksetDisplayName
         MIN-ACCESS       read-only
         DESCRIPTION      "Create/Write access is not required."
         
         OBJECT           cItpSpLinksetDescription
         MIN-ACCESS       read-only
         DESCRIPTION      "Create/Write access is not required."
         
         OBJECT           cItpSpLinksetVariant
         MIN-ACCESS       read-only
         DESCRIPTION      "Create/Write access is not required."
         
         OBJECT           cItpSpLinkDescription                  
         MIN-ACCESS       read-only
         DESCRIPTION      "Create/Write access is not required."
         
         OBJECT           cItpSpLinkType                  
         MIN-ACCESS       read-only
         DESCRIPTION      "Create/Write access is not required."
         
         OBJECT           cItpSpLinkifIndex               
         MIN-ACCESS       read-only
         DESCRIPTION      "Create/Write access is not required."
         
         OBJECT           cItpSpLinkMtp2T01               
         MIN-ACCESS       read-only
         DESCRIPTION      "Create/Write access is not required."
         
         OBJECT           cItpSpLinkMtp2T02               
         MIN-ACCESS       read-only
         DESCRIPTION      "Create/Write access is not required."
         
         OBJECT           cItpSpLinkMtp2T03               
         MIN-ACCESS       read-only
         DESCRIPTION      "Create/Write access is not required."
         
         OBJECT           cItpSpLinkMtp2T04E              
         MIN-ACCESS       read-only
         DESCRIPTION      "Create/Write access is not required."
         
         OBJECT           cItpSpLinkMtp2T04N              
         MIN-ACCESS       read-only
         DESCRIPTION      "Create/Write access is not required."
         
         OBJECT           cItpSpLinkMtp2T05               
         MIN-ACCESS       read-only
         DESCRIPTION      "Create/Write access is not required."
         
         OBJECT           cItpSpLinkMtp2T06               
         MIN-ACCESS       read-only
         DESCRIPTION      "Create/Write access is not required."
         
         OBJECT           cItpSpLinkMtp2T07               
         MIN-ACCESS       read-only
         DESCRIPTION      "Create/Write access is not required."
         
         OBJECT           cItpSpLinkMtp3T01               
         MIN-ACCESS       read-only
         DESCRIPTION      "Create/Write access is not required."
         
         OBJECT           cItpSpLinkMtp3T02               
         MIN-ACCESS       read-only
         DESCRIPTION      "Create/Write access is not required."
         
         OBJECT           cItpSpLinkMtp3T03               
         MIN-ACCESS       read-only
         DESCRIPTION      "Create/Write access is not required."
         
         OBJECT           cItpSpLinkMtp3T04               
         MIN-ACCESS       read-only
         DESCRIPTION      "Create/Write access is not required."
         
         OBJECT           cItpSpLinkMtp3T05               
         MIN-ACCESS       read-only
         DESCRIPTION      "Create/Write access is not required."
         
         OBJECT           cItpSpLinkMtp3T06               
         MIN-ACCESS       read-only
         DESCRIPTION      "Create/Write access is not required."
         
         OBJECT           cItpSpLinkMtp3T07               
         MIN-ACCESS       read-only
         DESCRIPTION      "Create/Write access is not required."
         
         OBJECT           cItpSpLinkMtp3T08               
         MIN-ACCESS       read-only
         DESCRIPTION      "Create/Write access is not required."
         
         OBJECT           cItpSpLinkMtp3T10               
         MIN-ACCESS       read-only
         DESCRIPTION      "Create/Write access is not required."
         
         OBJECT           cItpSpLinkMtp3T11               
         MIN-ACCESS       read-only
         DESCRIPTION      "Create/Write access is not required."
         
         OBJECT           cItpSpLinkMtp3T12               
         MIN-ACCESS       read-only
         DESCRIPTION      "Create/Write access is not required."
         
         OBJECT           cItpSpLinkMtp3T13               
         MIN-ACCESS       read-only
         DESCRIPTION      "Create/Write access is not required."
         
         OBJECT           cItpSpLinkMtp3T14               
         MIN-ACCESS       read-only
         DESCRIPTION      "Create/Write access is not required."
         
         OBJECT           cItpSpLinkMtp3T15               
         MIN-ACCESS       read-only
         DESCRIPTION      "Create/Write access is not required."
         
         OBJECT           cItpSpLinkMtp3T16               
         MIN-ACCESS       read-only
         DESCRIPTION      "Create/Write access is not required."
         
         OBJECT           cItpSpLinkMtp3T17               
         MIN-ACCESS       read-only
         DESCRIPTION      "Create/Write access is not required."
         
         OBJECT           cItpSpLinkMtp3T18               
         MIN-ACCESS       read-only
         DESCRIPTION      "Create/Write access is not required."
         
         OBJECT           cItpSpLinkMtp3T19               
         MIN-ACCESS       read-only
         DESCRIPTION      "Create/Write access is not required."
         
         OBJECT           cItpSpLinkMtp3T20               
         MIN-ACCESS       read-only
         DESCRIPTION      "Create/Write access is not required."
         
         OBJECT           cItpSpLinkMtp3T21               
         MIN-ACCESS       read-only
         DESCRIPTION      "Create/Write access is not required."
         
         OBJECT           cItpSpLinkMtp3T22               
         MIN-ACCESS       read-only
         DESCRIPTION      "Create/Write access is not required."
         
         OBJECT           cItpSpLinkMtp3T23               
         MIN-ACCESS       read-only
         DESCRIPTION      "Create/Write access is not required."
         
         OBJECT           cItpSpLinkMtp3T24               
         MIN-ACCESS       read-only
         DESCRIPTION      "Create/Write access is not required."
         
         OBJECT           cItpSpLinkMtp3T25               
         MIN-ACCESS       read-only
         DESCRIPTION      "Create/Write access is not required."
         
         OBJECT           cItpSpLinkMtp3T26               
         MIN-ACCESS       read-only
         DESCRIPTION      "Create/Write access is not required."
         
         OBJECT           cItpSpLinkMtp3T27               
         MIN-ACCESS       read-only
         DESCRIPTION      "Create/Write access is not required."
         
         OBJECT           cItpSpLinkMtp3T28               
         MIN-ACCESS       read-only
         DESCRIPTION      "Create/Write access is not required."
         
         OBJECT           cItpSpLinkMtp3T29               
         MIN-ACCESS       read-only
         DESCRIPTION      "Create/Write access is not required."
         
         OBJECT           cItpSpLinkMtp3T30               
         MIN-ACCESS       read-only
         DESCRIPTION      "Create/Write access is not required."
         
         OBJECT           cItpSpLinkMtp3T31               
         MIN-ACCESS       read-only
         DESCRIPTION      "Create/Write access is not required."
         
         OBJECT           cItpSpLinkMtp3T32               
         MIN-ACCESS       read-only
         DESCRIPTION      "Create/Write access is not required."
         
         OBJECT           cItpSpLinkMtp3T33               
         MIN-ACCESS       read-only
         DESCRIPTION      "Create/Write access is not required."
         
         OBJECT           cItpSpLinkMtp3T34               
         MIN-ACCESS       read-only
         DESCRIPTION      "Create/Write access is not required."
         
         OBJECT           cItpSpLinkTimerLinkTest        
         MIN-ACCESS       read-only
         DESCRIPTION      "Create/Write access is not required."
         
         OBJECT           cItpSpLinkTimerLinkMessage     
         MIN-ACCESS       read-only
         DESCRIPTION      "Create/Write access is not required."
         
         OBJECT           cItpSpLinkTimerLinkActRetry    
         MIN-ACCESS       read-only
         DESCRIPTION      "Create/Write access is not required."

         OBJECT           cItpSpLinkXmitQueueDepthHigh
         MIN-ACCESS       read-only
         DESCRIPTION      "Create/Write access is not required."
         
         OBJECT           cItpSpLinkCongestionAbate1      
         MIN-ACCESS       read-only
         DESCRIPTION      "Create/Write access is not required."
         
         OBJECT           cItpSpLinkCongestionAbate2      
         MIN-ACCESS       read-only
         DESCRIPTION      "Create/Write access is not required."
         
         OBJECT           cItpSpLinkCongestionAbate3      
         MIN-ACCESS       read-only
         DESCRIPTION      "Create/Write access is not required."
         
         OBJECT           cItpSpLinkCongestionOnset1      
         MIN-ACCESS       read-only
         DESCRIPTION      "Create/Write access is not required."
         
         OBJECT           cItpSpLinkCongestionOnset2      
         MIN-ACCESS       read-only
         DESCRIPTION      "Create/Write access is not required."
         
         OBJECT           cItpSpLinkCongestionOnset3      
         MIN-ACCESS       read-only
         DESCRIPTION      "Create/Write access is not required."
         
         OBJECT           cItpSpLinkSigLinkTest           
         MIN-ACCESS       read-only
         DESCRIPTION      "Create/Write access is not required."
         
         OBJECT           cItpSpLinkIPType1               
         MIN-ACCESS       read-only
         DESCRIPTION      "Create/Write access is not required."
         
         OBJECT           cItpSpLinkIPType2               
         MIN-ACCESS       read-only
         DESCRIPTION      "Create/Write access is not required."
         
         OBJECT           cItpSpLinkIPType3               
         MIN-ACCESS       read-only
         DESCRIPTION      "Create/Write access is not required."
         
         OBJECT           cItpSpLinkIPType4               
         MIN-ACCESS       read-only
         DESCRIPTION      "Create/Write access is not required."
         
         OBJECT           cItpSpLinkIPAddr1               
         MIN-ACCESS       read-only
         DESCRIPTION      "Create/Write access is not required."
         
         OBJECT           cItpSpLinkIPAddr2               
         MIN-ACCESS       read-only
         DESCRIPTION      "Create/Write access is not required."
         
         OBJECT           cItpSpLinkIPAddr3               
         MIN-ACCESS       read-only
         DESCRIPTION      "Create/Write access is not required."
         
         OBJECT           cItpSpLinkIPAddr4               
         MIN-ACCESS       read-only
         DESCRIPTION      "Create/Write access is not required."
         
         OBJECT           cItpSpLinkLocalPort             
         MIN-ACCESS       read-only
         DESCRIPTION      "Create/Write access is not required."
         
         OBJECT           cItpSpLinkRemotePort            
         MIN-ACCESS       read-only
         DESCRIPTION      "Create/Write access is not required."
         
         OBJECT           cItpSpLinkQosClass                  
         MIN-ACCESS       read-only
         DESCRIPTION      "Create/Write access is not required."
         
         OBJECT           cItpSpLinkRowStatus                  
         MIN-ACCESS       read-only
         DESCRIPTION      "Create/Write access is not required."
         
         OBJECT           cItpSpLinkDisplayName
         MIN-ACCESS       read-only
         DESCRIPTION      "Create/Write access is not required."
         
        ::= { cItpSpMIBCompliances 2 }
        
cItpSpMIBComplianceRev2 MODULE-COMPLIANCE
        STATUS current
        DESCRIPTION
                "The compliance statement for entities which implement
                 the Cisco SP MIB"
        MODULE -- this module
                MANDATORY-GROUPS { 
                        cItpSpPointCodeGroup,
                        cItpSpScalarsGroupRev2,
                        cItpSpLinksetGroupRev2,
                        cItpSpLinkGroupRev2,
                        cItpSpNotificationsEnableGroupRev2,
                        cItpSpNotificationsGroupRev2 
                }
                
         
         OBJECT           cItpSpVariant                   
         MIN-ACCESS       read-only
         DESCRIPTION      "Create/Write access is not required."
         
         OBJECT           cItpSpCLLICode                  
         MIN-ACCESS       read-only
         DESCRIPTION      "Create/Write access is not required."
         
         OBJECT           cItpSpDisplayName               
         MIN-ACCESS       read-only
         DESCRIPTION      "Create/Write access is not required."
         
         OBJECT           cItpSpDescription               
         MIN-ACCESS       read-only
         DESCRIPTION      "Create/Write access is not required."
         
         OBJECT           cItpSpMtp2T01                   
         MIN-ACCESS       read-only
         DESCRIPTION      "Create/Write access is not required."
         
         OBJECT           cItpSpMtp2T02                   
         MIN-ACCESS       read-only
         DESCRIPTION      "Create/Write access is not required."
         
         OBJECT           cItpSpMtp2T03                   
         MIN-ACCESS       read-only
         DESCRIPTION      "Create/Write access is not required."
         
         OBJECT           cItpSpMtp2T04E                  
         MIN-ACCESS       read-only
         DESCRIPTION      "Create/Write access is not required."
         
         OBJECT           cItpSpMtp2T04N                  
         MIN-ACCESS       read-only
         DESCRIPTION      "Create/Write access is not required."
         
         OBJECT           cItpSpMtp2T05                   
         MIN-ACCESS       read-only
         DESCRIPTION      "Create/Write access is not required."
         
         OBJECT           cItpSpMtp2T06                   
         MIN-ACCESS       read-only
         DESCRIPTION      "Create/Write access is not required."
         
         OBJECT           cItpSpMtp2T07                   
         MIN-ACCESS       read-only
         DESCRIPTION      "Create/Write access is not required."
         
         OBJECT           cItpSpMtp3T01                   
         MIN-ACCESS       read-only
         DESCRIPTION      "Create/Write access is not required."
         
         OBJECT           cItpSpMtp3T02                   
         MIN-ACCESS       read-only
         DESCRIPTION      "Create/Write access is not required."
         
         OBJECT           cItpSpMtp3T03                   
         MIN-ACCESS       read-only
         DESCRIPTION      "Create/Write access is not required."
         
         OBJECT           cItpSpMtp3T04                   
         MIN-ACCESS       read-only
         DESCRIPTION      "Create/Write access is not required."
         
         OBJECT           cItpSpMtp3T05                   
         MIN-ACCESS       read-only
         DESCRIPTION      "Create/Write access is not required."
         
         OBJECT           cItpSpMtp3T06                   
         MIN-ACCESS       read-only
         DESCRIPTION      "Create/Write access is not required."
         
         OBJECT           cItpSpMtp3T07                   
         MIN-ACCESS       read-only
         DESCRIPTION      "Create/Write access is not required."
         
         OBJECT           cItpSpMtp3T08                   
         MIN-ACCESS       read-only
         DESCRIPTION      "Create/Write access is not required."
         
         OBJECT           cItpSpMtp3T10                   
         MIN-ACCESS       read-only
         DESCRIPTION      "Create/Write access is not required."
         
         OBJECT           cItpSpMtp3T11                   
         MIN-ACCESS       read-only
         DESCRIPTION      "Create/Write access is not required."
         
         OBJECT           cItpSpMtp3T12                   
         MIN-ACCESS       read-only
         DESCRIPTION      "Create/Write access is not required."
         
         OBJECT           cItpSpMtp3T13                   
         MIN-ACCESS       read-only
         DESCRIPTION      "Create/Write access is not required."
         
         OBJECT           cItpSpMtp3T14                   
         MIN-ACCESS       read-only
         DESCRIPTION      "Create/Write access is not required."
         
         OBJECT           cItpSpMtp3T15                   
         MIN-ACCESS       read-only
         DESCRIPTION      "Create/Write access is not required."
         
         OBJECT           cItpSpMtp3T16                   
         MIN-ACCESS       read-only
         DESCRIPTION      "Create/Write access is not required."
         
         OBJECT           cItpSpMtp3T17                   
         MIN-ACCESS       read-only
         DESCRIPTION      "Create/Write access is not required."
         
         OBJECT           cItpSpMtp3T18                   
         MIN-ACCESS       read-only
         DESCRIPTION      "Create/Write access is not required."
         
         OBJECT           cItpSpMtp3T19                   
         MIN-ACCESS       read-only
         DESCRIPTION      "Create/Write access is not required."
         
         OBJECT           cItpSpMtp3T20                   
         MIN-ACCESS       read-only
         DESCRIPTION      "Create/Write access is not required."
         
         OBJECT           cItpSpMtp3T21                   
         MIN-ACCESS       read-only
         DESCRIPTION      "Create/Write access is not required."
         
         OBJECT           cItpSpMtp3T22                   
         MIN-ACCESS       read-only
         DESCRIPTION      "Create/Write access is not required."
         
         OBJECT           cItpSpMtp3T23                   
         MIN-ACCESS       read-only
         DESCRIPTION      "Create/Write access is not required."
         
         OBJECT           cItpSpMtp3T24                   
         MIN-ACCESS       read-only
         DESCRIPTION      "Create/Write access is not required."
         
         OBJECT           cItpSpMtp3T25                   
         MIN-ACCESS       read-only
         DESCRIPTION      "Create/Write access is not required."
         
         OBJECT           cItpSpMtp3T26                   
         MIN-ACCESS       read-only
         DESCRIPTION      "Create/Write access is not required."
         
         OBJECT           cItpSpMtp3T27                   
         MIN-ACCESS       read-only
         DESCRIPTION      "Create/Write access is not required."
         
         OBJECT           cItpSpMtp3T28                   
         MIN-ACCESS       read-only
         DESCRIPTION      "Create/Write access is not required."
         
         OBJECT           cItpSpMtp3T29                   
         MIN-ACCESS       read-only
         DESCRIPTION      "Create/Write access is not required."
         
         OBJECT           cItpSpMtp3T30                   
         MIN-ACCESS       read-only
         DESCRIPTION      "Create/Write access is not required."
         
         OBJECT           cItpSpMtp3T31                   
         MIN-ACCESS       read-only
         DESCRIPTION      "Create/Write access is not required."
         
         OBJECT           cItpSpMtp3T32                   
         MIN-ACCESS       read-only
         DESCRIPTION      "Create/Write access is not required."
         
         OBJECT           cItpSpMtp3T33                   
         MIN-ACCESS       read-only
         DESCRIPTION      "Create/Write access is not required."
         
         OBJECT           cItpSpMtp3T34                   
         MIN-ACCESS       read-only
         DESCRIPTION      "Create/Write access is not required."
         
         OBJECT           cItpSpTimerLinkTest             
         MIN-ACCESS       read-only
         DESCRIPTION      "Create/Write access is not required."
         
         OBJECT           cItpSpTimerLinkMessage          
         MIN-ACCESS       read-only
         DESCRIPTION      "Create/Write access is not required."
         
         OBJECT           cItpSpTimerLinkActRetry         
         MIN-ACCESS       read-only
         DESCRIPTION      "Create/Write access is not required."
         
         OBJECT           cItpSpTFR
         MIN-ACCESS       read-only
         DESCRIPTION      "Create/Write access is not required."
         
         OBJECT           cItpSpCongestionsLevels
         MIN-ACCESS       read-only
         DESCRIPTION      "Create/Write access is not required."
         
         OBJECT           cItpSpFastRestart 
         MIN-ACCESS       read-only
         DESCRIPTION      "Create/Write access is not required."
         
         OBJECT           cItpSpDistSccpUnseq 
         MIN-ACCESS       read-only
         DESCRIPTION      "Create/Write access is not required."
         
         OBJECT           cItpSpSummaryRoutingException
         MIN-ACCESS       read-only
         DESCRIPTION      "Create/Write access is not required."
                                    
         OBJECT           cItpSpPointCodeType       
         MIN-ACCESS       read-only
         DESCRIPTION      "Create/Write access is not required."
         
         OBJECT           cItpSpPointCodeRowStatus       
         MIN-ACCESS       read-only
         DESCRIPTION      "Create/Write access is not required."
         
         OBJECT           cItpSpLinksetSourcePointCode    
         MIN-ACCESS       read-only
         DESCRIPTION      "Create/Write access is not required."
         
         OBJECT           cItpSpLinksetAdjacentPointCode  
         MIN-ACCESS       read-only
         DESCRIPTION      "Create/Write access is not required."
         
         OBJECT           cItpSpLinksetInboundAcl         
         MIN-ACCESS       read-only
         DESCRIPTION      "Create/Write access is not required."
         
         OBJECT           cItpSpLinksetOutboundAcl        
         MIN-ACCESS       read-only
         DESCRIPTION      "Create/Write access is not required."
         
         OBJECT           cItpSpLinksetSnmmRTN            
         MIN-ACCESS       read-only
         DESCRIPTION      "Create/Write access is not required."
         
         OBJECT           cItpSpLinksetSntmRTN            
         MIN-ACCESS       read-only
         DESCRIPTION      "Create/Write access is not required."
         
         OBJECT           cItpSpLinksetSpare2RTN          
         MIN-ACCESS       read-only
         DESCRIPTION      "Create/Write access is not required."
         
         OBJECT           cItpSpLinksetSccpRTN            
         MIN-ACCESS       read-only
         DESCRIPTION      "Create/Write access is not required."
         
         OBJECT           cItpSpLinksetTupRTN             
         MIN-ACCESS       read-only
         DESCRIPTION      "Create/Write access is not required."
         
         OBJECT           cItpSpLinksetIsupRTN            
         MIN-ACCESS       read-only
         DESCRIPTION      "Create/Write access is not required."
         
         OBJECT           cItpSpLinksetDupcRTN            
         MIN-ACCESS       read-only
         DESCRIPTION      "Create/Write access is not required."
         
         OBJECT           cItpSpLinksetDupfRTN            
         MIN-ACCESS       read-only
         DESCRIPTION      "Create/Write access is not required."
         
         OBJECT           cItpSpLinksetMtupRTN            
         MIN-ACCESS       read-only
         DESCRIPTION      "Create/Write access is not required."
         
         OBJECT           cItpSpLinksetBisupRTN           
         MIN-ACCESS       read-only
         DESCRIPTION      "Create/Write access is not required."
         
         OBJECT           cItpSpLinksetSisupRTN           
         MIN-ACCESS       read-only
         DESCRIPTION      "Create/Write access is not required."
         
         OBJECT           cItpSpLinksetSpare11RTN         
         MIN-ACCESS       read-only
         DESCRIPTION      "Create/Write access is not required."
         
         OBJECT           cItpSpLinksetSpare12RTN         
         MIN-ACCESS       read-only
         DESCRIPTION      "Create/Write access is not required."
         
         OBJECT           cItpSpLinksetSpare13RTN         
         MIN-ACCESS       read-only
         DESCRIPTION      "Create/Write access is not required."
         
         OBJECT           cItpSpLinksetSpare14RTN         
         MIN-ACCESS       read-only
         DESCRIPTION      "Create/Write access is not required."
         
         OBJECT           cItpSpLinksetSpare15RTN         
         MIN-ACCESS       read-only
         DESCRIPTION      "Create/Write access is not required."
         
         OBJECT           cItpSpLinksetAccountingEnabled  
         MIN-ACCESS       read-only
         DESCRIPTION      "Create/Write access is not required."
         
         OBJECT           cItpSpLinksetMtp2T01            
         MIN-ACCESS       read-only
         DESCRIPTION      "Create/Write access is not required."
         
         OBJECT           cItpSpLinksetMtp2T02            
         MIN-ACCESS       read-only
         DESCRIPTION      "Create/Write access is not required."
         
         OBJECT           cItpSpLinksetMtp2T03            
         MIN-ACCESS       read-only
         DESCRIPTION      "Create/Write access is not required."
         
         OBJECT           cItpSpLinksetMtp2T04E           
         MIN-ACCESS       read-only
         DESCRIPTION      "Create/Write access is not required."
         
         OBJECT           cItpSpLinksetMtp2T04N           
         MIN-ACCESS       read-only
         DESCRIPTION      "Create/Write access is not required."
         
         OBJECT           cItpSpLinksetMtp2T05            
         MIN-ACCESS       read-only
         DESCRIPTION      "Create/Write access is not required."
         
         OBJECT           cItpSpLinksetMtp2T06            
         MIN-ACCESS       read-only
         DESCRIPTION      "Create/Write access is not required."
         
         OBJECT           cItpSpLinksetMtp2T07            
         MIN-ACCESS       read-only
         DESCRIPTION      "Create/Write access is not required."
         
         OBJECT           cItpSpLinksetMtp3T01            
         MIN-ACCESS       read-only
         DESCRIPTION      "Create/Write access is not required."
         
         OBJECT           cItpSpLinksetMtp3T02            
         MIN-ACCESS       read-only
         DESCRIPTION      "Create/Write access is not required."
         
         OBJECT           cItpSpLinksetMtp3T03            
         MIN-ACCESS       read-only
         DESCRIPTION      "Create/Write access is not required."
         
         OBJECT           cItpSpLinksetMtp3T04            
         MIN-ACCESS       read-only
         DESCRIPTION      "Create/Write access is not required."
         
         OBJECT           cItpSpLinksetMtp3T05            
         MIN-ACCESS       read-only
         DESCRIPTION      "Create/Write access is not required."
         
         OBJECT           cItpSpLinksetMtp3T06            
         MIN-ACCESS       read-only
         DESCRIPTION      "Create/Write access is not required."
         
         OBJECT           cItpSpLinksetMtp3T07
         MIN-ACCESS       read-only
         DESCRIPTION      "Create/Write access is not required."
         
         OBJECT           cItpSpLinksetMtp3T08            
         MIN-ACCESS       read-only
         DESCRIPTION      "Create/Write access is not required."
         
         OBJECT           cItpSpLinksetMtp3T10            
         MIN-ACCESS       read-only
         DESCRIPTION      "Create/Write access is not required."
         
         OBJECT           cItpSpLinksetMtp3T11            
         MIN-ACCESS       read-only
         DESCRIPTION      "Create/Write access is not required."
         
         OBJECT           cItpSpLinksetMtp3T12            
         MIN-ACCESS       read-only
         DESCRIPTION      "Create/Write access is not required."
         
         OBJECT           cItpSpLinksetMtp3T13            
         MIN-ACCESS       read-only
         DESCRIPTION      "Create/Write access is not required."
         
         OBJECT           cItpSpLinksetMtp3T14            
         MIN-ACCESS       read-only
         DESCRIPTION      "Create/Write access is not required."
         
         OBJECT           cItpSpLinksetMtp3T15            
         MIN-ACCESS       read-only
         DESCRIPTION      "Create/Write access is not required."
         
         OBJECT           cItpSpLinksetMtp3T16            
         MIN-ACCESS       read-only
         DESCRIPTION      "Create/Write access is not required."
         
         OBJECT           cItpSpLinksetMtp3T17            
         MIN-ACCESS       read-only
         DESCRIPTION      "Create/Write access is not required."
         
         OBJECT           cItpSpLinksetMtp3T18            
         MIN-ACCESS       read-only
         DESCRIPTION      "Create/Write access is not required."
         
         OBJECT           cItpSpLinksetMtp3T19            
         MIN-ACCESS       read-only
         DESCRIPTION      "Create/Write access is not required."
         
         OBJECT           cItpSpLinksetMtp3T20            
         MIN-ACCESS       read-only
         DESCRIPTION      "Create/Write access is not required."
         
         OBJECT           cItpSpLinksetMtp3T21            
         MIN-ACCESS       read-only
         DESCRIPTION      "Create/Write access is not required."
         
         OBJECT           cItpSpLinksetMtp3T22            
         MIN-ACCESS       read-only
         DESCRIPTION      "Create/Write access is not required."
         
         OBJECT           cItpSpLinksetMtp3T23            
         MIN-ACCESS       read-only
         DESCRIPTION      "Create/Write access is not required."
         
         OBJECT           cItpSpLinksetMtp3T24            
         MIN-ACCESS       read-only
         DESCRIPTION      "Create/Write access is not required."
         
         OBJECT           cItpSpLinksetMtp3T25            
         MIN-ACCESS       read-only
         DESCRIPTION      "Create/Write access is not required."
         
         OBJECT           cItpSpLinksetMtp3T26            
         MIN-ACCESS       read-only
         DESCRIPTION      "Create/Write access is not required."
         
         OBJECT           cItpSpLinksetMtp3T27            
         MIN-ACCESS       read-only
         DESCRIPTION      "Create/Write access is not required."
         
         OBJECT           cItpSpLinksetMtp3T28            
         MIN-ACCESS       read-only
         DESCRIPTION      "Create/Write access is not required."
         
         OBJECT           cItpSpLinksetMtp3T29            
         MIN-ACCESS       read-only
         DESCRIPTION      "Create/Write access is not required."
         
         OBJECT           cItpSpLinksetMtp3T30            
         MIN-ACCESS       read-only
         DESCRIPTION      "Create/Write access is not required."
         
         OBJECT           cItpSpLinksetMtp3T31            
         MIN-ACCESS       read-only
         DESCRIPTION      "Create/Write access is not required."
         
         OBJECT           cItpSpLinksetMtp3T32            
         MIN-ACCESS       read-only
         DESCRIPTION      "Create/Write access is not required."
         
         OBJECT           cItpSpLinksetMtp3T33            
         MIN-ACCESS       read-only
         DESCRIPTION      "Create/Write access is not required."
         
         OBJECT           cItpSpLinksetMtp3T34            
         MIN-ACCESS       read-only
         DESCRIPTION      "Create/Write access is not required."
         
         OBJECT           cItpSpLinksetTimerLinkTest      
         MIN-ACCESS       read-only
         DESCRIPTION      "Create/Write access is not required."
         
         OBJECT           cItpSpLinksetTimerLinkMessage   
         MIN-ACCESS       read-only
         DESCRIPTION      "Create/Write access is not required."
         
         OBJECT           cItpSpLinksetTimerLinkActRetry  
         MIN-ACCESS       read-only
         DESCRIPTION      "Create/Write access is not required."
         
         OBJECT           cItpSpLinksetActPriority        
         MIN-ACCESS       read-only
         DESCRIPTION      "Create/Write access is not required."
         
         OBJECT           cItpSpLinksetType               
         MIN-ACCESS       read-only
         DESCRIPTION      "Create/Write access is not required."
         
         OBJECT           cItpSpLinksetRowStatus                  
         MIN-ACCESS       read-only
         DESCRIPTION      "Create/Write access is not required."
         
         OBJECT           cItpSpLinksetNi
         MIN-ACCESS       read-only
         DESCRIPTION      "Create/Write access is not required."
         
         OBJECT           cItpSpLinksetDisplayName
         MIN-ACCESS       read-only
         DESCRIPTION      "Create/Write access is not required."
         
         OBJECT           cItpSpLinksetDescription
         MIN-ACCESS       read-only
         DESCRIPTION      "Create/Write access is not required."
         
         OBJECT           cItpSpLinksetVariant
         MIN-ACCESS       read-only
         DESCRIPTION      "Create/Write access is not required."
         
         OBJECT           cItpSpLinkDescription                  
         MIN-ACCESS       read-only
         DESCRIPTION      "Create/Write access is not required."
         
         OBJECT           cItpSpLinkType                  
         MIN-ACCESS       read-only
         DESCRIPTION      "Create/Write access is not required."
         
         OBJECT           cItpSpLinkifIndex               
         MIN-ACCESS       read-only
         DESCRIPTION      "Create/Write access is not required."
         
         OBJECT           cItpSpLinkMtp2T01               
         MIN-ACCESS       read-only
         DESCRIPTION      "Create/Write access is not required."
         
         OBJECT           cItpSpLinkMtp2T02               
         MIN-ACCESS       read-only
         DESCRIPTION      "Create/Write access is not required."
         
         OBJECT           cItpSpLinkMtp2T03               
         MIN-ACCESS       read-only
         DESCRIPTION      "Create/Write access is not required."
         
         OBJECT           cItpSpLinkMtp2T04E              
         MIN-ACCESS       read-only
         DESCRIPTION      "Create/Write access is not required."
         
         OBJECT           cItpSpLinkMtp2T04N              
         MIN-ACCESS       read-only
         DESCRIPTION      "Create/Write access is not required."
         
         OBJECT           cItpSpLinkMtp2T05               
         MIN-ACCESS       read-only
         DESCRIPTION      "Create/Write access is not required."
         
         OBJECT           cItpSpLinkMtp2T06               
         MIN-ACCESS       read-only
         DESCRIPTION      "Create/Write access is not required."
         
         OBJECT           cItpSpLinkMtp2T07               
         MIN-ACCESS       read-only
         DESCRIPTION      "Create/Write access is not required."
         
         OBJECT           cItpSpLinkMtp3T01               
         MIN-ACCESS       read-only
         DESCRIPTION      "Create/Write access is not required."
         
         OBJECT           cItpSpLinkMtp3T02               
         MIN-ACCESS       read-only
         DESCRIPTION      "Create/Write access is not required."
         
         OBJECT           cItpSpLinkMtp3T03               
         MIN-ACCESS       read-only
         DESCRIPTION      "Create/Write access is not required."
         
         OBJECT           cItpSpLinkMtp3T04               
         MIN-ACCESS       read-only
         DESCRIPTION      "Create/Write access is not required."
         
         OBJECT           cItpSpLinkMtp3T05               
         MIN-ACCESS       read-only
         DESCRIPTION      "Create/Write access is not required."
         
         OBJECT           cItpSpLinkMtp3T06               
         MIN-ACCESS       read-only
         DESCRIPTION      "Create/Write access is not required."
         
         OBJECT           cItpSpLinkMtp3T07               
         MIN-ACCESS       read-only
         DESCRIPTION      "Create/Write access is not required."
         
         OBJECT           cItpSpLinkMtp3T08               
         MIN-ACCESS       read-only
         DESCRIPTION      "Create/Write access is not required."
         
         OBJECT           cItpSpLinkMtp3T10               
         MIN-ACCESS       read-only
         DESCRIPTION      "Create/Write access is not required."
         
         OBJECT           cItpSpLinkMtp3T11               
         MIN-ACCESS       read-only
         DESCRIPTION      "Create/Write access is not required."
         
         OBJECT           cItpSpLinkMtp3T12               
         MIN-ACCESS       read-only
         DESCRIPTION      "Create/Write access is not required."
         
         OBJECT           cItpSpLinkMtp3T13               
         MIN-ACCESS       read-only
         DESCRIPTION      "Create/Write access is not required."
         
         OBJECT           cItpSpLinkMtp3T14               
         MIN-ACCESS       read-only
         DESCRIPTION      "Create/Write access is not required."
         
         OBJECT           cItpSpLinkMtp3T15               
         MIN-ACCESS       read-only
         DESCRIPTION      "Create/Write access is not required."
         
         OBJECT           cItpSpLinkMtp3T16               
         MIN-ACCESS       read-only
         DESCRIPTION      "Create/Write access is not required."
         
         OBJECT           cItpSpLinkMtp3T17               
         MIN-ACCESS       read-only
         DESCRIPTION      "Create/Write access is not required."
         
         OBJECT           cItpSpLinkMtp3T18               
         MIN-ACCESS       read-only
         DESCRIPTION      "Create/Write access is not required."
         
         OBJECT           cItpSpLinkMtp3T19               
         MIN-ACCESS       read-only
         DESCRIPTION      "Create/Write access is not required."
         
         OBJECT           cItpSpLinkMtp3T20               
         MIN-ACCESS       read-only
         DESCRIPTION      "Create/Write access is not required."
         
         OBJECT           cItpSpLinkMtp3T21               
         MIN-ACCESS       read-only
         DESCRIPTION      "Create/Write access is not required."
         
         OBJECT           cItpSpLinkMtp3T22               
         MIN-ACCESS       read-only
         DESCRIPTION      "Create/Write access is not required."
         
         OBJECT           cItpSpLinkMtp3T23               
         MIN-ACCESS       read-only
         DESCRIPTION      "Create/Write access is not required."
         
         OBJECT           cItpSpLinkMtp3T24               
         MIN-ACCESS       read-only
         DESCRIPTION      "Create/Write access is not required."
         
         OBJECT           cItpSpLinkMtp3T25               
         MIN-ACCESS       read-only
         DESCRIPTION      "Create/Write access is not required."
         
         OBJECT           cItpSpLinkMtp3T26               
         MIN-ACCESS       read-only
         DESCRIPTION      "Create/Write access is not required."
         
         OBJECT           cItpSpLinkMtp3T27               
         MIN-ACCESS       read-only
         DESCRIPTION      "Create/Write access is not required."
         
         OBJECT           cItpSpLinkMtp3T28               
         MIN-ACCESS       read-only
         DESCRIPTION      "Create/Write access is not required."
         
         OBJECT           cItpSpLinkMtp3T29               
         MIN-ACCESS       read-only
         DESCRIPTION      "Create/Write access is not required."
         
         OBJECT           cItpSpLinkMtp3T30               
         MIN-ACCESS       read-only
         DESCRIPTION      "Create/Write access is not required."
         
         OBJECT           cItpSpLinkMtp3T31               
         MIN-ACCESS       read-only
         DESCRIPTION      "Create/Write access is not required."
         
         OBJECT           cItpSpLinkMtp3T32               
         MIN-ACCESS       read-only
         DESCRIPTION      "Create/Write access is not required."
         
         OBJECT           cItpSpLinkMtp3T33               
         MIN-ACCESS       read-only
         DESCRIPTION      "Create/Write access is not required."
         
         OBJECT           cItpSpLinkMtp3T34               
         MIN-ACCESS       read-only
         DESCRIPTION      "Create/Write access is not required."
         
         OBJECT           cItpSpLinkTimerLinkTest        
         MIN-ACCESS       read-only
         DESCRIPTION      "Create/Write access is not required."
         
         OBJECT           cItpSpLinkTimerLinkMessage     
         MIN-ACCESS       read-only
         DESCRIPTION      "Create/Write access is not required."
         
         OBJECT           cItpSpLinkTimerLinkActRetry    
         MIN-ACCESS       read-only
         DESCRIPTION      "Create/Write access is not required."

         OBJECT           cItpSpLinkXmitQueueDepthHigh
         MIN-ACCESS       read-only
         DESCRIPTION      "Create/Write access is not required."
         
         OBJECT           cItpSpLinkCongestionAbate1      
         MIN-ACCESS       read-only
         DESCRIPTION      "Create/Write access is not required."
         
         OBJECT           cItpSpLinkCongestionAbate2      
         MIN-ACCESS       read-only
         DESCRIPTION      "Create/Write access is not required."
         
         OBJECT           cItpSpLinkCongestionAbate3      
         MIN-ACCESS       read-only
         DESCRIPTION      "Create/Write access is not required."
         
         OBJECT           cItpSpLinkCongestionOnset1      
         MIN-ACCESS       read-only
         DESCRIPTION      "Create/Write access is not required."
         
         OBJECT           cItpSpLinkCongestionOnset2      
         MIN-ACCESS       read-only
         DESCRIPTION      "Create/Write access is not required."
         
         OBJECT           cItpSpLinkCongestionOnset3      
         MIN-ACCESS       read-only
         DESCRIPTION      "Create/Write access is not required."
         
         OBJECT           cItpSpLinkSigLinkTest           
         MIN-ACCESS       read-only
         DESCRIPTION      "Create/Write access is not required."
         
         OBJECT           cItpSpLinkIPType1               
         MIN-ACCESS       read-only
         DESCRIPTION      "Create/Write access is not required."
         
         OBJECT           cItpSpLinkIPType2               
         MIN-ACCESS       read-only
         DESCRIPTION      "Create/Write access is not required."
         
         OBJECT           cItpSpLinkIPType3               
         MIN-ACCESS       read-only
         DESCRIPTION      "Create/Write access is not required."
         
         OBJECT           cItpSpLinkIPType4               
         MIN-ACCESS       read-only
         DESCRIPTION      "Create/Write access is not required."
         
         OBJECT           cItpSpLinkIPAddr1               
         MIN-ACCESS       read-only
         DESCRIPTION      "Create/Write access is not required."
         
         OBJECT           cItpSpLinkIPAddr2               
         MIN-ACCESS       read-only
         DESCRIPTION      "Create/Write access is not required."
         
         OBJECT           cItpSpLinkIPAddr3               
         MIN-ACCESS       read-only
         DESCRIPTION      "Create/Write access is not required."
         
         OBJECT           cItpSpLinkIPAddr4               
         MIN-ACCESS       read-only
         DESCRIPTION      "Create/Write access is not required."
         
         OBJECT           cItpSpLinkLocalPort             
         MIN-ACCESS       read-only
         DESCRIPTION      "Create/Write access is not required."
         
         OBJECT           cItpSpLinkRemotePort            
         MIN-ACCESS       read-only
         DESCRIPTION      "Create/Write access is not required."
         
         OBJECT           cItpSpLinkQosClass                  
         MIN-ACCESS       read-only
         DESCRIPTION      "Create/Write access is not required."
         
         OBJECT           cItpSpLinkRowStatus                  
         MIN-ACCESS       read-only
         DESCRIPTION      "Create/Write access is not required."
         
         OBJECT           cItpSpLinkDisplayName
         MIN-ACCESS       read-only
         DESCRIPTION      "Create/Write access is not required."
         
         OBJECT           cItpSpLinkPlanCapacitySent
         MIN-ACCESS       read-write
         DESCRIPTION      "Create access is not required."
         
         OBJECT           cItpSpLinkPlanCapacityRcvd
         MIN-ACCESS       read-write
         DESCRIPTION      "Create access is not required."
        ::= { cItpSpMIBCompliances 3 }

-- Units of Conformance

cItpSpScalarsGroup OBJECT-GROUP
        OBJECTS { cItpSpVariant,
                  cItpSpCLLICode,
                  cItpSpDisplayName,
                  cItpSpDescription,
                  cItpSpMtp2T01,
                  cItpSpMtp2T02,
                  cItpSpMtp2T03,
                  cItpSpMtp2T04E,
                  cItpSpMtp2T04N,
                  cItpSpMtp2T05,
                  cItpSpMtp2T06,
                  cItpSpMtp2T07,
                  cItpSpMtp3T01,
                  cItpSpMtp3T02,
                  cItpSpMtp3T03,
                  cItpSpMtp3T04,
                  cItpSpMtp3T05,
                  cItpSpMtp3T06,
                  cItpSpMtp3T07,
                  cItpSpMtp3T08,
                  cItpSpMtp3T10,
                  cItpSpMtp3T11,
                  cItpSpMtp3T12,
                  cItpSpMtp3T13,
                  cItpSpMtp3T14,
                  cItpSpMtp3T15,
                  cItpSpMtp3T16,
                  cItpSpMtp3T17,
                  cItpSpMtp3T18,
                  cItpSpMtp3T19,
                  cItpSpMtp3T20,
                  cItpSpMtp3T21,
                  cItpSpMtp3T22,
                  cItpSpMtp3T23,
                  cItpSpMtp3T24,
                  cItpSpMtp3T25,
                  cItpSpMtp3T26,
                  cItpSpMtp3T27,
                  cItpSpMtp3T28,
                  cItpSpMtp3T29,
                  cItpSpMtp3T30,
                  cItpSpMtp3T31,
                  cItpSpMtp3T32,
                  cItpSpMtp3T33,
                  cItpSpMtp3T34,
                  cItpSpTimerLinkTest,   
                  cItpSpTimerLinkMessage,
                  cItpSpTimerLinkActRetry,
                  cItpSpTFR,              
                  cItpSpCongestionsLevels,
                  cItpSpFastRestart
        }
        STATUS deprecated -- superceded by cItpSpScalarsGroupRev2
        DESCRIPTION
                "SP main objects."
        ::= { cItpSpMIBGroups 1 }
        

cItpSpPointCodeGroup OBJECT-GROUP
        OBJECTS { 
                  cItpSpPointCodeType,       
                  cItpSpPointCodeDisplay,       
                  cItpSpPointCodeRowStatus       
        }
        STATUS current
        DESCRIPTION
                "SP main objects."
        ::= { cItpSpMIBGroups 2 }


cItpSpLinksetGroup OBJECT-GROUP
        OBJECTS {
                cItpSpLinksetSourcePointCode, 
                cItpSpLinksetSourceDisplayPC,  
                cItpSpLinksetAdjacentPointCode,
                cItpSpLinksetAdjacentDisplayPC,
                cItpSpLinksetState,
                cItpSpLinksetInboundAcl,
                cItpSpLinksetOutboundAcl,
                cItpSpLinksetSnmmRTN,
                cItpSpLinksetSntmRTN,
                cItpSpLinksetSpare2RTN,
                cItpSpLinksetSccpRTN,
                cItpSpLinksetTupRTN,
                cItpSpLinksetIsupRTN,
                cItpSpLinksetDupcRTN,
                cItpSpLinksetDupfRTN,
                cItpSpLinksetMtupRTN,
                cItpSpLinksetBisupRTN,
                cItpSpLinksetSisupRTN,
                cItpSpLinksetSpare11RTN,
                cItpSpLinksetSpare12RTN,
                cItpSpLinksetSpare13RTN,
                cItpSpLinksetSpare14RTN,
                cItpSpLinksetSpare15RTN,
                cItpSpLinksetAccountingEnabled,
                cItpSpLinksetNumLinks,
                cItpSpLinksetDurationInService,   
                cItpSpLinksetDurationOutService,  
                cItpSpLinksetMtp2T01,
                cItpSpLinksetMtp2T02,
                cItpSpLinksetMtp2T03,
                cItpSpLinksetMtp2T04E,
                cItpSpLinksetMtp2T04N,
                cItpSpLinksetMtp2T05,
                cItpSpLinksetMtp2T06,
                cItpSpLinksetMtp2T07,
                cItpSpLinksetMtp3T01,
                cItpSpLinksetMtp3T02,
                cItpSpLinksetMtp3T03,
                cItpSpLinksetMtp3T04,
                cItpSpLinksetMtp3T05,
                cItpSpLinksetMtp3T06,
                cItpSpLinksetMtp3T07,
                cItpSpLinksetMtp3T08,
                cItpSpLinksetMtp3T10,
                cItpSpLinksetMtp3T11,
                cItpSpLinksetMtp3T12,
                cItpSpLinksetMtp3T13,
                cItpSpLinksetMtp3T14,
                cItpSpLinksetMtp3T15,
                cItpSpLinksetMtp3T16,
                cItpSpLinksetMtp3T17,
                cItpSpLinksetMtp3T18,
                cItpSpLinksetMtp3T19,
                cItpSpLinksetMtp3T20,
                cItpSpLinksetMtp3T21,
                cItpSpLinksetMtp3T22,
                cItpSpLinksetMtp3T23,
                cItpSpLinksetMtp3T24,
                cItpSpLinksetMtp3T25,
                cItpSpLinksetMtp3T26,
                cItpSpLinksetMtp3T27,
                cItpSpLinksetMtp3T28,
                cItpSpLinksetMtp3T29,
                cItpSpLinksetMtp3T30,
                cItpSpLinksetMtp3T31,
                cItpSpLinksetMtp3T32,
                cItpSpLinksetMtp3T33,
                cItpSpLinksetMtp3T34,
                cItpSpLinksetTimerLinkTest,   
                cItpSpLinksetTimerLinkMessage,
                cItpSpLinksetTimerLinkActRetry,
                cItpSpLinksetPlanCapacity,
                cItpSpLinksetActPriority, 
                cItpSpLinksetType,
                cItpSpLinksetRowStatus,
                cItpSpLinksetNi,
                cItpSpLinksetDisplayName,
                cItpSpLinksetDescription
        }
        STATUS deprecated -- superceded by cItpSpLinksetGroupRev2
        DESCRIPTION
                "SP linkset objects."
        ::= { cItpSpMIBGroups 3 }

cItpSpLinkGroup OBJECT-GROUP
        OBJECTS {
                cItpSpLinkDescription,
                cItpSpLinkState,
                cItpSpLinkType,
                cItpSpLinkifIndex,
                cItpSpLinkSctpAssociation,
                cItpSpLinkMtp3PacketsRcvd,
                cItpSpLinkMtp3PacketsSent,
                cItpSpLinkMtp3BytesRcvd,
                cItpSpLinkMtp3BytesSent,
                cItpSpLinkMtp2T01,
                cItpSpLinkMtp2T02,
                cItpSpLinkMtp2T03,
                cItpSpLinkMtp2T04E,
                cItpSpLinkMtp2T04N,
                cItpSpLinkMtp2T05,
                cItpSpLinkMtp2T06,
                cItpSpLinkMtp2T07,
                cItpSpLinkMtp3T01,
                cItpSpLinkMtp3T02,
                cItpSpLinkMtp3T03,
                cItpSpLinkMtp3T04,
                cItpSpLinkMtp3T05,
                cItpSpLinkMtp3T06,
                cItpSpLinkMtp3T07,
                cItpSpLinkMtp3T08,
                cItpSpLinkMtp3T10,
                cItpSpLinkMtp3T11,
                cItpSpLinkMtp3T12,
                cItpSpLinkMtp3T13,
                cItpSpLinkMtp3T14,
                cItpSpLinkMtp3T15,
                cItpSpLinkMtp3T16,
                cItpSpLinkMtp3T17,
                cItpSpLinkMtp3T18,
                cItpSpLinkMtp3T19,
                cItpSpLinkMtp3T20,
                cItpSpLinkMtp3T21,
                cItpSpLinkMtp3T22,
                cItpSpLinkMtp3T23,
                cItpSpLinkMtp3T24,
                cItpSpLinkMtp3T25,
                cItpSpLinkMtp3T26,
                cItpSpLinkMtp3T27,
                cItpSpLinkMtp3T28,
                cItpSpLinkMtp3T29,
                cItpSpLinkMtp3T30,
                cItpSpLinkMtp3T31,
                cItpSpLinkMtp3T32,
                cItpSpLinkMtp3T33,
                cItpSpLinkMtp3T34,
                cItpSpLinkTimerLinkTest,   
                cItpSpLinkTimerLinkMessage,
                cItpSpLinkTimerLinkActRetry,
                cItpSpLinkXmitQueueDepth,
                cItpSpLinkXmitQueueDepthHigh,
                cItpSpLinkXmitQueueDepthHighRT,
                cItpSpLinkCongestionState,
                cItpSpLinkCongestionAbate1,
                cItpSpLinkCongestionAbate2,
                cItpSpLinkCongestionAbate3,
                cItpSpLinkCongestionOnset1,
                cItpSpLinkCongestionOnset2,
                cItpSpLinkCongestionOnset3,
                cItpSpLinkSigLinkTest,
                cItpSpLinkQ752T1E1,   
                cItpSpLinkQ752T1E2,   
                cItpSpLinkQ752T1E3,   
                cItpSpLinkQ752T1E4,   
                cItpSpLinkQ752T1E5,   
                cItpSpLinkQ752T1E6,   
                cItpSpLinkQ752T1E7,   
                cItpSpLinkQ752T1E8,   
                cItpSpLinkQ752T1E9,   
                cItpSpLinkQ752T1E10,  
                cItpSpLinkQ752T1E11,  
                cItpSpLinkQ752T2E1,   
                cItpSpLinkQ752T2E5,   
                cItpSpLinkQ752T2E6,   
                cItpSpLinkQ752T2E7,   
                cItpSpLinkQ752T2E9,   
                cItpSpLinkQ752T2E10,  
                cItpSpLinkQ752T2E15,  
                cItpSpLinkQ752T2E16,  
                cItpSpLinkQ752T2E18,  
                cItpSpLinkMtp3PacketsRetrans,   -- Q752/3.2
                cItpSpLinkMtp3BytesRetrans,     -- Q752/3.2
                cItpSpLinkQ752T3E6,   
                cItpSpLinkQ752T3E7,   
                cItpSpLinkQ752T3E10L1,
                cItpSpLinkQ752T3E10L2,
                cItpSpLinkQ752T3E10L3,
                cItpSpLinkQ752T3E11L1,
                cItpSpLinkQ752T3E11L2,
                cItpSpLinkQ752T3E11L3,
                cItpSpLinkIPType1,
                cItpSpLinkIPType2,
                cItpSpLinkIPType3,
                cItpSpLinkIPType4,
                cItpSpLinkIPAddr1,
                cItpSpLinkIPAddr2,
                cItpSpLinkIPAddr3,
                cItpSpLinkIPAddr4,
                cItpSpLinkLocalPort,
                cItpSpLinkRemotePort,
                cItpSpLinkQosClass, 
                cItpSpLinkRowStatus,
                cItpSpLinkStateReason,   
                cItpSpLinkDisplayName
        }
        STATUS deprecated -- superceded by cItpSpLinkGroupRev2
        DESCRIPTION
                "SP link objects."
        ::= { cItpSpMIBGroups 4 }

cItpSpNotificationsEnableGroup OBJECT-GROUP
        OBJECTS {
                cItpSpLsStateChangeNotifEnabled,
                cItpSpLnkStateChangeNotifEnabled,
                cItpSpCongestionNotifEnabled 
        }                      
        STATUS deprecated 
        -- superceded by cItpSpNotificationsEnableGroupRev2
        DESCRIPTION
                "SP enable notification objects."
        ::= { cItpSpMIBGroups 5 }
        
cItpSpNotificationsGroup NOTIFICATION-GROUP
        NOTIFICATIONS {
                cItpSpLinksetStateChange, 
                cItpSpLinkStateChange, 
                cItpSpCongestionChange
        }                      
        STATUS deprecated 
        -- superceded by cItpSpNotificationsEnableGroupRev2
        DESCRIPTION
                "SP notification objects."
        ::= { cItpSpMIBGroups 6 }
        
cItpSpStatsGroup OBJECT-GROUP
        OBJECTS {
                 cItpSpDistSccpUnseq,
                 cItpSpSummaryRoutingException,
                 cItpSpLinksetVariant,
                 cItpSpLinkDroppedPkts,   
                 cItpSpLinkTransmittedLssu, 
                 cItpSpLinkReceivedLssu, 
                 cItpSpLinkProtocolDetails,
                 cItpSpLinkLsacState,
                 cItpSpLinkTsrcState,
                 cItpSpLinkTcocState,
                 cItpSpLinkTcocLocalBSNT,
                 cItpSpLinkTcocRemoteBSNT,
                 cItpSpLinkTcbcState,
                 cItpSpLinkReceivedSIB,          
                 cItpSpLinkTransmittedSIB,         
                 cItpSpLinkMtp2ExpiredT01,  
                 cItpSpLinkMtp2ExpiredT02,  
                 cItpSpLinkMtp2ExpiredT03,  
                 cItpSpLinkMtp2ExpiredT04, 
                 cItpSpLinkMtp2ExpiredT05,  
                 cItpSpLinkMtp2ExpiredT06,  
                 cItpSpLinkMtp2ExpiredT07,  
                 cItpSpLinkOMAERMCount,     
                 cItpSpLinkOMAERMFailCount, 
                 cItpSpLinkOMSURMCount,     
                 cItpSpLinkOMSURMFailCount
        }                      
        STATUS deprecated 
        -- superceded by cItpSpScalarsGroupRev2
        --               cItpSpLinkGroupRev2 
        DESCRIPTION
                "SP protocol statistics objects."
        ::= { cItpSpMIBGroups 7 }
        
-- Changes for second revision                 

cItpSpScalarsGroupRev2 OBJECT-GROUP
        OBJECTS { cItpSpVariant,
                  cItpSpCLLICode,
                  cItpSpDisplayName,
                  cItpSpDescription,
                  cItpSpMtp2T01,
                  cItpSpMtp2T02,
                  cItpSpMtp2T03,
                  cItpSpMtp2T04E,
                  cItpSpMtp2T04N,
                  cItpSpMtp2T05,
                  cItpSpMtp2T06,
                  cItpSpMtp2T07,
                  cItpSpMtp3T01,
                  cItpSpMtp3T02,
                  cItpSpMtp3T03,
                  cItpSpMtp3T04,
                  cItpSpMtp3T05,
                  cItpSpMtp3T06,
                  cItpSpMtp3T07,
                  cItpSpMtp3T08,
                  cItpSpMtp3T10,
                  cItpSpMtp3T11,
                  cItpSpMtp3T12,
                  cItpSpMtp3T13,
                  cItpSpMtp3T14,
                  cItpSpMtp3T15,
                  cItpSpMtp3T16,
                  cItpSpMtp3T17,
                  cItpSpMtp3T18,
                  cItpSpMtp3T19,
                  cItpSpMtp3T20,
                  cItpSpMtp3T21,
                  cItpSpMtp3T22,
                  cItpSpMtp3T23,
                  cItpSpMtp3T24,
                  cItpSpMtp3T25,
                  cItpSpMtp3T26,
                  cItpSpMtp3T27,
                  cItpSpMtp3T28,
                  cItpSpMtp3T29,
                  cItpSpMtp3T30,
                  cItpSpMtp3T31,
                  cItpSpMtp3T32,
                  cItpSpMtp3T33,
                  cItpSpMtp3T34,
                  cItpSpTimerLinkTest,   
                  cItpSpTimerLinkMessage,
                  cItpSpTimerLinkActRetry,
                  cItpSpTFR,              
                  cItpSpCongestionsLevels,
                  cItpSpFastRestart,
                  cItpSpDistSccpUnseq,
                  cItpSpSummaryRoutingException,
                  cItpSpUtilSampleInterval,
                  cItpSpUtilThreshold,
                  cItpSpUtilAbateDelta 
        }
        STATUS current
        DESCRIPTION
                "SP main objects."
        ::= { cItpSpMIBGroups 8 }
        
cItpSpLinksetGroupRev2 OBJECT-GROUP
        OBJECTS {
                cItpSpLinksetSourcePointCode, 
                cItpSpLinksetSourceDisplayPC,  
                cItpSpLinksetAdjacentPointCode,
                cItpSpLinksetAdjacentDisplayPC,
                cItpSpLinksetState,
                cItpSpLinksetInboundAcl,
                cItpSpLinksetOutboundAcl,
                cItpSpLinksetSnmmRTN,
                cItpSpLinksetSntmRTN,
                cItpSpLinksetSpare2RTN,
                cItpSpLinksetSccpRTN,
                cItpSpLinksetTupRTN,
                cItpSpLinksetIsupRTN,
                cItpSpLinksetDupcRTN,
                cItpSpLinksetDupfRTN,
                cItpSpLinksetMtupRTN,
                cItpSpLinksetBisupRTN,
                cItpSpLinksetSisupRTN,
                cItpSpLinksetSpare11RTN,
                cItpSpLinksetSpare12RTN,
                cItpSpLinksetSpare13RTN,
                cItpSpLinksetSpare14RTN,
                cItpSpLinksetSpare15RTN,
                cItpSpLinksetAccountingEnabled,
                cItpSpLinksetNumLinks,
                cItpSpLinksetDurationInService,   
                cItpSpLinksetDurationOutService,  
                cItpSpLinksetMtp2T01,
                cItpSpLinksetMtp2T02,
                cItpSpLinksetMtp2T03,
                cItpSpLinksetMtp2T04E,
                cItpSpLinksetMtp2T04N,
                cItpSpLinksetMtp2T05,
                cItpSpLinksetMtp2T06,
                cItpSpLinksetMtp2T07,
                cItpSpLinksetMtp3T01,
                cItpSpLinksetMtp3T02,
                cItpSpLinksetMtp3T03,
                cItpSpLinksetMtp3T04,
                cItpSpLinksetMtp3T05,
                cItpSpLinksetMtp3T06,
                cItpSpLinksetMtp3T07,
                cItpSpLinksetMtp3T08,
                cItpSpLinksetMtp3T10,
                cItpSpLinksetMtp3T11,
                cItpSpLinksetMtp3T12,
                cItpSpLinksetMtp3T13,
                cItpSpLinksetMtp3T14,
                cItpSpLinksetMtp3T15,
                cItpSpLinksetMtp3T16,
                cItpSpLinksetMtp3T17,
                cItpSpLinksetMtp3T18,
                cItpSpLinksetMtp3T19,
                cItpSpLinksetMtp3T20,
                cItpSpLinksetMtp3T21,
                cItpSpLinksetMtp3T22,
                cItpSpLinksetMtp3T23,
                cItpSpLinksetMtp3T24,
                cItpSpLinksetMtp3T25,
                cItpSpLinksetMtp3T26,
                cItpSpLinksetMtp3T27,
                cItpSpLinksetMtp3T28,
                cItpSpLinksetMtp3T29,
                cItpSpLinksetMtp3T30,
                cItpSpLinksetMtp3T31,
                cItpSpLinksetMtp3T32,
                cItpSpLinksetMtp3T33,
                cItpSpLinksetMtp3T34,
                cItpSpLinksetTimerLinkTest,   
                cItpSpLinksetTimerLinkMessage,
                cItpSpLinksetTimerLinkActRetry,
                cItpSpLinksetActPriority, 
                cItpSpLinksetType,
                cItpSpLinksetRowStatus,
                cItpSpLinksetNi,
                cItpSpLinksetDisplayName,
                cItpSpLinksetDescription,
                cItpSpLinksetVariant
        }
        STATUS current
        DESCRIPTION
                "SP linkset objects."
        ::= { cItpSpMIBGroups 9 }

cItpSpLinkGroupRev2 OBJECT-GROUP
        OBJECTS {
                cItpSpLinkDescription,
                cItpSpLinkState,
                cItpSpLinkType,
                cItpSpLinkifIndex,
                cItpSpLinkSctpAssociation,
                cItpSpLinkMtp3PacketsRcvd,
                cItpSpLinkMtp3PacketsSent,
                cItpSpLinkMtp3BytesRcvd,
                cItpSpLinkMtp3BytesSent,
                cItpSpLinkMtp2T01,
                cItpSpLinkMtp2T02,
                cItpSpLinkMtp2T03,
                cItpSpLinkMtp2T04E,
                cItpSpLinkMtp2T04N,
                cItpSpLinkMtp2T05,
                cItpSpLinkMtp2T06,
                cItpSpLinkMtp2T07,
                cItpSpLinkMtp3T01,
                cItpSpLinkMtp3T02,
                cItpSpLinkMtp3T03,
                cItpSpLinkMtp3T04,
                cItpSpLinkMtp3T05,
                cItpSpLinkMtp3T06,
                cItpSpLinkMtp3T07,
                cItpSpLinkMtp3T08,
                cItpSpLinkMtp3T10,
                cItpSpLinkMtp3T11,
                cItpSpLinkMtp3T12,
                cItpSpLinkMtp3T13,
                cItpSpLinkMtp3T14,
                cItpSpLinkMtp3T15,
                cItpSpLinkMtp3T16,
                cItpSpLinkMtp3T17,
                cItpSpLinkMtp3T18,
                cItpSpLinkMtp3T19,
                cItpSpLinkMtp3T20,
                cItpSpLinkMtp3T21,
                cItpSpLinkMtp3T22,
                cItpSpLinkMtp3T23,
                cItpSpLinkMtp3T24,
                cItpSpLinkMtp3T25,
                cItpSpLinkMtp3T26,
                cItpSpLinkMtp3T27,
                cItpSpLinkMtp3T28,
                cItpSpLinkMtp3T29,
                cItpSpLinkMtp3T30,
                cItpSpLinkMtp3T31,
                cItpSpLinkMtp3T32,
                cItpSpLinkMtp3T33,
                cItpSpLinkMtp3T34,
                cItpSpLinkTimerLinkTest,   
                cItpSpLinkTimerLinkMessage,
                cItpSpLinkTimerLinkActRetry,
                cItpSpLinkXmitQueueDepth,
                cItpSpLinkXmitQueueDepthHigh,
                cItpSpLinkXmitQueueDepthHighRT,
                cItpSpLinkCongestionState,
                cItpSpLinkCongestionAbate1,
                cItpSpLinkCongestionAbate2,
                cItpSpLinkCongestionAbate3,
                cItpSpLinkCongestionOnset1,
                cItpSpLinkCongestionOnset2,
                cItpSpLinkCongestionOnset3,
                cItpSpLinkSigLinkTest,
                cItpSpLinkQ752T1E1,   
                cItpSpLinkQ752T1E2,   
                cItpSpLinkQ752T1E3,   
                cItpSpLinkQ752T1E4,   
                cItpSpLinkQ752T1E5,   
                cItpSpLinkQ752T1E6,   
                cItpSpLinkQ752T1E7,   
                cItpSpLinkQ752T1E8,   
                cItpSpLinkQ752T1E9,   
                cItpSpLinkQ752T1E10,  
                cItpSpLinkQ752T1E11,  
                cItpSpLinkQ752T2E1,   
                cItpSpLinkQ752T2E5,   
                cItpSpLinkQ752T2E6,   
                cItpSpLinkQ752T2E7,   
                cItpSpLinkQ752T2E9,   
                cItpSpLinkQ752T2E10,  
                cItpSpLinkQ752T2E15,  
                cItpSpLinkQ752T2E16,  
                cItpSpLinkQ752T2E18,  
                cItpSpLinkMtp3PacketsRetrans,   -- Q752/3.2
                cItpSpLinkMtp3BytesRetrans,     -- Q752/3.2
                cItpSpLinkQ752T3E6,   
                cItpSpLinkQ752T3E7,   
                cItpSpLinkQ752T3E10L1,
                cItpSpLinkQ752T3E10L2,
                cItpSpLinkQ752T3E10L3,
                cItpSpLinkQ752T3E11L1,
                cItpSpLinkQ752T3E11L2,
                cItpSpLinkQ752T3E11L3,
                cItpSpLinkIPType1,
                cItpSpLinkIPType2,
                cItpSpLinkIPType3,
                cItpSpLinkIPType4,
                cItpSpLinkIPAddr1,
                cItpSpLinkIPAddr2,
                cItpSpLinkIPAddr3,
                cItpSpLinkIPAddr4,
                cItpSpLinkLocalPort,
                cItpSpLinkRemotePort,
                cItpSpLinkQosClass, 
                cItpSpLinkRowStatus,
                cItpSpLinkStateReason,   
                cItpSpLinkDisplayName,
                 cItpSpLinkDroppedPkts,   
                 cItpSpLinkTransmittedLssu, 
                 cItpSpLinkReceivedLssu, 
                 cItpSpLinkProtocolDetails,
                 cItpSpLinkLsacState,
                 cItpSpLinkTsrcState,
                 cItpSpLinkTcocState,
                 cItpSpLinkTcocLocalBSNT,
                 cItpSpLinkTcocRemoteBSNT,
                 cItpSpLinkTcbcState,
                 cItpSpLinkReceivedSIB,          
                 cItpSpLinkTransmittedSIB,         
                 cItpSpLinkMtp2ExpiredT01,  
                 cItpSpLinkMtp2ExpiredT02,  
                 cItpSpLinkMtp2ExpiredT03,  
                 cItpSpLinkMtp2ExpiredT04, 
                 cItpSpLinkMtp2ExpiredT05,  
                 cItpSpLinkMtp2ExpiredT06,  
                 cItpSpLinkMtp2ExpiredT07,  
                 cItpSpLinkOMAERMCount,     
                 cItpSpLinkOMAERMFailCount, 
                 cItpSpLinkOMSURMCount,     
                 cItpSpLinkOMSURMFailCount,
                 cItpSpLinkPlanCapacityRcvd,
                 cItpSpLinkUtilThresholdRcvd,
                 cItpSpLinkUtilizationRcvd,
                 cItpSpLinkUtilStateRcvd,
                 cItpSpLinkL2BytesRcvd,
                 cItpSpLinkPlanCapacitySent,
                 cItpSpLinkUtilThresholdSent,
                 cItpSpLinkUtilizationSent,
                 cItpSpLinkUtilStateSent,
                 cItpSpLinkL2BytesSent
        }
        STATUS current
        DESCRIPTION
                "SP link objects."
        ::= { cItpSpMIBGroups 10 }

cItpSpNotificationsEnableGroupRev2 OBJECT-GROUP
        OBJECTS {
                cItpSpLsStateChangeNotifEnabled,
                cItpSpLnkStateChangeNotifEnabled,
                cItpSpCongestionNotifEnabled, 
                cItpSpLinkUtilNotifEnabled 
        }                      
        STATUS current
        DESCRIPTION
                "SP enable notification objects."
        ::= { cItpSpMIBGroups 11 }
        
cItpSpNotificationsGroupRev2 NOTIFICATION-GROUP
        NOTIFICATIONS {
                cItpSpLinksetStateChange, 
                cItpSpLinkStateChange, 
                cItpSpCongestionChange,
                cItpSpLinkRcvdUtilChange,
                cItpSpLinkSentUtilChange
        }                      
        STATUS current
        DESCRIPTION
                "SP notification objects."
        ::= { cItpSpMIBGroups 12 }
END
