-- *****************************************************************
-- CISCO-ITP-RT-CAPABILITY.my:  Itp Signalling Point Routing 
--                              Agent capability MIB
--
-- August 2001, John Linton
--
-- Copyright (c) 2001-2002 by cisco Systems, Inc.
-- All rights reserved.
-- *****************************************************************
CISCO-ITP-RT-CAPABILITY DEFINITIONS ::= BEGIN

IMPORTS
        MODULE-IDENTITY
                FROM SNMPv2-SMI
                
        AGENT-CAPABILITIES
                FROM SNMPv2-CONF
                
        ciscoAgentCapability
                FROM CISCO-SMI;
                

ciscoItpRtCapability MODULE-IDENTITY
                LAST-UPDATED    "200201210000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-ss7@cisco.com"
                DESCRIPTION
                        "Agent capabilities for the CISCO-ITP-RT-MIB."
                        
                REVISION        "200201210000Z"
                DESCRIPTION
                        "Updated capabilities MIB as required for 
                         new groups.
                         
                         cItpRtNotificationsGroup,
                         cItpRtScalarGroupRev1"
                        
                REVISION        "200110240000Z"
                DESCRIPTION
                        "Initial version of this MIB module."
        ::= { ciscoAgentCapability 216 }

ciscoItpRtCapabilityV12R024MB1 AGENT-CAPABILITIES

    PRODUCT-RELEASE "Cisco IOS 12.2(4)MB1"
    STATUS          current
    DESCRIPTION     "IOS 12.2(4)MB1 Cisco CISCO-ITP-RT-MIB.my User Agent
                       MIB capabilities."

    SUPPORTS        CISCO-ITP-RT-MIB
        INCLUDES    { 
                        cItpRtScalarGroup,
                        cItpRouteGroup
                    }  
                      

    ::= { ciscoItpRtCapability 1 }

ciscoItpRtCapabilityV12R0204MB3 AGENT-CAPABILITIES

    PRODUCT-RELEASE "Cisco IOS 12.2(4)MB3"
    STATUS          current
    DESCRIPTION     "IOS 12.2(4)MB3 Cisco CISCO-ITP-RT-MIB.my User Agent
                       MIB capabilities."

    SUPPORTS        CISCO-ITP-RT-MIB
        INCLUDES    { 
                        cItpRtScalarGroup,
                        cItpRouteGroup,
                        cItpRtNotificationsGroup,
                        cItpRtScalarGroupRev1
                    }  
    ::= { ciscoItpRtCapability 2 }

END
