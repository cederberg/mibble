-- $ID$
-- ********************************************************************
-- CISCO-GGSN-MIB.my: MIB file for GGSN 
-- 
-- Dec   2001, Rajesh M. L.
--
-- Copyright (c), 2000, 2001 by Cisco Systems, Inc.
-- All rights reserved.
-- ********************************************************************
-- $Endlog$


CISCO-GGSN-MIB DEFINITIONS ::= BEGIN
 
IMPORTS
        MODULE-IDENTITY,
        NOTIFICATION-TYPE,
        OBJECT-TYPE,
        Integer32,
        Counter32,
        Gauge32
                FROM SNMPv2-SMI
        Unsigned32,
        CiscoAlarmSeverity, CiscoInetAddressMask,
        InterfaceIndexOrZero
                FROM CISCO-TC
        DisplayString,
        TruthValue,
        TimeStamp,
        RowStatus
                FROM SNMPv2-TC
        InetAddressType,
        InetAddress
                FROM INET-ADDRESS-MIB
        MODULE-COMPLIANCE,
        OBJECT-GROUP,
        NOTIFICATION-GROUP
                FROM SNMPv2-CONF
        ciscoMgmt
                FROM CISCO-SMI;


cGgsnMIB    MODULE-IDENTITY
        LAST-UPDATED    "200112081500Z"
        ORGANIZATION    "Cisco Systems, Inc."
        CONTACT-INFO
                "       Cisco Systems
                        Customer Service
 
                Postal: 170 W Tasman Drive
                        San Jose, CA  95134
                        USA
 
                   Tel: +1 800 553-NETS
 
                E-mail: cs-gprs@cisco.com"
        DESCRIPTION
                "This MIB module manages the Gateway GPRS Support
                Node (GGSN) devices. 

                A GGSN device provides interworking with external 
                packet-data network of a particular GPRS service
                provider. It provides a combination of IP routing
                and GPRS specific functionality to support mobile
                users.
               
                Note on notifications:

                When an alarm occurs on the device, if the alarm's
                severity is higher than the severity filter threshold,
                a notification is generated by the device; and if
                cGgsnNotifEnabled is 'true', then the device's
                SNMP-engine configuration will be searched to
                determine where to send the notification. 

                Acronyms and terms:

                 APN    Access Point Name
                 ETSI   European Telecommunications Standards Institute
                 GGSN   Gateway GPRS Support Node
                 GPRS   General Packet Radio Service
                 GSM    Global System for Mobile communication
                 G-PDU  GTP PDU 
                 MS     Mobile Station
                 PDP    Packet Data Protocol
                 PDU    Protocol Data Unit
                 SGSN   Serving GPRS support Node
                 T-PDU  the payload of G-PDU 

                REFERENCE

                [1] GSM 03.60: Digital cellular telecommunications
                    system (Phase 2+); General Packet Radio Service
                    (GPRS); Service description; Stage 2. V7.1.0

                [2] GSM 09.60: Digital cellular telecommunication
                    system (Phase 2+); General Packet Radio Service
                    (GPRS); GPRS Tunnelling Protocol (GTP) across
                    Gn and Gp Interface. V7.3.0"

        REVISION       "200112081500Z"
        DESCRIPTION
                "Initial version of this MIB module."
        ::= {ciscoMgmt 240}

--
-- Object definitions
-- 

cGgsnMIBObjects         OBJECT IDENTIFIER 
                            ::= { cGgsnMIB 1 }

cGgsnStatistics         OBJECT IDENTIFIER
                            ::= { cGgsnMIBObjects 1 }
cGgsnNotifMgmt          OBJECT IDENTIFIER
                            ::= { cGgsnMIBObjects 2 }
cGgsnConfigurations     OBJECT IDENTIFIER
                            ::= { cGgsnMIBObjects 3 }
cGgsnStatus             OBJECT IDENTIFIER
                            ::= { cGgsnMIBObjects 4 }

--
-- MIBObjects
--
 
-- 
-- Statistics 
-- 

cGgsnSentSigMessages          OBJECT-TYPE
    SYNTAX                    Counter32
    UNITS                     "packets"
    MAX-ACCESS                read-only
    STATUS                    current
    DESCRIPTION
         "The number of GTP signalling messages sent."
     ::= { cGgsnStatistics 1 }

cGgsnReceivedSigMessages      OBJECT-TYPE
    SYNTAX                    Counter32
    UNITS                     "packets"
    MAX-ACCESS                read-only
    STATUS                    current
    DESCRIPTION
         "The number of GTP signalling messages received."
     ::= { cGgsnStatistics 2 }

cGgsnUnexpectedSigMessages    OBJECT-TYPE
    SYNTAX                    Counter32
    UNITS                     "packets"
    MAX-ACCESS                read-only
    STATUS                    current
    DESCRIPTION
        "The number of unexpected GTP signalling messages received." 
    ::= { cGgsnStatistics 3 }

cGgsnSentGPDUs                OBJECT-TYPE
    SYNTAX                    Counter32
    UNITS                     "packets"
    MAX-ACCESS                read-only
    STATUS                    current
    DESCRIPTION
        "The number of G-PDU messages sent."
    ::= { cGgsnStatistics 4 }

cGgsnReceivedGPDUs            OBJECT-TYPE
    SYNTAX                    Counter32
    UNITS                     "packets"
    MAX-ACCESS                read-only
    STATUS                    current
    DESCRIPTION
         "The number of G-PDU messages received."
     ::= { cGgsnStatistics 5 }

cGgsnSentGPDUOctets           OBJECT-TYPE
    SYNTAX                    Counter32
    UNITS                     "bytes"
    MAX-ACCESS                read-only
    STATUS                    current
    DESCRIPTION
        "The number of total bytes sent in G-PDU messages."
    ::= { cGgsnStatistics 6 }

cGgsnReceivedGPDUOctets       OBJECT-TYPE
    SYNTAX                    Counter32
    UNITS                     "bytes"
    MAX-ACCESS                read-only
    STATUS                    current
    DESCRIPTION
        "The number of total bytes received in G-PDU messages."
    ::= { cGgsnStatistics 7 }

cGgsnUnexpectedGPDUs          OBJECT-TYPE
    SYNTAX                    Counter32
    UNITS                     "packets"
    MAX-ACCESS                read-only
    STATUS                    current
    DESCRIPTION
        "The number of unexpected G-PDU messages, for example,
        non existent PDP contexts and ACL denial."
    ::= { cGgsnStatistics 8 }

cGgsnActivationRejectedPdps   OBJECT-TYPE
    SYNTAX                    Counter32
    UNITS                     "packets"
    MAX-ACCESS                read-only
    STATUS                    current
    DESCRIPTION
         "The number of PDP contexts that the activation request
         was rejected."
    ::= { cGgsnStatistics 9 }

cGgsnOutOfResourcePdps        OBJECT-TYPE
    SYNTAX                    Counter32
    UNITS                     "packets"
    MAX-ACCESS                read-only
    STATUS                    current
    DESCRIPTION
         "The number of PDP contexts that the activation request
         rejected due to the GGSN running out of resources for
         transmitting GTP packets. Examples:
          - Out of memory;
          - The number of PDPs on GGSN reached limit;
          - all dynamic PDP address are occupied;"
    ::= { cGgsnStatistics 10 }

cGgsnParserErrorMessages      OBJECT-TYPE
    SYNTAX                    Counter32
    UNITS                     "packets"
    MAX-ACCESS                read-only
    STATUS                    current
    DESCRIPTION
         "The number of GTP messages received with wrong value.
         It includes the following cases:

          - mandatory and optional information element in the GTP
            packet is duplicated, missing, unknown, incorrect or
            out of order.

          - the GTP message is too short to hold the GTP header for
            the supported version.

          - the GTP messages running an unsupported version of GTP.

          - Unknown GTP message type."

    ::= { cGgsnStatistics 11 }

cGgsnTotalCreatedPdps         OBJECT-TYPE
    SYNTAX                    Counter32
    UNITS                     "packets"
    MAX-ACCESS                read-only
    STATUS                    current
    DESCRIPTION
         "This object represents the total number of PDP contexts 
         created."
    ::= { cGgsnStatistics 12 }

cGgsnTotalDeletedPdps         OBJECT-TYPE
    SYNTAX                    Counter32
    UNITS                     "packets"
    MAX-ACCESS                read-only
    STATUS                    current
    DESCRIPTION
         "This object represents the total number of PDP contexts
         deleted."
    ::= { cGgsnStatistics 13 }

cGgsnTotalNetworkInitPdps     OBJECT-TYPE
    SYNTAX                    Counter32
    UNITS                     "packets"
    MAX-ACCESS                read-only
    STATUS                    current
    DESCRIPTION
         "This object represents the total number of PDP contexts
         activated by the GGSN that were initiated by the PDN."
    ::= { cGgsnStatistics 14 }

cGgsnTotalPppPdpsCreated      OBJECT-TYPE
    SYNTAX                    Counter32
    UNITS                     "packets"
    MAX-ACCESS                read-only
    STATUS                    current
    DESCRIPTION
         "This object represents the total number of PPP PDP 
         contexts created."
    ::= { cGgsnStatistics 15 }

cGgsnTotalPppPdpsDeleted      OBJECT-TYPE
    SYNTAX                    Counter32
    UNITS                     "packets"
    MAX-ACCESS                read-only
    STATUS                    current
    DESCRIPTION
         "This object represents the total number of PPP PDP
         contexts deleted."
    ::= { cGgsnStatistics 16 }

cGgsnOutOfResourcePppRegenPdps OBJECT-TYPE
    SYNTAX                     Counter32
    UNITS                      "packets"
    MAX-ACCESS                 read-only
    STATUS                     current
    DESCRIPTION
         "This object represents the total number of create PDP 
         context and delete PDP context requests rejected due to 
         unavailable resource on the GGSN for PPP regeneration."
    ::= { cGgsnStatistics 17 }

cGgsnDroppedPppRegenPdps      OBJECT-TYPE
    SYNTAX                    Counter32
    UNITS                     "packets"
    MAX-ACCESS                read-only
    STATUS                    current
    DESCRIPTION
         "This object represents the total number of create PDP 
         context and delete PDP context requests that were dropped 
         due to the threshold limit being reached for maximum number
         of PPP regeneration sessions allowed on the GGSN."
    ::= { cGgsnStatistics 18 }

--
--  Notification and alarm related objects
--

cGgsnNotifEnabled              OBJECT-TYPE
    SYNTAX                     TruthValue
    MAX-ACCESS                 read-write
    STATUS                     current
    DESCRIPTION
        "Indicates whether cGgsnNotification notification will
        be sent when a notification is generated by the device.
          - 'true',  it will enable the device to send a notification,
                     as well as logging the notification to the
                     cGgsnHistNotifTable.
          - 'false', it will prevent the device from sending out a
                     notification, but it will still log the
                     notification into cGgsnHistNotifTable."
    DEFVAL { false }
    ::= { cGgsnNotifMgmt 1 }

cGgsnNotifLeastSeverLevel      OBJECT-TYPE
    SYNTAX                     CiscoAlarmSeverity
    MAX-ACCESS                 read-write
    STATUS                     current
    DESCRIPTION
        "Indicates the least severity level of the cGgsnNotification
        notifications to be generated by the device. Thus, notifications
        are not generated for alarms with a severity level less urgent 
        than the value of this object. This object cannot be set to
        cleared(1) or indeterminate(2)."
   DEFVAL { info }
   ::= { cGgsnNotifMgmt 2 }

cGgsnGeneratedNotifs           OBJECT-TYPE
    SYNTAX                     Counter32
    UNITS                      "notifications"
    MAX-ACCESS                 read-only
    STATUS                     current
    DESCRIPTION
        "The number of cGgsnNotification notifications that have
        been generated since sysUpTime."
    ::= { cGgsnNotifMgmt 3 }

cGgsnIgnoredAlarms             OBJECT-TYPE
    SYNTAX                     Counter32
    UNITS                      "notifications"
    MAX-ACCESS                 read-only
    STATUS                     current
    DESCRIPTION
        "The number of alarms which are less severe than
        cGgsnNotifLeastSeverLevel since sysUpTime, and thus,
        for which no notification was generated."
    ::= { cGgsnNotifMgmt 4 }

cGgsnHistNotifMaxLength        OBJECT-TYPE
    SYNTAX                     Integer32 (1..2147483647)
    UNITS                      "entries"
    MAX-ACCESS                 read-write
    STATUS                     current
    DESCRIPTION
        "The maximum number of entries to be retained in the
        cGgsnHistNotifTable. When the table is full, the oldest 
        entries are removed to make space for new entries." 
    DEFVAL  { 100 }
    ::= { cGgsnNotifMgmt 5 }

cGgsnHistNotifLatestIndex      OBJECT-TYPE
    SYNTAX                     Unsigned32 (1..4294967295)
    MAX-ACCESS                 read-only
    STATUS                     current
    DESCRIPTION
        "The value of cGgsnHistNotifIndex for the most recently 
         created entry in cGgsnHistNotifTable."
    ::= { cGgsnNotifMgmt 6 }

cGgsnHistNotifTable            OBJECT-TYPE
    SYNTAX                     SEQUENCE OF CGgsnHistNotifEntry
    MAX-ACCESS                 not-accessible
    STATUS                     current
    DESCRIPTION
        "A history table of the most recent cGgsnNotification
        notifications generated by this device.
        If a new cGgsnNotification notification is generated when
        the number of entries is equal to cGgsnHistNotifMaxLength,
        then the oldest entry is deleted and replaced with an entry
        for the latest notification."
    ::= { cGgsnNotifMgmt 7 }

cGgsnHistNotifEntry            OBJECT-TYPE
    SYNTAX                     CGgsnHistNotifEntry
    MAX-ACCESS                 not-accessible
    STATUS                     current
    DESCRIPTION
        "Detailed information concerning a particular notification
        that previously generated from this device."
    INDEX   { cGgsnHistNotifIndex }
    ::= { cGgsnHistNotifTable 1 }

CGgsnHistNotifEntry        ::= SEQUENCE {
    cGgsnHistNotifIndex           Unsigned32,
    cGgsnHistNotifType            INTEGER,
    cGgsnHistNotifSeverity        CiscoAlarmSeverity,
    cGgsnHistNotifTimestamp       TimeStamp,
    cGgsnHistNotifGgsnIpAddrType  InetAddressType,
    cGgsnHistNotifGgsnIpAddr      InetAddress,
    cGgsnHistNotifInfo            DisplayString
    }

cGgsnHistNotifIndex            OBJECT-TYPE
    SYNTAX                     Unsigned32 (1..4294967295)
    MAX-ACCESS                 not-accessible
    STATUS                     current
    DESCRIPTION
        "A monotonically increasing integer for the sole purpose of
        indexing notifications. When it reaches the maximum value,
        it wraps the value back to 1."
    ::= { cGgsnHistNotifEntry 1 }

cGgsnHistNotifType             OBJECT-TYPE
    SYNTAX   INTEGER {
               ggsnServiceUp(1),   -- GGSN service has started
               ggsnServiceDown(2), -- GGSN service is shutdown
               mapSgsnUp(3),       -- MAP-SGSN service has started
               mapSgsnDown(4),     -- MAP-SGSN service is shutdown
               noResource(5),      -- MS initiated PDP count reaches 
                                   -- the limit OR
                                   -- Network initiated PDP count 
                                   -- reaches the limit
               noRADIUS(6),        -- RADIUS Server is not configured
               noDHCPServer(7),    -- DHCP server is not configured
               ipAllocationFail(8),-- IP address allocation failed
               authenticationFail(9), -- Authentication failed
               apnUnreachable(10)  -- Access point is not reachable
             }

    MAX-ACCESS                 read-only
    STATUS                     current
    DESCRIPTION
        "This object indicates the type of notification."
    ::= { cGgsnHistNotifEntry 2 }

cGgsnHistNotifSeverity         OBJECT-TYPE
    SYNTAX                     CiscoAlarmSeverity
    MAX-ACCESS                 read-only
    STATUS                     current
    DESCRIPTION
        "This object indicates the severity level of the
        notification. This object cannot be set to cleared(1)
        or indeterminate(2)."
    ::= { cGgsnHistNotifEntry 3 }

cGgsnHistNotifTimestamp        OBJECT-TYPE
    SYNTAX                     TimeStamp
    MAX-ACCESS                 read-only
    STATUS                     current
    DESCRIPTION
        "This object indicates the value of sysUpTime when
        this notification was generated."
    ::= { cGgsnHistNotifEntry 4 }

cGgsnHistNotifGgsnIpAddrType   OBJECT-TYPE
    SYNTAX                     InetAddressType
    MAX-ACCESS                 read-only
    STATUS                     current
    DESCRIPTION
        "This object indicates the type of Internet address
         by which cGgsnHistNotifGgsnIpAddr is reachable."
    ::= { cGgsnHistNotifEntry 5 }

cGgsnHistNotifGgsnIpAddr       OBJECT-TYPE
    SYNTAX                     InetAddress
    MAX-ACCESS                 read-only
    STATUS                     current
    DESCRIPTION
        "The object indicates the IP address that uniquely
        identifies the device which generated the notification."
    ::= { cGgsnHistNotifEntry 6 }

cGgsnHistNotifInfo             OBJECT-TYPE
    SYNTAX                     DisplayString (SIZE (1..64))
    MAX-ACCESS                 read-only
    STATUS                     current
    DESCRIPTION
        "A textual description of cGgsnHistNotifType, which
        potentially contains additional information (more than
        just the type of alarm).
        If the text of the message exceeds 64 bytes, the message
        will be truncated to 63 bytes and a '*' character will
        be appended to indicate the message has been truncated."
   ::= { cGgsnHistNotifEntry 7 }

--
-- Configurations
--

cGgsnDefaultIpAllocationMethod  OBJECT-TYPE
    SYNTAX                      INTEGER {
                                   disable(1),
                                   dhcp(2),
                                   radius(3)
                                }
    MAX-ACCESS                  read-write
    STATUS                      current
    DESCRIPTION
        "Specifies the default method by which the GGSN obtains 
         address leases for mobile user sessions.

            - 'disable', which indicates that dynamic address 
            allocation is disabled.

            - 'dhcp', which indicates that the DHCP server 
            will be used.

            - 'radius', which indicates that the radius server
            will be used."

        DEFVAL { disable }
        ::= { cGgsnConfigurations 1 }

cGgsnIdlePdpPurgeTimer   OBJECT-TYPE
    SYNTAX               Unsigned32 (0..255)
    UNITS                "hours"
    MAX-ACCESS           read-write
    STATUS               current
    DESCRIPTION
        "This object specifies the time that the GGSN waits
         before purging idle PDP contexts. A value '0' will
         disable the purge timer."
    DEFVAL { 72 }
    ::= { cGgsnConfigurations 2 }

cGgsnIpDupProtectTable   OBJECT-TYPE
    SYNTAX               SEQUENCE OF CGgsnIpDupProtectEntry
    MAX-ACCESS           not-accessible
    STATUS               current
    DESCRIPTION
        "This table contains the range of IP address used in the 
        GPRS PLMN. These IP addresses are used to avoid IP address 
        duplication in GPRS network. IP address duplication occurs 
        when a MS uses an IP address which is already used in the PLMN.
        The IP addresses configured inside GPRS network should be in 
        these ranges and MS IP address should not be in this range."
    ::= { cGgsnConfigurations 3 }

cGgsnIpDupProtectEntry   OBJECT-TYPE
    SYNTAX               CGgsnIpDupProtectEntry
    MAX-ACCESS           not-accessible
    STATUS               current
    DESCRIPTION
        "Entry containing the start and end IP address in the address 
         range. An Entry with start IP >= end IP is not allowed.
         No new entry will be accepted if that would cause any IP
         address(es) to be represented by more than one row in this 
         table."
    INDEX    { cGgsnMsExcludeRangeStartIpType,
               cGgsnMsExcludeRangeStartIp,
               cGgsnMsExcludeRangeEndIpType,
               cGgsnMsExcludeRangeEndIp }
    ::= { cGgsnIpDupProtectTable 1 }

CGgsnIpDupProtectEntry   ::= SEQUENCE {
    cGgsnMsExcludeRangeStartIpType    InetAddressType,
    cGgsnMsExcludeRangeStartIp        InetAddress,
    cGgsnMsExcludeRangeEndIpType      InetAddressType,
    cGgsnMsExcludeRangeEndIp          InetAddress,
    cGgsnIpDupProtectRowStatus        RowStatus
    }

cGgsnMsExcludeRangeStartIpType OBJECT-TYPE
    SYNTAX                     InetAddressType
    MAX-ACCESS                 not-accessible
    STATUS                     current
    DESCRIPTION
        "The type of Internet address by which 
        cGgsnMsExcludeRangeStartIp is reachable. The value of this 
        object should be same as cGgsnMsExcludeRangeEndIpType."
    ::= { cGgsnIpDupProtectEntry 1 }

cGgsnMsExcludeRangeStartIp     OBJECT-TYPE
    SYNTAX                     InetAddress
    MAX-ACCESS                 not-accessible
    STATUS                     current
    DESCRIPTION
        "Starting IP address in the address range." 
    ::= { cGgsnIpDupProtectEntry 2 }

cGgsnMsExcludeRangeEndIpType   OBJECT-TYPE
    SYNTAX                     InetAddressType
    MAX-ACCESS                 not-accessible
    STATUS                     current
    DESCRIPTION
        "The type of Internet address by which cGgsnMsExcludeRangeEndIp
        is reachable. The value of this object should be same as
        cGgsnMsExcludeRangeStartIpType."
    ::= { cGgsnIpDupProtectEntry 3 }

cGgsnMsExcludeRangeEndIp       OBJECT-TYPE
    SYNTAX                     InetAddress
    MAX-ACCESS                 not-accessible
    STATUS                     current
    DESCRIPTION
        "Ending IP address in the address range." 
    ::= { cGgsnIpDupProtectEntry 4 }

cGgsnIpDupProtectRowStatus     OBJECT-TYPE
    SYNTAX                     RowStatus
    MAX-ACCESS                 read-create
    STATUS                     current
    DESCRIPTION
        "This object is used to create a new row or delete an
        existing row in this table.

        To create a row, set this object to 'createAndGo'.
        To delete a row, set this object to 'destroy'."
    ::= { cGgsnIpDupProtectEntry 5 }

cGgsnDefaultAggregTable        OBJECT-TYPE
    SYNTAX                     SEQUENCE OF CGgsnDefaultAggregEntry
    MAX-ACCESS                 not-accessible
    STATUS                     current
    DESCRIPTION
        "This table contains the list of default aggregate routes 
        configured on the GGSN. GGSN uses a static host route to 
        forward user data packets for each PDP context received 
        from Gi interface to Gn interface. Using the aggregate 
        route (address range), the total number of static routes 
        implemented in the GGSN for PDP requests can be greatly 
        reduced."
    ::= { cGgsnConfigurations 4 }

cGgsnDefaultAggregEntry        OBJECT-TYPE
    SYNTAX                     CGgsnDefaultAggregEntry
    MAX-ACCESS                 not-accessible
    STATUS                     current
    DESCRIPTION
        "An Entry contains the IP network prefix which is used to 
        combine the routes of PDP requests for the same network as 
        a single route on the GGSN."
    INDEX    { cGgsnDefaultAggregIpAddrType,
               cGgsnDefaultAggregIpAddr,
               cGgsnDefaultAggregIpMask
             }
    ::= { cGgsnDefaultAggregTable 1 }

CGgsnDefaultAggregEntry         ::= SEQUENCE {
    cGgsnDefaultAggregIpAddrType    InetAddressType,
    cGgsnDefaultAggregIpAddr        InetAddress,
    cGgsnDefaultAggregIpMask        CiscoInetAddressMask,
    cGgsnDefaultAggregRowStatus     RowStatus
    }


cGgsnDefaultAggregIpAddrType   OBJECT-TYPE
    SYNTAX                     InetAddressType
    MAX-ACCESS                 not-accessible
    STATUS                     current
    DESCRIPTION
        "This object specifies the type of Internet address 
        denoted by cGgsnDefaultAggregIpAddr."
    ::= { cGgsnDefaultAggregEntry 1  }

cGgsnDefaultAggregIpAddr       OBJECT-TYPE
    SYNTAX                     InetAddress
    MAX-ACCESS                 not-accessible
    STATUS                     current
    DESCRIPTION
        "This object specifies the IP address whose network prefix
        is going to be defined by cGgsnDefaultAggregIpMask."
    ::= { cGgsnDefaultAggregEntry 2 }

cGgsnDefaultAggregIpMask       OBJECT-TYPE
    SYNTAX                     CiscoInetAddressMask
    MAX-ACCESS                 not-accessible
    STATUS                     current
    DESCRIPTION
        "This object specifies the net-mask pertaining to 
        cGgsnDefaultAggregIpAddr."
    ::= { cGgsnDefaultAggregEntry 3 }

cGgsnDefaultAggregRowStatus    OBJECT-TYPE
    SYNTAX                     RowStatus
    MAX-ACCESS                 read-create
    STATUS                     current
    DESCRIPTION
        "This object is used to create a new row or delete an
        existing row in this table.

        To create a row, set this object to 'createAndGo'.
        To delete a row, set this object to 'destroy'.
        The values 'createAndWait' and 'notInService' are
        not supported."
    ::= { cGgsnDefaultAggregEntry 4 }

cGgsnDefaultAaaAuthServerGroup OBJECT-TYPE
    SYNTAX                     DisplayString
    MAX-ACCESS                 read-write
    STATUS                     current
    DESCRIPTION
        "This object specifies the AAA radius server group
        that is used for authentication by all APN's on this GGSN."
    ::= { cGgsnConfigurations 5 }

cGgsnDefaultAaaAccServerGroup  OBJECT-TYPE
    SYNTAX                     DisplayString
    MAX-ACCESS                 read-write
    STATUS                     current
    DESCRIPTION
        "This object specifies the AAA radius server group
        that is used for accounting  by all APN's on this GGSN."
    ::= { cGgsnConfigurations 6 }

cGgsnPppVirtualTemplate        OBJECT-TYPE
    SYNTAX                     InterfaceIndexOrZero
    MAX-ACCESS                 read-write
    STATUS                     current
    DESCRIPTION
        "This object represents the virtual template interface used
        by PPP Type PDP's."
    ::= { cGgsnConfigurations 7 }

cGgsnPppRegenVirtualTemplate   OBJECT-TYPE
    SYNTAX                     InterfaceIndexOrZero
    MAX-ACCESS                 read-write
    STATUS                     current
    DESCRIPTION
        "This object represents the virtual template interface used
        for PPP Regeneration by the APN's on which PPP Regeneration 
        is configured.

        The value zero indicates that no interface is specified."
    DEFVAL { 0 }
    ::= { cGgsnConfigurations 8 }

--
-- Status 
--

cGgsnVersion                   OBJECT-TYPE
    SYNTAX                     INTEGER {
                                        release14(1),
                                        release30(2),
                                        release40(3)
                               }
    MAX-ACCESS                 read-only
    STATUS                     current
    DESCRIPTION
        "This object specifies the which release of GPRS
        image is currently running on the GGSN."
    ::= { cGgsnStatus 1 }

cGgsnActiveNetworkInitPdps    OBJECT-TYPE
    SYNTAX                    Gauge32
    UNITS                     "packets"
    MAX-ACCESS                read-only
    STATUS                    current
    DESCRIPTION
         "This object represents the number of network initiated
         PDP contexts that are currently active."
    ::= { cGgsnStatus 2 }

cGgsnActivePppPdps            OBJECT-TYPE
    SYNTAX                    Gauge32
    UNITS                     "packets"
    MAX-ACCESS                read-only
    STATUS                    current
    DESCRIPTION
         "This object represents the number of PPP PDP contexts
          that are currently active."
    ::= { cGgsnStatus 3 }

cGgsnActivePppRegenPdps       OBJECT-TYPE
    SYNTAX                    Gauge32
    UNITS                     "packets"
    MAX-ACCESS                read-only
    STATUS                    current
    DESCRIPTION
         "This object represents the number of PPP-Regen PDP contexts
          that are currently active."
    ::= { cGgsnStatus 4 }

cGgsnPendingPppRegenPdps      OBJECT-TYPE
    SYNTAX                    Gauge32
    UNITS                     "packets"
    MAX-ACCESS                read-only
    STATUS                    current
    DESCRIPTION
         "This object represents the current number of pending 
         PPP regeneration sessions."
    ::= { cGgsnStatus 5 }

--
--  Notification Definitions
--

cGgsnNotifPrefix       OBJECT IDENTIFIER
                           ::= { cGgsnMIB 2 }
cGgsnNotifications     OBJECT IDENTIFIER
                           ::= { cGgsnNotifPrefix 0 }

--
-- notifications
--

cGgsnNotification      NOTIFICATION-TYPE
    OBJECTS                {
                            cGgsnHistNotifType,
                            cGgsnHistNotifSeverity,
                            cGgsnHistNotifTimestamp,
                            cGgsnHistNotifGgsnIpAddrType,
                            cGgsnHistNotifGgsnIpAddr,
                            cGgsnHistNotifInfo
                           }
    STATUS            current
    DESCRIPTION
        "This notification indicates the occurrence of a GGSN 
        related alarm. If and when additional useful information
        is availble for specific types of alarms, then that  
        information may be appended to the end of the
        notification in additional varbinds."
    ::= { cGgsnNotifications 1 }

-- 
-- Conformances definitions
-- 

cGgsnMIBConformances   OBJECT IDENTIFIER
                           ::= { cGgsnMIB 3 }

cGgsnMIBCompliances    OBJECT IDENTIFIER
                           ::= { cGgsnMIBConformances 1}
cGgsnMIBGroups         OBJECT IDENTIFIER
                           ::= { cGgsnMIBConformances 2}

--
-- Compliances statements
--

cGgsnMIBCompliance   MODULE-COMPLIANCE
        STATUS           current
        DESCRIPTION
             "The compliance statements for entities which
             implement the CISCO GGSN MIB.

             An implementation for cGgsnMsExcludeRangeStartIpType
             and cGgsnMsExcludeRangeEndIpType is only required
             to support IPv4 addresses."
        MODULE      -- this module
        MANDATORY-GROUPS { cGgsnStatisticsGroup,
                           cGgsnNotifMgmtGroup,
                           cGgsnConfigurationsGroup,
                           cGgsnNotifGroup,
                           cGgsnStatusGroup
                         }
        ::= { cGgsnMIBCompliances 1 }

-- units of conformance

cGgsnStatisticsGroup   OBJECT-GROUP
    OBJECTS                {
                           cGgsnSentSigMessages,
                           cGgsnReceivedSigMessages,
                           cGgsnUnexpectedSigMessages,
                           cGgsnSentGPDUs,
                           cGgsnReceivedGPDUs,
                           cGgsnSentGPDUOctets,
                           cGgsnReceivedGPDUOctets,
                           cGgsnUnexpectedGPDUs,
                           cGgsnActivationRejectedPdps,
                           cGgsnOutOfResourcePdps,
                           cGgsnParserErrorMessages,
                           cGgsnTotalCreatedPdps,
                           cGgsnTotalDeletedPdps,
                           cGgsnTotalNetworkInitPdps,
                           cGgsnTotalPppPdpsCreated,
                           cGgsnTotalPppPdpsDeleted,
                           cGgsnOutOfResourcePppRegenPdps,
                           cGgsnDroppedPppRegenPdps
                           }
    STATUS                 current
    DESCRIPTION
        " A collection of statistics on GGSN."
    ::= { cGgsnMIBGroups 1 }

cGgsnNotifMgmtGroup   OBJECT-GROUP
    OBJECTS                {
                           cGgsnNotifEnabled,
                           cGgsnNotifLeastSeverLevel,
                           cGgsnGeneratedNotifs,
                           cGgsnIgnoredAlarms,
                           cGgsnHistNotifMaxLength,
                           cGgsnHistNotifLatestIndex,
                           cGgsnHistNotifType,
                           cGgsnHistNotifSeverity,
                           cGgsnHistNotifTimestamp,
                           cGgsnHistNotifGgsnIpAddrType,
                           cGgsnHistNotifGgsnIpAddr,
                           cGgsnHistNotifInfo
                           }
    STATUS                 current
    DESCRIPTION
        " A collection of objects related with notification
        management on GGSN."
    ::= { cGgsnMIBGroups 2 }

cGgsnConfigurationsGroup   OBJECT-GROUP
    OBJECTS                {
                           cGgsnDefaultIpAllocationMethod,
                           cGgsnIdlePdpPurgeTimer,
                           cGgsnIpDupProtectRowStatus,
                           cGgsnDefaultAggregRowStatus,
                           cGgsnDefaultAaaAuthServerGroup,
                           cGgsnDefaultAaaAccServerGroup,
                           cGgsnPppVirtualTemplate,
                           cGgsnPppRegenVirtualTemplate
                           }
    STATUS                 current
    DESCRIPTION
        " A collection of objects related with configurations on
         GGSN"
    ::= { cGgsnMIBGroups 3 }

cGgsnNotifGroup         NOTIFICATION-GROUP
    NOTIFICATIONS       { cGgsnNotification }
    STATUS              current
    DESCRIPTION
        "A collection of notifications."
    ::= { cGgsnMIBGroups 4 }

cGgsnStatusGroup           OBJECT-GROUP
    OBJECTS                {
                           cGgsnVersion,
                           cGgsnActiveNetworkInitPdps,
                           cGgsnActivePppPdps,
                           cGgsnActivePppRegenPdps,
                           cGgsnPendingPppRegenPdps
                           }
    STATUS                 current
    DESCRIPTION
        " A collection of objects representing status on GGSN."
    ::= { cGgsnMIBGroups 5 }

END
