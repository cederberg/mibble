-- *****************************************************************
-- CISCO-ITP-XUA-MIB: ITP M3UA/SUA MIB for SS7oIP
--
-- December 2001, Shekhar Acharya, John Linton
--
-- Copyright (c) 2001-2002 by Cisco Systems, Inc.
-- All rights reserved.
-- *****************************************************************
CISCO-ITP-XUA-MIB DEFINITIONS ::= BEGIN

IMPORTS
        Counter32,
        Gauge32,
        MODULE-IDENTITY,
        NOTIFICATION-TYPE,
        OBJECT-TYPE,
        TimeTicks,
        Unsigned32
                FROM SNMPv2-SMI
                
        InetAddressType, 
        InetAddress,
        InetPortNumber
             FROM INET-ADDRESS-MIB

        CItpTcPointCode,
        CItpTcSubSystemNumber,
        CItpTcServiceIndicator,
        CItpTcXuaName,
        CItpTcQos
                FROM CISCO-ITP-TC-MIB

        cItpSpCLLICode
                FROM CISCO-ITP-SP-MIB

        RowStatus,
        TruthValue,
        TEXTUAL-CONVENTION
                FROM SNMPv2-TC

        MODULE-COMPLIANCE,
        NOTIFICATION-GROUP,
        OBJECT-GROUP
                FROM SNMPv2-CONF

        ciscoMgmt
                FROM CISCO-SMI;

ciscoItpXuaMIB MODULE-IDENTITY
        LAST-UPDATED    "200204150000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7@cisco.com"
        DESCRIPTION
                "The MIB for MTP3 User Adaptation (M3UA) and SCCP User
                 Adaptation (SUA) for Cisco's IP Transfer Point (ITP)
                 implementation.
                
                 The Cisco IP Transfer Point (ITP) is a hardware and
                 software solution that transports SS7 traffic using
                 IP. Each ITP node provides function similar to SS7
                 signaling point.   
                
                 The relevant ITU documents describing this technology
                 is the ITU Q series, including ITU Q.700: Introduction
                 to CCITT Signaling System No. 7 and ITU Q.701
                 Functional description of the message transfer part
                 (MTP) of Signaling System No. 7.

                 The relevent information about M3UA and SUA is
                 available at the IETF:
                 http://www.ietf.org/html.charters/sigtran-charter.html

                 This MIB consists of the following tables:
                   M3UA/SUA (XUA) Instance Table
                   M3UA/SUA (XUA) Instance Local IP Table
                   Signaling Gateway Mate Table
                   Application Server Process (ASP) Table
                   Application Server Process (ASP) Remote IP Table
                   Application Server Process (ASP) Statistics Table
                   Application Server (AS) Table
                   ASP-AS Table

                 Abbreviations:
                 AS    - Application Server
                 ASP   - Application Server Process
                 ASPAC - ASP ACtive message
                 ASPDN - ASP Down message
                 ASPIA - ASP InActive message
                 ASPUP - ASP UP message
                 CIC   - Circuit Identifier Code for ISUP
                 CLLI  - Common Language Location Codes
                 DPC   - Destination Point Code
                 DAUD  - Destination AUDit
                 DAVA  - Destination AVAilable
                 DUNA  - Destination UNAvailable
                 DUPU  - Destination User Part Unavailable
                 ERR   - Error message
                 GTT   - Global Title Translation
                 HLR   - Home Location Registry
                 ISDN  - Integrated Services Digital Network
                 ISUP  - ISDN User Part
                 M3UA  - MTP3 User Adaptation
                 MGC   - Media Gateway Controller used in VoIP
                 MTP   - Message Transport Protocol
                 MTP2  - Layer 2 of Message Transport Protocol
                 MTP3  - Layer 3 of Message Transport Protocol
                 NMS   - Network Management System
                 OPC   - Originating Point Code
                 PC    - Point Code
                 QOS   - Quality Of Service
                 SCCP  - Signaling Connection Control Part
                 SCP   - Service Control Point (SS7)
                 SCON  - Signaling link CONgestion
                 SCON0 - Signaling link CONgestion level 0 (no congestion)
                 SCON1 - Signaling link CONgestion level 1
                 SCON2 - Signaling link CONgestion level 2
                 SCON3 - Signaling link CONgestion level 3
                 SGMP  - Signaling Gateway Mated Protocol
                 SCTP  - Stream Transmission Protocol(RFC 2960)
                 SI    - Signaling Indicator
                 SIO   - Service Indicator Octet (SS7)
                 SNMM  - Signaling Network Management Message
                 SSN   - Subsystem Number for SCCP
                 SUA   - SCCP User Adaptation
                 TT    - Title Translation
                 XUA   - M3UA, SUA or SGMP

                 Brief description:

                 The Signaling Gateway (SG) on the ITP receives the SS7
                 packets, converts them to M3UA/SUA packets and routes
                 them to the ASPs over SCTP/IP association. The routing
                 of the packet depends on the routing information
                 present in the packet and the routing keys configured
                 as part of the ASes. 

                 There can be one or more instances of M3UA/SUA at the
                 SG. These instances are identified by a unique port
                 number. Each of these instances can have one or more
                 IP addresses which form 'local' end of the multi-homing
                 SCTP association.

                 The Application Server Process (ASP) is a remote entity
                 which has its own port number and one or more IP
                 addresses to form the 'remote' end of the multi-homing
                 SCTP association. Examples of ASPs are MGCs, IP SCPs or
                 IP HLRs.

                 Application Server (AS), as described in section
                 '1.2 Terminology' of M3UA/SUA draft, is a logical
                 entity serving a specific Routing Key. An example of
                 an AS is a virtual switch element handling all call
                 processing for a unique range of PSTN trunks,
                 identified by an SS7 SIO/DPC/OPC/CIC_range. Another
                 example is a virtual database element, handling all
                 HLR transactions for a particular SS7 DPC/OPC/SCCP_SSN
                 combination. The AS contains a set of one or more
                 unique ASPs of which one or more is normally actively
                 processing traffic. Note that there is a 1:1
                 relationship between an AS and a Routing Key.

                 An ASP can serve one or more ASes and an AS can have
                 one or more ASPs. An ASP while serving an AS can be
                 active, inactive or down. When one or more ASPs for
                 an AS is active, the AS is active. When all ASPs for
                 an AS are inactive, the AS is inactive. The state of
                 the AS is maintained in one object, whereas, the state
                 of an ASP is maintained for each AS that it serves in
                 ASP-AS table.

                 The SGs are always deployed in mated pairs to provide
                 high availability and redundancy. The SG mates exchange
                 the state of ASes. When an AS is down on one SG, it can
                 route the SS7 message to its mate which can properly
                 route that SS7 message."

        REVISION        "200204150000Z"
        DESCRIPTION
                "Initial version of this MIB module."
        ::= { ciscoMgmt 253 }

-- Top-level structure of the MIB
ciscoItpXuaMIBNotifs     OBJECT IDENTIFIER ::= { ciscoItpXuaMIB 0 }
ciscoItpXuaMIBObjects    OBJECT IDENTIFIER ::= { ciscoItpXuaMIB 1 }
ciscoItpXuaConformance   OBJECT IDENTIFIER ::= { ciscoItpXuaMIB 2 }

cItpXuaScalars       OBJECT IDENTIFIER ::= { ciscoItpXuaMIBObjects 1 }
cItpXuaInst          OBJECT IDENTIFIER ::= { ciscoItpXuaMIBObjects 2 }
cItpXuaInstLocalIp   OBJECT IDENTIFIER ::= { ciscoItpXuaMIBObjects 3 }
cItpXuaSgm           OBJECT IDENTIFIER ::= { ciscoItpXuaMIBObjects 4 }
cItpXuaAsp           OBJECT IDENTIFIER ::= { ciscoItpXuaMIBObjects 5 }
cItpXuaAspRemoteIp   OBJECT IDENTIFIER ::= { ciscoItpXuaMIBObjects 6 }
cItpXuaAspStats      OBJECT IDENTIFIER ::= { ciscoItpXuaMIBObjects 7 }
cItpXuaAs            OBJECT IDENTIFIER ::= { ciscoItpXuaMIBObjects 8 }
cItpXuaAspAs         OBJECT IDENTIFIER ::= { ciscoItpXuaMIBObjects 9 }
cItpXuaMIBNotifObjects  OBJECT IDENTIFIER ::=
        { ciscoItpXuaMIBObjects 10 }

-- ********************************************************************
-- *                                                                  *
-- * Textual Conventions                                              *
-- *                                                                  *
-- ********************************************************************

CItpXuaProtocol ::= TEXTUAL-CONVENTION
        STATUS          current
        DESCRIPTION
                "The possible protocol types supported by AS or ASP
                'm3ua'  : The protocol is M3UA.
                'sua'   : The protocol is SUA.
                'sgmp'  : The protocol is Signaling Gateway Mated
                          Protocol (SGMP)."
        SYNTAX INTEGER {
                m3ua(1),
                sua(2),
                sgmp(3)
        }

CItpXuaTrafMode ::= TEXTUAL-CONVENTION
        STATUS          current
        DESCRIPTION
                "The possible traffic modes supported by AS
                'overRide'  : In override mode, one ASP takes over
                   all traffic for the AS, possibly overriding any
                   currently active ASP in the AS.

                'broadcast' : In broadcast mode, every active ASP
                   receives the same message.

                'loadBind'  : In loadshare bindings mode, an ASP
                   shares in the traffic distribution with any other
                   currently active ASPs based on ASP bindings.

                'loadRndRobin' : In loadshare roundrobin mode, an
                   ASP shares in the traffic distribution with any
                   other currently active ASPs using a roundrobin
                   algorithm."
        REFERENCE
                "3.7.1 ASP Active in M3UA draft and 3.9.11 Traffic Mode
                 Type in SUA draft."
        SYNTAX INTEGER {
                overRide(1),
                loadBind(2),
                loadRndRobin(3),
                broadcast(4)
        }

CItpXuaAsState ::= TEXTUAL-CONVENTION
        STATUS          current
        DESCRIPTION
                "The possible AS states
                'down' : The AS is unavailable. This state implies 
                         that all ASPs that are serving this AS are
                         in the 'down' state. Initially the AS will
                         be in this state.

                'inactive' : The AS is available but no application 
                             traffic is active (i.e., one or more
                             ASPs are in the inactive state, but none
                             in the active state).

                'active' : The AS is available and application traffic 
                           is active.  This state implies that at least
                           one ASP is in the active state.

                'pending' : An active ASP has transitioned to inactive
                            or down and it was the last remaining
                            active ASP serving the AS. Depending on
                            the recovery timer and an ASP becoming
                            active this AS moves to active, inactive,
                            or down state."
        REFERENCE
                "4.3.2 AS States in M3UA/SUA draft."
        SYNTAX INTEGER {
                down(1),
                inactive(2),
                active(3),
                pending(4)
        }

CItpXuaAspState ::= TEXTUAL-CONVENTION
        STATUS          current
        DESCRIPTION
                "The possible ASP states
                'down' : The remote peer at the ASP is unavailable
                         and/or the related SCTP association is down.
                         Initially all ASPs will be in this state.

                'inactive' : The remote peer at the ASP is available
                             (and the related SCTP association is up)
                             but application traffic is stopped. In 
                             this state the ASP should not be sent any
                             DATA or SNMM messages for the AS for
                             which the ASP is inactive.

                'active' : The remote peer at the ASP is available and 
                           application traffic is active."
        REFERENCE
                "4.3.1 ASP States in M3UA/SUA draft."
        SYNTAX INTEGER {
                down(1),
                inactive(2),
                active(3)
        }

--  *************************************************************
--  *                                                           *
--  * XUA Scalars                                               *
--  *                                                           *
--  *************************************************************
         
cItpXuaInstConfigLastChanged OBJECT-TYPE
        SYNTAX          TimeTicks
        MAX-ACCESS      read-only
        STATUS          current
        DESCRIPTION
                "The value of system timestamp at the time of the last
                 creation or deletion of an entry in the
                 cItpXuaInstTable. This value can be used to prevent
                 unnecessary walks of the XUA Instance Table."
        ::= { cItpXuaScalars 1 }

cItpXuaSgmConfigLastChanged OBJECT-TYPE
        SYNTAX          TimeTicks
        MAX-ACCESS      read-only
        STATUS          current
        DESCRIPTION
                "The value of system timestamp at the time of the last
                 creation or deletion of an entry in the
                 cItpXuaSgmTable. This value can be used to prevent
                 unnecessary walks of the XUA SG Mate Table."
        ::= { cItpXuaScalars 2 }

cItpXuaAspConfigLastChanged OBJECT-TYPE
        SYNTAX          TimeTicks
        MAX-ACCESS      read-only
        STATUS          current
        DESCRIPTION
                "The value of system timestamp at the time of the last
                 creation or deletion of an entry in the
                 cItpXuaAspTable. This value can be used to prevent
                 unnecessary walks of the XUA ASP Table."
        ::= { cItpXuaScalars 3 }

cItpXuaAsConfigLastChanged OBJECT-TYPE
        SYNTAX          TimeTicks
        MAX-ACCESS      read-only
        STATUS          current
        DESCRIPTION
                "The value of system timestamp at the time of the last
                 creation or deletion of an entry in the
                 cItpXuaAsTable. This value can be used to prevent
                 unnecessary walks of the XUA AS Table."
        ::= { cItpXuaScalars 4 }

cItpXuaStateChangeNotifEnabled  OBJECT-TYPE
        SYNTAX          TruthValue
        MAX-ACCESS      read-write
        STATUS          current
        DESCRIPTION 
                "The State notification truth value.
                'true'  Indicates that the notification generation
                        is enabled for ASP state changes, AS state
                        changes and SG Mate state changes.
                'false' Indicates that the notification generation
                        is disabled for ASP state change, AS state
                        and SG Mate state change."
        DEFVAL { false }
        ::= { cItpXuaScalars 5 }

--  *************************************************************
--  *                                                           *
--  * XUA Instance Table                                        *
--  *                                                           *
--  *************************************************************

cItpXuaInstTable        OBJECT-TYPE
        SYNTAX          SEQUENCE OF CItpXuaInstTableEntry 
        MAX-ACCESS      not-accessible
        STATUS          current
        DESCRIPTION
                "A table of M3UA/SUA/SGMP instances.

                 There can be multiple M3UA or SUA instances on a
                 given Signaling Gateway. Each instance is uniquely
                 identified by the port number. The local port number
                 of the ASP (cItpXuaAspLocalPort) matches with the
                 port number of the instance (cItpXuaInstPort).

                 Also for a given instance, there can be multiple
                 local IP addresses which are used for the
                 multi-homing feature of the SCTP associations.

                 There can only be one instance of SGMP.

                 Entries are added to this table via 
                 cItpXuaInstRowStatus in accordance with the 
                 RowStatus convention."
        ::= { cItpXuaInst 1 }

cItpXuaInstTableEntry   OBJECT-TYPE
        SYNTAX          CItpXuaInstTableEntry
        MAX-ACCESS      not-accessible
        STATUS          current
        DESCRIPTION
                "A list of XUA instance attributes."
        INDEX   { 
                cItpXuaInstPort      -- local port
        }
        ::= { cItpXuaInstTable  1 }

CItpXuaInstTableEntry  ::= SEQUENCE {
        cItpXuaInstPort                     InetPortNumber,
        cItpXuaInstProtocol                 CItpXuaProtocol,
	cItpXuaInstShut                     TruthValue,
        cItpXuaInstActiveASPs               Gauge32,
        cItpXuaInstRowStatus                RowStatus
}

cItpXuaInstPort         OBJECT-TYPE
        SYNTAX          InetPortNumber
        MAX-ACCESS      not-accessible
        STATUS          current
        DESCRIPTION
                "The local SCTP port for the XUA instance. The value
                 zero is not allowed."
        ::= { cItpXuaInstTableEntry 1 }

cItpXuaInstProtocol     OBJECT-TYPE
        SYNTAX          CItpXuaProtocol
        MAX-ACCESS      read-create
        STATUS          current
        DESCRIPTION
                "The protocol of the XUA instance."
        ::= { cItpXuaInstTableEntry 2 }

cItpXuaInstShut         OBJECT-TYPE
        SYNTAX          TruthValue
        MAX-ACCESS      read-create
        STATUS          current
        DESCRIPTION
                "The XUA Instance Shut truth value.
                'true'  Indicates that the XUA Instance has
                        been shutdown by an administrative action.
                'false' Indicates that the XUA Instance is
                        not shutdown."
        DEFVAL { false }
        ::= { cItpXuaInstTableEntry 3 }

cItpXuaInstActiveASPs   OBJECT-TYPE
        SYNTAX          Gauge32 (0..65535)
        MAX-ACCESS      read-only
        STATUS          current
        DESCRIPTION
                "The number of ASPs connected to this instance."
        ::= { cItpXuaInstTableEntry 4 }

cItpXuaInstRowStatus    OBJECT-TYPE
        SYNTAX          RowStatus
        MAX-ACCESS      read-create
        STATUS          current
        DESCRIPTION
                "The object is used by a management station to 
                 create or delete the row entry in cItpXuaInstTable  
                 following the RowStatus textual convention."
        ::= { cItpXuaInstTableEntry 5 }
        
--  *************************************************************
--  *                                                           *
--  * XUA Instance Local IP sub-table                           *
--  *                                                           *
--  *************************************************************

cItpXuaInstLocalIpTable OBJECT-TYPE
        SYNTAX          SEQUENCE OF CItpXuaInstLocalIpTableEntry 
        MAX-ACCESS      not-accessible
        STATUS          current
        DESCRIPTION
                "A table of Local IP addresses for the XUA
                 instances.

                 For a given instance, there can be multiple local
                 IP addresses which are used for the multi-homing
                 feature of the SCTP associations. This table lists
                 out the configured local IP addresses.

                 Entries are added to this table via 
                 cItpXuaInstLocalIpRowStatus in accordance with 
                 the RowStatus convention."
        ::= { cItpXuaInstLocalIp 1 }

cItpXuaInstLocalIpTableEntry  OBJECT-TYPE
        SYNTAX                CItpXuaInstLocalIpTableEntry
        MAX-ACCESS            not-accessible
        STATUS                current
        DESCRIPTION
                "A list of attributes of the Local IP addresses for
                 the XUA instances."
        INDEX   { 
                cItpXuaInstPort,          -- Local Port, shared index
                cItpXuaInstAddrNum        -- Address Number
        }
        ::= { cItpXuaInstLocalIpTable  1 }

CItpXuaInstLocalIpTableEntry  ::= SEQUENCE {
        cItpXuaInstAddrNum             Unsigned32,
        cItpXuaInstLocalIpType         InetAddressType,
        cItpXuaInstLocalIpAddr         InetAddress,
        cItpXuaInstLocalIpRowStatus    RowStatus
}

cItpXuaInstAddrNum       OBJECT-TYPE
        SYNTAX           Unsigned32 (1..65535)
        MAX-ACCESS       not-accessible
        STATUS           current
        DESCRIPTION
                "This object specifies the index for the XUA
                 instance's IP address. The SCTP port number
                 cItpXuaInstPort specifies the XUA instance."
        ::= { cItpXuaInstLocalIpTableEntry 1 }

cItpXuaInstLocalIpType  OBJECT-TYPE
        SYNTAX          InetAddressType
        MAX-ACCESS      read-create
        STATUS          current
        DESCRIPTION
                "This object contains the type of the local
                 IP address used to create the association
                 for ASPs connecting to the XUA instance
                 specified by the cItpXuaInstPort."
        ::= { cItpXuaInstLocalIpTableEntry 2 }

cItpXuaInstLocalIpAddr  OBJECT-TYPE
        SYNTAX          InetAddress
        MAX-ACCESS      read-create
        STATUS          current
        DESCRIPTION
                "This object contains the local IP address
                 used to create the association for ASPs
                 connecting to the XUA instance specified
                 by the cItpXuaInstPort."
        ::= { cItpXuaInstLocalIpTableEntry 3 }
        
cItpXuaInstLocalIpRowStatus  OBJECT-TYPE
        SYNTAX               RowStatus
        MAX-ACCESS           read-create
        STATUS               current
        DESCRIPTION
                "The object is used by a management station to 
                 create or delete the row entry in
                 cItpXuaInstLocalIpTable following the RowStatus
                 textual convention."
        ::= { cItpXuaInstLocalIpTableEntry 4 }

--  *************************************************************
--  *                                                           *
--  * Signaling Gateway Mate (SGM) Table                        *
--  *                                                           *
--  *************************************************************

cItpXuaSgmTable         OBJECT-TYPE
        SYNTAX          SEQUENCE OF CItpXuaSgmTableEntry 
        MAX-ACCESS      not-accessible
        STATUS          current
        DESCRIPTION
                "A table of SG Mate attributes.
                
                 Entries are added to this table via 
                 cItpXuaSgmRowStatus in accordance with 
                 the RowStatus convention."
        ::= { cItpXuaSgm  1 }

cItpXuaSgmTableEntry    OBJECT-TYPE
        SYNTAX          CItpXuaSgmTableEntry
        MAX-ACCESS      not-accessible
        STATUS          current
        DESCRIPTION
                "A list of SG Mate attributes."
        INDEX   {
                cItpXuaSgmName     -- SGM Name
        }
        ::= { cItpXuaSgmTable  1 }

CItpXuaSgmTableEntry  ::= SEQUENCE {
        cItpXuaSgmName                      CItpTcXuaName,
        cItpXuaSgmAssocId                   Unsigned32,
        cItpXuaSgmLocalPort                 InetPortNumber,
        cItpXuaSgmRemotePort                InetPortNumber,
        cItpXuaSgmShut                      TruthValue,
        cItpXuaSgmActiveTS                  TimeTicks,
        cItpXuaSgmQosClass                  CItpTcQos,
        cItpXuaSgmPassive                   TruthValue,
        cItpXuaSgmState                     CItpXuaAspState,
        cItpXuaSgmRowStatus                 RowStatus
}

cItpXuaSgmName          OBJECT-TYPE
        SYNTAX          CItpTcXuaName
        MAX-ACCESS      not-accessible
        STATUS          current
        DESCRIPTION
                "The name of the SG Mate."
        ::= { cItpXuaSgmTableEntry 1 }

cItpXuaSgmAssocId       OBJECT-TYPE
        SYNTAX          Unsigned32
        MAX-ACCESS      read-only
        STATUS          current
        DESCRIPTION
                "This is the association identifier defined in
                 the Stream Control Transmission Protocol(SCTP)
                 MIB. A value greater than zero indicates a valid
                 association and zero indicates no association."
        ::= { cItpXuaSgmTableEntry 2 }

cItpXuaSgmLocalPort     OBJECT-TYPE
        SYNTAX          InetPortNumber
        MAX-ACCESS      read-create
        STATUS          current
        DESCRIPTION
          "This object contains the local SCTP port number
           used to create the association supporting this link.
           This local port determines the XUA instance that
           this SG Mate is connected with. The value zero is not
           allowed."
        ::= { cItpXuaSgmTableEntry 3 }

cItpXuaSgmRemotePort    OBJECT-TYPE
        SYNTAX          InetPortNumber
        MAX-ACCESS      read-create
        STATUS          current
        DESCRIPTION
                "This object contains the remote SCTP port number
                 used to create the association supporting this link.
                 The value zero is not allowed."
        ::= { cItpXuaSgmTableEntry 4 }

cItpXuaSgmShut          OBJECT-TYPE
        SYNTAX          TruthValue
        MAX-ACCESS      read-create
        STATUS          current
        DESCRIPTION
                "The SG Mate shut truth value.
                'true'  Indicates that the SG Mate has been
                        shutdown by an administrative action.
                'false' Indicates that the SG Mate is not
                        shutdown."
        DEFVAL { false }
        ::= { cItpXuaSgmTableEntry 6 }

cItpXuaSgmActiveTS      OBJECT-TYPE
        SYNTAX          TimeTicks
        MAX-ACCESS      read-only
        STATUS          current
        DESCRIPTION
                "The value of system timestamp at the time when this
                 SG Mate became active. A value of zero (0) indicates
                 that the SG Mate is not active."
        ::= { cItpXuaSgmTableEntry 7 }

cItpXuaSgmQosClass      OBJECT-TYPE
        SYNTAX          CItpTcQos
        MAX-ACCESS      read-create
        STATUS          current
        DESCRIPTION
                "This object specifies the QOS class for the SG
                 Mate. The value of 255 is not applicable. A value
                 of zero (0) indicates that QOS class is not
                 defined."
        DEFVAL { 0 }
        ::= { cItpXuaSgmTableEntry 8 }

cItpXuaSgmPassive       OBJECT-TYPE
        SYNTAX          TruthValue
        MAX-ACCESS      read-create
        STATUS          current
        DESCRIPTION
                "The SG Mate Passive truth value.
                'true'  Indicates that the SG Mate is passive, i.e.
                        it waits for the SG Mate to initiate the
                        SCTP association.
                'false' Indicates that the SG Mate is not passive,
                        i.e., it initiates the SCTP association with
                        its SG Mate."
        DEFVAL { true }
        ::= { cItpXuaSgmTableEntry 10 }

cItpXuaSgmState         OBJECT-TYPE
        SYNTAX          CItpXuaAspState
        MAX-ACCESS      read-only
        STATUS          current
        DESCRIPTION
                "The state of the SG Mate. Only active and inactive
                 states are applicable."
        ::= { cItpXuaSgmTableEntry 11 }

cItpXuaSgmRowStatus     OBJECT-TYPE
        SYNTAX          RowStatus
        MAX-ACCESS      read-create
        STATUS          current
        DESCRIPTION
                "The object is used by a management station to 
                 create or delete the row entry in cItpXuaSgmTable
                 following the RowStatus textual convention."
        ::= { cItpXuaSgmTableEntry 12 }
         
--  *************************************************************
--  *                                                           *
--  * Application Server Process (ASP) Table                    *
--  *                                                           *
--  *************************************************************

cItpXuaAspTable         OBJECT-TYPE
        SYNTAX          SEQUENCE OF CItpXuaAspTableEntry 
        MAX-ACCESS      not-accessible
        STATUS          current
        DESCRIPTION
                "A table of Application Server Processes (ASP).
                
                 Entries are added to this table via 
                 cItpXuaAspRowStatus in accordance with 
                 the RowStatus convention."
        ::= { cItpXuaAsp  1 }

cItpXuaAspTableEntry    OBJECT-TYPE
        SYNTAX          CItpXuaAspTableEntry
        MAX-ACCESS      not-accessible
        STATUS          current
        DESCRIPTION
                "A list of Application Server Processes."
        INDEX   {
                cItpXuaAspName     -- ASP Name
        }
        ::= { cItpXuaAspTable  1 }

CItpXuaAspTableEntry  ::= SEQUENCE {
	cItpXuaAspName                      CItpTcXuaName,
        cItpXuaAspAssocId                   Unsigned32,
        cItpXuaAspLocalPort                 InetPortNumber,
        cItpXuaAspRemotePort                InetPortNumber,
        cItpXuaAspProtocol                  CItpXuaProtocol,
        cItpXuaAspShut                      TruthValue,
        cItpXuaAspBlocked                   TruthValue,
	cItpXuaAspQosClass                  CItpTcQos,
        cItpXuaAspIdentifier                Unsigned32,
        cItpXuaAspRowStatus                 RowStatus
}

cItpXuaAspName          OBJECT-TYPE
        SYNTAX          CItpTcXuaName
        MAX-ACCESS      not-accessible
        STATUS          current
        DESCRIPTION
                "The name of the Applicaton Server Process."
        ::= { cItpXuaAspTableEntry 1 }

cItpXuaAspAssocId       OBJECT-TYPE
        SYNTAX          Unsigned32  (0..65535)
        MAX-ACCESS      read-only
        STATUS          current
        DESCRIPTION
                "This is the association identifier defined in
                 the Stream Control Transmission Protocol(SCTP)
                 MIB. A value greater than zero indicates a valid
                 association and zero indicates no association."
        ::= { cItpXuaAspTableEntry 2 }

cItpXuaAspLocalPort     OBJECT-TYPE
        SYNTAX          InetPortNumber
        MAX-ACCESS      read-create
        STATUS          current
        DESCRIPTION
                "This object contains the local SCTP port number
                 used to create the association supporting this link.
                 This local port determines the XUA instance that
                 this ASP is connected with. The value zero is not
                 allowed."
        ::= { cItpXuaAspTableEntry 3 }

cItpXuaAspRemotePort    OBJECT-TYPE
        SYNTAX          InetPortNumber
        MAX-ACCESS      read-create
        STATUS          current
        DESCRIPTION
                "This object contains the configured remote SCTP port
                 number used to create the association supporting this
                 link. The value zero means any non-zero remote port is
                 acceptable. The actual remote port can be determined
                 from SCTP association in cItpXuaAspAssocId."
        ::= { cItpXuaAspTableEntry 4 }

cItpXuaAspProtocol      OBJECT-TYPE
        SYNTAX          CItpXuaProtocol       
        MAX-ACCESS      read-create
        STATUS          current
        DESCRIPTION
                "The protocol used by this ASP. Only M3UA or SUA are
                 allowed."
        ::= { cItpXuaAspTableEntry 5 }

cItpXuaAspShut          OBJECT-TYPE
        SYNTAX          TruthValue
        MAX-ACCESS      read-create
        STATUS          current
        DESCRIPTION
                "The ASP Shut truth value.
                'true'  Indicates that the ASP has been shutdown 
                        by an administrative action.
                'false' Indicates that the ASP is not shutdown."
        DEFVAL { false }
        ::= { cItpXuaAspTableEntry 6 }

cItpXuaAspBlocked       OBJECT-TYPE
        SYNTAX          TruthValue
        MAX-ACCESS      read-create
        STATUS          current
        DESCRIPTION
                "When an ASP is blocked, it cannot receive normal
                 data traffic, but it can send or receive control
                 messages.

                 The ASP Blocked  truth value.
                'true'  Indicates that the ASP has been blocked 
                        by an administrative action.
                'false' Indicates that the ASP is not blocked."
        DEFVAL { false }
        ::= { cItpXuaAspTableEntry 7 }

cItpXuaAspQosClass      OBJECT-TYPE
        SYNTAX          CItpTcQos
        MAX-ACCESS      read-create
        STATUS          current
        DESCRIPTION
                "This object specifies the QOS class for the ASP.
                 The value of 255 is not applicable. A value of
                 zero (0) indicates that QOS class is not defined.
                 When QOS class is defined, it overrides the QOS
                 class specified by cItpXuaAsQosClass."
        DEFVAL { 0 }
        ::= { cItpXuaAspTableEntry 9 }

cItpXuaAspIdentifier    OBJECT-TYPE
        SYNTAX          Unsigned32 (0..4294967295)
        MAX-ACCESS      read-only
        STATUS          current
        DESCRIPTION
                "A unique value received by the Signaling Gateway
                 from the ASP as part of ASP UP message."
        REFERENCE
                "3.5.1 ASP Up in M3UA/SUA draft."
        ::= { cItpXuaAspTableEntry 10 }

cItpXuaAspRowStatus     OBJECT-TYPE
        SYNTAX          RowStatus
        MAX-ACCESS      read-create
        STATUS          current
        DESCRIPTION
                "The object is used by a management station to 
                 create or delete the row entry in cItpXuaAspTable
                 following the RowStatus textual convention."
        ::= { cItpXuaAspTableEntry 11 }
         
--  *************************************************************
--  *                                                           *
--  * Application Server Process (ASP) Remote IP sub-table      *
--  *                                                           *
--  *************************************************************

cItpXuaAspRemoteIpTable OBJECT-TYPE
        SYNTAX          SEQUENCE OF CItpXuaAspRemoteIpTableEntry 
        MAX-ACCESS      not-accessible
        STATUS          current
        DESCRIPTION
                "A table of Remote IP addresses for the Application
                 Server Processes (ASP).

                 For a given ASP, there can be multiple remote
                 IP addresses which are used for the multi-homing
                 feature of the SCTP associations.
                 
                 Entries are added to this table via 
                 cItpXuaAspRemoteIpRowStatus in accordance with 
                 the RowStatus convention."
        ::= { cItpXuaAspRemoteIp  1 }

cItpXuaAspRemoteIpTableEntry OBJECT-TYPE
        SYNTAX               CItpXuaAspRemoteIpTableEntry
        MAX-ACCESS           not-accessible
        STATUS               current
        DESCRIPTION
                "A list of Remote IP addresses for the Application
                 Server Processes."
        INDEX   {
                cItpXuaAspName,         -- ASP Name, shared index
                cItpXuaAspAddrNum       -- IP Address number
        }
        ::= { cItpXuaAspRemoteIpTable  1 }

CItpXuaAspRemoteIpTableEntry  ::= SEQUENCE {
        cItpXuaAspAddrNum                   Unsigned32,
        cItpXuaAspRemoteIpType              InetAddressType,
        cItpXuaAspRemoteIpAddr              InetAddress,
        cItpXuaAspRemoteIpRowStatus         RowStatus
        }

cItpXuaAspAddrNum        OBJECT-TYPE
        SYNTAX           Unsigned32 (1..65535)
        MAX-ACCESS       not-accessible
        STATUS           current
        DESCRIPTION
                "This object specifies the index for the ASP's
                 remote IP address. The ASP Name in cItpXuaAspName
                 specifies the ASP."
        ::= { cItpXuaAspRemoteIpTableEntry 1 }

cItpXuaAspRemoteIpType  OBJECT-TYPE
        SYNTAX          InetAddressType
        MAX-ACCESS      read-create
        STATUS          current
        DESCRIPTION
                "This object contains the type of the remote IP address
                 used to create the association supporting this ASP."
        ::= { cItpXuaAspRemoteIpTableEntry 2 }

cItpXuaAspRemoteIpAddr  OBJECT-TYPE
        SYNTAX          InetAddress
        MAX-ACCESS      read-create
        STATUS          current
        DESCRIPTION
                "This object contains the remote IP address used to
                 create the association supporting this ASP."
        ::= { cItpXuaAspRemoteIpTableEntry 3 }

cItpXuaAspRemoteIpRowStatus OBJECT-TYPE
        SYNTAX              RowStatus
        MAX-ACCESS          read-create
        STATUS              current
        DESCRIPTION
                "The object is used by a management station to 
                 create or delete the row entry in
                 cItpXuaAspRemoteIpTable following the RowStatus
                 textual convention."
        ::= { cItpXuaAspRemoteIpTableEntry 4 }
         
--  *************************************************************
--  *                                                           *
--  * Application Server Process (ASP) Statistics Table         *
--  *                                                           *
--  *************************************************************

cItpXuaAspStatsTable    OBJECT-TYPE
        SYNTAX          SEQUENCE OF CItpXuaAspStatsTableEntry 
        MAX-ACCESS      not-accessible
        STATUS          current
        DESCRIPTION
                "A table of Application Server Processes (ASP)
                 statistics."
        ::= { cItpXuaAspStats 1 }

cItpXuaAspStatsTableEntry OBJECT-TYPE
        SYNTAX          CItpXuaAspStatsTableEntry
        MAX-ACCESS      not-accessible
        STATUS          current
        DESCRIPTION
                "A list of ASP statistics."
        INDEX   {
                cItpXuaAspName     -- ASP Name
        }
        ::= { cItpXuaAspStatsTable  1 }

CItpXuaAspStatsTableEntry  ::= SEQUENCE {
        cItpXuaAspPktsFromAsp               Counter32,
        cItpXuaAspPktsToAsp                 Counter32,
        cItpXuaAspPktsFromMtp3              Counter32,
        cItpXuaAspPktsToMtp3                Counter32,
        cItpXuaAspASPUPsRcvd                Counter32,
        cItpXuaAspASPUPACKsSent             Counter32,
        cItpXuaAspASPDNsRcvd                Counter32,
        cItpXuaAspASPDNACKsSent             Counter32,
        cItpXuaAspASPACsRcvd                Counter32,
        cItpXuaAspASPACACKsSent             Counter32,
        cItpXuaAspASPIAsRcvd                Counter32,
        cItpXuaAspASPIAACKsSent             Counter32,
        cItpXuaAspErrorsRcvd                Counter32,
        cItpXuaAspErrorsSent                Counter32,
        cItpXuaAspNotifysSent               Counter32,
        cItpXuaAspDUNAsRcvd                 Counter32,
        cItpXuaAspDUNAsSent                 Counter32,
        cItpXuaAspDAVAsRcvd                 Counter32,
        cItpXuaAspDAVAsSent                 Counter32,
        cItpXuaAspDUPUsRcvd                 Counter32,
        cItpXuaAspDUPUsSent                 Counter32,
        cItpXuaAspDAUDsRcvd                 Counter32,
        cItpXuaAspDAUDsSent                 Counter32,
        cItpXuaAspSCON0sRcvd                Counter32,
        cItpXuaAspSCON1sRcvd                Counter32,
        cItpXuaAspSCON2sRcvd                Counter32,
        cItpXuaAspSCON3sRcvd                Counter32,
        cItpXuaAspSCON0sSent                Counter32,
        cItpXuaAspSCON1sSent                Counter32,
        cItpXuaAspSCON2sSent                Counter32,
        cItpXuaAspSCON3sSent                Counter32
}

cItpXuaAspPktsFromAsp   OBJECT-TYPE
        SYNTAX          Counter32
        UNITS           "packets"
        MAX-ACCESS      read-only
        STATUS          current
        DESCRIPTION
                "The number of data packets received from this ASP."
        ::= { cItpXuaAspStatsTableEntry 1 }

cItpXuaAspPktsToAsp     OBJECT-TYPE
        SYNTAX          Counter32
        UNITS           "packets"
        MAX-ACCESS      read-only
        STATUS          current
        DESCRIPTION
                "The number of data packets sent to this ASP."
        ::= { cItpXuaAspStatsTableEntry 2 }

cItpXuaAspPktsFromMtp3  OBJECT-TYPE
        SYNTAX          Counter32
        UNITS           "packets"
        MAX-ACCESS      read-only
        STATUS          current
        DESCRIPTION
                "The number of data packets received from MTP3."
        ::= { cItpXuaAspStatsTableEntry 3 }

cItpXuaAspPktsToMtp3    OBJECT-TYPE
        SYNTAX          Counter32
        UNITS           "packets"
        MAX-ACCESS      read-only
        STATUS          current
        DESCRIPTION
                "The number of data packets sent to MTP3."
        ::= { cItpXuaAspStatsTableEntry 4 }

cItpXuaAspASPUPsRcvd    OBJECT-TYPE
        SYNTAX          Counter32
        UNITS           "messages"
        MAX-ACCESS      read-only
        STATUS          current
        DESCRIPTION
                "The number of ASP Up messages received."
        REFERENCE
                "Section 3.5.1 ASP Up (UP) of M3UA/SUA draft."
        ::= { cItpXuaAspStatsTableEntry 5 }

cItpXuaAspASPUPACKsSent OBJECT-TYPE
        SYNTAX          Counter32
        UNITS           "messages"
        MAX-ACCESS      read-only
        STATUS          current
        DESCRIPTION
                "The number of ASP Up ACK messages sent."
        REFERENCE
                "Section 3.5.2 ASP Up Acknowledgement (ASP Up Ack)
                 of M3UA/SUA draft."
        ::= { cItpXuaAspStatsTableEntry 6 }

cItpXuaAspASPDNsRcvd    OBJECT-TYPE
        SYNTAX          Counter32
        UNITS           "messages"
        MAX-ACCESS      read-only
        STATUS          current
        DESCRIPTION
                "The number of ASP Down messages received."
        REFERENCE
                "Section 3.5.3 ASP Down of M3UA/SUA draft."
        ::= { cItpXuaAspStatsTableEntry 7 }

cItpXuaAspASPDNACKsSent OBJECT-TYPE
        SYNTAX          Counter32
        UNITS           "messages"
        MAX-ACCESS      read-only
        STATUS          current
        DESCRIPTION
                "The number of ASP Down ACK messages sent."
        REFERENCE
                "Section 3.5.4 ASP Down Acknowledgement
                 (ASP Down Ack) of M3UA/SUA draft."
        ::= { cItpXuaAspStatsTableEntry 8 }

cItpXuaAspASPACsRcvd    OBJECT-TYPE
        SYNTAX          Counter32
        UNITS           "messages"
        MAX-ACCESS      read-only
        STATUS          current
        DESCRIPTION
                "The number of ASP Active messages received."
        REFERENCE
                "Sections 3.7.1 ASP Active of M3UA draft and
                 3.6.1 of SUA draft."
        ::= { cItpXuaAspStatsTableEntry 9 }

cItpXuaAspASPACACKsSent OBJECT-TYPE
        SYNTAX          Counter32
        UNITS           "messages"
        MAX-ACCESS      read-only
        STATUS          current
        DESCRIPTION
                "The number of ASP Active ACK messages sent."
        REFERENCE
                "Sections 3.7.2 ASP Active Acknowledgement
                 (ASP Active Ack) of M3UA draft and 3.6.2 ASP
                 Active (ACTIVE) of SUA draft."
        ::= { cItpXuaAspStatsTableEntry 10 }

cItpXuaAspASPIAsRcvd    OBJECT-TYPE
        SYNTAX          Counter32
        UNITS           "messages"
        MAX-ACCESS      read-only
        STATUS          current
        DESCRIPTION
                "The number of ASP Inactive messages received."
        REFERENCE
                "Sections 3.7.3 ASP Inactive of M3UA draft and
                 3.6.3 of SUA draft."
        ::= { cItpXuaAspStatsTableEntry 11 }

cItpXuaAspASPIAACKsSent OBJECT-TYPE
        SYNTAX          Counter32
        UNITS           "messages"
        MAX-ACCESS      read-only
        STATUS          current
        DESCRIPTION
                "The number of ASP Inactive ACK messages sent."
        REFERENCE
                "Sections 3.7.4 ASP Inactive Acknowledgement
                 (ASP Inactive Ack) of M3UA draft and 3.6.4 ASP
                 Inactive (INACTIVE) of SUA draft."
        ::= { cItpXuaAspStatsTableEntry 12 }

cItpXuaAspErrorsRcvd    OBJECT-TYPE
        SYNTAX          Counter32
        UNITS           "messages"
        MAX-ACCESS      read-only
        STATUS          current
        DESCRIPTION
                "The number of ASP Error messages received."
        REFERENCE
                "Sections 3.8.1  Error of M3UA draft and
                 3.7.1 Error (ERR) of SUA draft."
        ::= { cItpXuaAspStatsTableEntry 13 }

cItpXuaAspErrorsSent    OBJECT-TYPE
        SYNTAX          Counter32
        UNITS           "messages"
        MAX-ACCESS      read-only
        STATUS          current
        DESCRIPTION
                "The number of ASP Error messages sent."
        REFERENCE
                "Sections 3.8.1  Error of M3UA draft and
                 3.7.1 Error (ERR) of SUA draft."
        ::= { cItpXuaAspStatsTableEntry 14 }

cItpXuaAspNotifysSent   OBJECT-TYPE
        SYNTAX          Counter32
        UNITS           "messages"
        MAX-ACCESS      read-only
        STATUS          current
        DESCRIPTION
                "The number of ASP Notify messages sent."
        REFERENCE
                "Sections 3.8.2 Notify of M3UA draft and
                 3.7.2 Notify (NTFY) of SUA draft."
        ::= { cItpXuaAspStatsTableEntry 15 }

cItpXuaAspDUNAsRcvd     OBJECT-TYPE
        SYNTAX          Counter32
        UNITS           "messages"
        MAX-ACCESS      read-only
        STATUS          current
        DESCRIPTION
                "The number of Destination Unavailable messages
                 received."
        REFERENCE
                "Section 3.4.1 Destination Unavailable (DUNA) of
                 M3UA/SUA draft."
        ::= { cItpXuaAspStatsTableEntry 16 }

cItpXuaAspDUNAsSent     OBJECT-TYPE
        SYNTAX          Counter32
        UNITS           "messages"
        MAX-ACCESS      read-only
        STATUS          current
        DESCRIPTION
                "The number of Destination Unavailable messages
                 sent."
        REFERENCE
                "Section 3.4.1 Destination Unavailable (DUNA) of
                 M3UA/SUA draft."
        ::= { cItpXuaAspStatsTableEntry 17 }

cItpXuaAspDAVAsRcvd     OBJECT-TYPE
        SYNTAX          Counter32
        UNITS           "messages"
        MAX-ACCESS      read-only
        STATUS          current
        DESCRIPTION
                "The number of Destination Available messages
                 received."
        REFERENCE
                "Section 3.4.2 Destination Available (DAVA) of
                 M3UA/SUA draft."
        ::= { cItpXuaAspStatsTableEntry 18 }

cItpXuaAspDAVAsSent     OBJECT-TYPE
        SYNTAX          Counter32
        UNITS           "messages"
        MAX-ACCESS      read-only
        STATUS          current
        DESCRIPTION
                "The number of Destination Available messages
                 sent."
        REFERENCE
                "Section 3.4.2 Destination Available (DAVA) of
                 M3UA/SUA draft."
        ::= { cItpXuaAspStatsTableEntry 19 }

cItpXuaAspDUPUsRcvd     OBJECT-TYPE
        SYNTAX          Counter32
        UNITS           "messages"
        MAX-ACCESS      read-only
        STATUS          current
        DESCRIPTION
                "The number of Destination User Part Unavailable
                 messages received."
        REFERENCE
                "Section 3.4.5 Destination User Part Unavailable
                 (DUPU) of M3UA/SUA draft."
        ::= { cItpXuaAspStatsTableEntry 20 }

cItpXuaAspDUPUsSent     OBJECT-TYPE
        SYNTAX          Counter32
        UNITS           "messages"
        MAX-ACCESS      read-only
        STATUS          current
        DESCRIPTION
                "The number of Destination User Part Unavailable
                 messages sent."
        REFERENCE
                "Section 3.4.5 Destination User Part Unavailable
                 (DUPU) of M3UA/SUA draft."
        ::= { cItpXuaAspStatsTableEntry 21 }

cItpXuaAspDAUDsRcvd     OBJECT-TYPE
        SYNTAX          Counter32
        UNITS           "messages"
        MAX-ACCESS      read-only
        STATUS          current
        DESCRIPTION
                "The number of Destination State Audit
                 messages received."
        REFERENCE
                "Section 3.4.3 Destination State Audit (DAUD)
                 of M3UA/SUA draft."
        ::= { cItpXuaAspStatsTableEntry 22 }

cItpXuaAspDAUDsSent     OBJECT-TYPE
        SYNTAX          Counter32
        UNITS           "messages"
        MAX-ACCESS      read-only
        STATUS          current
        DESCRIPTION
                "The number of Destination State Audit
                 messages sent."
        REFERENCE
                "Section 3.4.3 Destination State Audit (DAUD)
                 of M3UA/SUA draft."
        ::= { cItpXuaAspStatsTableEntry 23 }

cItpXuaAspSCON0sRcvd    OBJECT-TYPE
        SYNTAX          Counter32
        UNITS           "messages"
        MAX-ACCESS      read-only
        STATUS          current
        DESCRIPTION
                "The number of Signaling Congestion messages with
                 congestion level 0 (or no congestion) received."
        REFERENCE
                "Section 3.4.4 Signalling Congestion (SCON)
                 of M3UA/SUA draft."
        ::= { cItpXuaAspStatsTableEntry 24 }

cItpXuaAspSCON1sRcvd    OBJECT-TYPE
        SYNTAX          Counter32
        UNITS           "messages"
        MAX-ACCESS      read-only
        STATUS          current
        DESCRIPTION
                "The number of Signaling Congestion messages with
                 congestion level 1 received."
        REFERENCE
                "Section 3.4.4 Signalling Congestion (SCON)
                 of M3UA/SUA draft."
        ::= { cItpXuaAspStatsTableEntry 25 }

cItpXuaAspSCON2sRcvd    OBJECT-TYPE
        SYNTAX          Counter32
        UNITS           "messages"
        MAX-ACCESS      read-only
        STATUS          current
        DESCRIPTION
                "The number of Signaling Congestion messages with
                 congestion level 2 received."
        REFERENCE
                "Section 3.4.4 Signalling Congestion (SCON)
                 of M3UA/SUA draft."
        ::= { cItpXuaAspStatsTableEntry 26 }

cItpXuaAspSCON3sRcvd    OBJECT-TYPE
        SYNTAX          Counter32
        UNITS           "messages"
        MAX-ACCESS      read-only
        STATUS          current
        DESCRIPTION
                "The number of Signaling Congestion messages with
                 congestion level 3 received."
        REFERENCE
                "Section 3.4.4 Signalling Congestion (SCON)
                 of M3UA/SUA draft."
        ::= { cItpXuaAspStatsTableEntry 27 }

cItpXuaAspSCON0sSent    OBJECT-TYPE
        SYNTAX          Counter32
        UNITS           "messages"
        MAX-ACCESS      read-only
        STATUS          current
        DESCRIPTION
                "The number of Signaling Congestion messages with
                 congestion level 0 (or no congestion) sent."
        REFERENCE
                "Section 3.4.4 Signalling Congestion (SCON)
                 of M3UA/SUA draft."
        ::= { cItpXuaAspStatsTableEntry 28 }

cItpXuaAspSCON1sSent    OBJECT-TYPE
        SYNTAX          Counter32
        UNITS           "messages"
        MAX-ACCESS      read-only
        STATUS          current
        DESCRIPTION
                "The number of Signaling Congestion messages with
                 congestion level 1 sent."
        REFERENCE
                "Section 3.4.4 Signalling Congestion (SCON)
                 of M3UA/SUA draft."
        ::= { cItpXuaAspStatsTableEntry 29 }

cItpXuaAspSCON2sSent    OBJECT-TYPE
        SYNTAX          Counter32
        UNITS           "messages"
        MAX-ACCESS      read-only
        STATUS          current
        DESCRIPTION
                "The number of Signaling Congestion messages with
                 congestion level 2 sent."
        REFERENCE
                "Section 3.4.4 Signalling Congestion (SCON)
                 of M3UA/SUA draft."
        ::= { cItpXuaAspStatsTableEntry 30 }

cItpXuaAspSCON3sSent    OBJECT-TYPE
        SYNTAX          Counter32
        UNITS           "messages"
        MAX-ACCESS      read-only
        STATUS          current
        DESCRIPTION
                "The number of Signaling Congestion messages with
                 congestion level 3 sent."
        REFERENCE
                "Section 3.4.4 Signalling Congestion (SCON)
                 of M3UA/SUA draft."
        ::= { cItpXuaAspStatsTableEntry 31 }

--  *************************************************************
--  *                                                           *
--  * Application Server (AS) Table                             *
--  *                                                           *
--  *************************************************************

cItpXuaAsTable          OBJECT-TYPE
        SYNTAX          SEQUENCE OF CItpXuaAsTableEntry 
        MAX-ACCESS      not-accessible
        STATUS          current
        DESCRIPTION
                "A table of M3UA/SUA Application Server (AS) entries.
                
                 Entries are added to this table via 
                 cItpXuaAsRowStatus in accordance with 
                 the RowStatus convention."
        ::= { cItpXuaAs 1 }

cItpXuaAsTableEntry     OBJECT-TYPE
        SYNTAX          CItpXuaAsTableEntry 
        MAX-ACCESS      not-accessible
        STATUS          current
        DESCRIPTION
                "A list of M3UA/SUA AS attributes."
        INDEX   {
                cItpXuaAsName        -- AS Name
        }
        ::= { cItpXuaAsTable  1 }

CItpXuaAsTableEntry  ::= SEQUENCE {
        cItpXuaAsName                      CItpTcXuaName,
        cItpXuaAsProtocol                  CItpXuaProtocol,
        cItpXuaAsShut                      TruthValue,
        cItpXuaAsState                     CItpXuaAsState,
        cItpXuaAsStateOnSgMate             CItpXuaAsState,
        cItpXuaAsActiveTS                  TimeTicks,
        cItpXuaAsQosClass                  CItpTcQos,
        cItpXuaAsTrafMode                  CItpXuaTrafMode,
        cItpXuaAsRerouting                 TruthValue,
        cItpXuaAsRoutingContext            Unsigned32,
        cItpXuaAsRkParameters              BITS,
        cItpXuaAsRkDpc                     CItpTcPointCode,
        cItpXuaAsRkOpc                     CItpTcPointCode,
        cItpXuaAsRkOpcMask                 Unsigned32,
        cItpXuaAsRkSi                      CItpTcServiceIndicator,
        cItpXuaAsRkSsn                     CItpTcSubSystemNumber,
        cItpXuaAsRkGtt                     TruthValue,
        cItpXuaAsRkCicMin                  Unsigned32,
        cItpXuaAsRkCicMax                  Unsigned32,
        cItpXuaAsPktsFromMtp3              Counter32,
        cItpXuaAsPktsToASPsOfAs            Counter32,
        cItpXuaAsRowStatus                 RowStatus
}

cItpXuaAsName           OBJECT-TYPE
        SYNTAX          CItpTcXuaName    
        MAX-ACCESS      not-accessible
        STATUS          current
        DESCRIPTION
                "The Application Server name. This name has only 
                 local significance."
        ::= { cItpXuaAsTableEntry  1 }

cItpXuaAsProtocol       OBJECT-TYPE
        SYNTAX          CItpXuaProtocol       
        MAX-ACCESS      read-create
        STATUS          current
        DESCRIPTION
                "The protocol used by this AS."
        ::= { cItpXuaAsTableEntry 2 }

cItpXuaAsShut           OBJECT-TYPE
        SYNTAX          TruthValue
        MAX-ACCESS      read-create
        STATUS          current
        DESCRIPTION
                "The AS Shut truth value.
                'true'  Indicates that the AS has been shutdown 
                        by an administrative action.
                'false' Indicates that the AS is not shutdown."
        DEFVAL { false }
        ::= { cItpXuaAsTableEntry 3 }

cItpXuaAsState          OBJECT-TYPE
        SYNTAX          CItpXuaAsState
        MAX-ACCESS      read-only
        STATUS          current
        DESCRIPTION
                "The Application Server (AS) state."
        REFERENCE
                "4.3.2 AS States in M3UA/SUA draft."
        ::= { cItpXuaAsTableEntry 4 }

cItpXuaAsStateOnSgMate  OBJECT-TYPE
        SYNTAX          CItpXuaAsState
        MAX-ACCESS      read-only
        STATUS          current
        DESCRIPTION
                "The Application Server (AS) state on the mated
                 Signaling Gateway.  This object provides the status
                 of an Application Service as provided by the 
                 Signaling Gateway Mated  Protocol.  This object 
                 can be used by the NMS to assist in problem 
                 determination.  
                 
                 Each Signaling Gateway Mated pair should have 
                 same definitions.  This allows the NMS
                 examine the status Application Service from 
                 perspective of each Signalling Gateway.  If the
                 definitions are different on the mated pairs the
                 NMS will be unable to determine the relationships
                 between the ASes and mated pairs."
        REFERENCE
                "4.3.2 AS States in M3UA/SUA draft."
        ::= { cItpXuaAsTableEntry 5 }

cItpXuaAsActiveTS       OBJECT-TYPE
        SYNTAX          TimeTicks
        MAX-ACCESS      read-only
        STATUS          current
        DESCRIPTION
                "The value of system uptime at the time 
                 when this AS became active. A value of zero (0) 
                 indicates that the AS is not active."
        ::= { cItpXuaAsTableEntry 6 }

cItpXuaAsQosClass       OBJECT-TYPE
        SYNTAX          CItpTcQos
        MAX-ACCESS      read-create
        STATUS          current
        DESCRIPTION
                "The AS specifies the QOS class for all its ASPs.
                 The value of 255 is not applicable. A value of
                 zero (0) indicates that QOS class is not defined.
                 This value can be overridden by cItpXuaAspQosClass."
        DEFVAL { 0 }
        ::= { cItpXuaAsTableEntry 7 }

cItpXuaAsTrafMode       OBJECT-TYPE
        SYNTAX          CItpXuaTrafMode      
        MAX-ACCESS      read-create
        STATUS          current
        DESCRIPTION
                "The traffic mode for the data packets
                 received for this AS."
        ::= { cItpXuaAsTableEntry 8 }

cItpXuaAsRerouting      OBJECT-TYPE
        SYNTAX          TruthValue
        MAX-ACCESS      read-only
        STATUS          current
        DESCRIPTION
                "The AS Rerouting truth value.
                'true'  Indicates that this SG is rerouting the
                        traffic to the mated SG.
                'false' Indicates that this SG is not rerouting
                        the traffic to the mated SG."
        ::= { cItpXuaAsTableEntry 9 }

cItpXuaAsRoutingContext OBJECT-TYPE
        SYNTAX          Unsigned32 (0..4294967295)
        MAX-ACCESS      read-only
        STATUS          current
        DESCRIPTION
                "An ASP may be configured to serve more than one AS. In
                 this case, the Routing Context parameter is exchanged
                 between the SG and the ASP, identifying the relevant
                 AS. The Routing Context uniquely identifies the range
                 of traffic associated with a particular AS, which the
                 ASP is configured to receive. There is a 1:1
                 relationship between a Routing Context value and a
                 Routing Key within an AS."
        REFERENCE
                "1.4.2 Routing Contexts and Routing Keys in M3UA draft
                 and 3.9.6 Routing Context in SUA draft."
        ::= { cItpXuaAsTableEntry 10 }

cItpXuaAsRkParameters   OBJECT-TYPE
        SYNTAX          BITS { 
                          dpc(0),
                          opc(1),
                          opcMask(2),
                          si(3),
                          ssn(4),
                          gtt(5),
                          cic(6)
                        }
        MAX-ACCESS      read-create
        STATUS          current
        DESCRIPTION
                "The cItpXuaAsRkParameters object indicates
                 which Routing Key parameters are valid for
                 this AS.

                'dpc'     : The cItpXuaAsRkDpc is the relevant column.
                   
                'opc'     : cItpXuaAsRkOpc and cItpXuaAsRkOpcMask are
                            the relevant columns.
                   
                'opcMask' : Indicates that a mask is to be applied when
                            the opc is specified in the routing key. If
                            the mask is not specified then the mask is
                            assumed to be all zeros.

                'si'      : The cItpXuaAsRkSi is the relevant column.
                   
                'ssn'     : Indicates that a SSN is to be checked as
                            part of the routing key.

                'gtt'     : The cItpXuaAsRkGtt is the relevant column.
                            It indicates that routing key for this AS
                            can be the result of Global Title
                            Translation.

                'cic'     : The cItpXuaAsRkCicMin and cItpXuaAsRkCicMax
                            are the relevant columns.

                 The following combination is allowed for all si's:
                   gtt
                   dpc
                   dpc + opc
                   dpc + opc + opcMask

                 When si equals 3 (SCCP), the following is allowed:
                   dpc + si
                   dpc + si + opc
                   dpc + si + ssn
                   dpc + si + ssn + opc

                 When si equals 5 (ISUP), the following is allowed:
                   dpc + si
                   dpc + si + opc
                   dpc + si + cic
                   dpc + si + cic + opc"
        ::= { cItpXuaAsTableEntry 11 }

cItpXuaAsRkDpc          OBJECT-TYPE
        SYNTAX          CItpTcPointCode
        MAX-ACCESS      read-create
        STATUS          current
        DESCRIPTION
                "The Destination Point Code (DPC) in the routing
                 key for the AS. The 'dpc' bit in the
                 cItpXuaAsRkParameters object is used to indicate
                 whether this object's value has any current
                 relevance."
        ::= { cItpXuaAsTableEntry 12 }

cItpXuaAsRkOpc          OBJECT-TYPE
        SYNTAX          CItpTcPointCode
        MAX-ACCESS      read-create
        STATUS          current
        DESCRIPTION
                "The Origin Point Code (OPC) in the routing
                 key for the AS. The 'opc' bit in the
                 cItpXuaAsRkParameters object is used to indicate
                 whether this object's value has any current
                 relevance."
        ::= { cItpXuaAsTableEntry 13 }

cItpXuaAsRkOpcMask      OBJECT-TYPE
        SYNTAX          Unsigned32
        MAX-ACCESS      read-create
        STATUS          current
        DESCRIPTION
                "The Origin Point Code (OPC) mask in the routing
                 key for the AS. The 'opcMask' bit in the
                 cItpXuaAsRkParameters object is used to indicate
                 whether this object's value has any current
                 relevance."
        ::= { cItpXuaAsTableEntry 14 }

cItpXuaAsRkSi           OBJECT-TYPE
        SYNTAX          CItpTcServiceIndicator
        MAX-ACCESS      read-create
        STATUS          current
        DESCRIPTION
                "The Service Indicator in the routing key for
                 the AS. The 'si' bit in the cItpXuaAsRkParameters
                 object is used to indicate whether this object's
                 value has any current relevance."
        ::= { cItpXuaAsTableEntry 15 }

cItpXuaAsRkSsn          OBJECT-TYPE
        SYNTAX          CItpTcSubSystemNumber
        MAX-ACCESS      read-create
        STATUS          current
        DESCRIPTION
                "The SubSystem Number (SSN) in routing key for
                 the AS. The 'ssn' bit in the cItpXuaAsRkParameters
                 object is used to indicate whether this object's
                 value has any current relevance."
        ::= { cItpXuaAsTableEntry 16 }

cItpXuaAsRkGtt          OBJECT-TYPE
        SYNTAX          TruthValue
        MAX-ACCESS      read-create
        STATUS          current
        DESCRIPTION
                "The Routing key Global Title Translation (GTT)
                 truth value.
                'true'  Indicates that the GTT is enabled.
                'false' Indicates that the GTT is not enabled.

                 The 'gtt' bit in the cItpXuaAsRkParameters object
                 is used to indicate whether this object's value
                 has any current relevance."
        ::= { cItpXuaAsTableEntry 17 }

cItpXuaAsRkCicMin       OBJECT-TYPE
        SYNTAX          Unsigned32 (0..65535)
        MAX-ACCESS      read-create
        STATUS          current
        DESCRIPTION
                "The Routing key minimum CIC value. The 'cic'
                 bit in the cItpXuaAsRkParameters object is used
                 to indicate whether this object's value has any
                 current relevance."
        ::= { cItpXuaAsTableEntry 18 }

cItpXuaAsRkCicMax       OBJECT-TYPE
        SYNTAX          Unsigned32 (0..65535)
        MAX-ACCESS      read-create
        STATUS          current
        DESCRIPTION
                "The Routing key maximum CIC value. The 'cic'
                 bit in the cItpXuaAsRkParameters object is used
                 to indicate whether this object's value has any
                 current relevance."
        ::= { cItpXuaAsTableEntry 19 }

cItpXuaAsPktsFromMtp3   OBJECT-TYPE
        SYNTAX          Counter32
        UNITS           "packets"
        MAX-ACCESS      read-only
        STATUS          current
        DESCRIPTION
                "The number of data packets received from MTP3."
        ::= { cItpXuaAsTableEntry 20 }

cItpXuaAsPktsToASPsOfAs OBJECT-TYPE
        SYNTAX          Counter32
        UNITS           "packets"
        MAX-ACCESS      read-only
        STATUS          current
        DESCRIPTION
                "The number of data packets sent to all ASPs that
                 are serving this AS."
        ::= { cItpXuaAsTableEntry 21 }

cItpXuaAsRowStatus      OBJECT-TYPE
        SYNTAX          RowStatus
        MAX-ACCESS      read-create
        STATUS          current
        DESCRIPTION
                "The object is used by a management station to 
                 create or delete the row entry in cItpXuaAsTable 
                 following the RowStatus textual convention."
        ::= { cItpXuaAsTableEntry 22 }
         
--  *************************************************************
--  *                                                           *
--  * M3UA/SUA - ASP-AS Table                                   *
--  *                                                           *
--  *************************************************************

cItpXuaAspAsTable       OBJECT-TYPE
        SYNTAX          SEQUENCE OF CItpXuaAspAsTableEntry 
        MAX-ACCESS      not-accessible
        STATUS          current
        DESCRIPTION
                "A table of M3UA/SUA ASP-AS entries.

                 An ASP can serve one or more ASes. For each AS
                 that it serves, the ASP maintains the state
                 information.
                 
                 Entries are added to this table via 
                 cItpXuaAspAsRowStatus in accordance with 
                 the RowStatus convention."
        ::= { cItpXuaAspAs  1 }

cItpXuaAspAsTableEntry  OBJECT-TYPE
        SYNTAX          CItpXuaAspAsTableEntry 
        MAX-ACCESS      not-accessible
        STATUS          current
        DESCRIPTION
                "A list of M3UA/SUA ASP-AS attributes."
        INDEX   {
                cItpXuaAspName,    -- ASP Name, shared index
                cItpXuaAspAsName   -- AS Name
        }
        ::= { cItpXuaAspAsTable  1 }

CItpXuaAspAsTableEntry  ::= SEQUENCE {
        cItpXuaAspAsName                   CItpTcXuaName,
        cItpXuaAspAsState                  CItpXuaAspState,
        cItpXuaAspAsActiveTS               TimeTicks,
        cItpXuaAspAsRowStatus              RowStatus
}

cItpXuaAspAsName        OBJECT-TYPE
        SYNTAX          CItpTcXuaName    
        MAX-ACCESS      not-accessible
        STATUS          current
        DESCRIPTION
                "The Application Server name."
        ::= { cItpXuaAspAsTableEntry  1 }

cItpXuaAspAsState       OBJECT-TYPE
        SYNTAX          CItpXuaAspState
        MAX-ACCESS      read-only
        STATUS          current
        DESCRIPTION
                "The state of the ASP that serves this AS."
        REFERENCE
                "4.3.1 ASP States in M3UA/SUA draft."
        ::= { cItpXuaAspAsTableEntry 2 }

cItpXuaAspAsActiveTS    OBJECT-TYPE
        SYNTAX          TimeTicks
        MAX-ACCESS      read-only
        STATUS          current
        DESCRIPTION
                "The value of system timestamp at the time when this
                 ASP became active with respect to the specified AS.
                 If the ASP is not active with respect to the 
                 specified AS this object will contain a value of 
                 zero."
        ::= { cItpXuaAspAsTableEntry 3 }

cItpXuaAspAsRowStatus   OBJECT-TYPE
        SYNTAX          RowStatus
        MAX-ACCESS      read-create
        STATUS          current
        DESCRIPTION
                "The object is used by a management station to 
                 create or delete the row entry in cItpXuaAspAsTable
                 following the RowStatus textual convention."
        ::= { cItpXuaAspAsTableEntry 4}
         
--  *************************************************************
--  *                                                           *
--  * Notification Objects                                      *
--  *                                                           *
--  *************************************************************


cItpXuaSgmDisplayName   OBJECT-TYPE
        SYNTAX          CItpTcXuaName
        MAX-ACCESS      accessible-for-notify
        STATUS          current
        DESCRIPTION
                "This object identifies the SG Mate name associated with
                 the ciscoItpXuaSgmStateChange notification."
        ::= { cItpXuaMIBNotifObjects 1 }

cItpXuaAspDisplayName   OBJECT-TYPE
        SYNTAX          CItpTcXuaName
        MAX-ACCESS      accessible-for-notify
        STATUS          current
        DESCRIPTION
                "This object identifies the ASP name associated with
                 the ciscoItpXuaAspStateChange notification."
        ::= { cItpXuaMIBNotifObjects 2 }

cItpXuaAsDisplayName    OBJECT-TYPE
        SYNTAX          CItpTcXuaName
        MAX-ACCESS      accessible-for-notify
        STATUS          current
        DESCRIPTION
                "This object identifies the AS name associated with
                 the ciscoItpXuaAspStateChange and
                 ciscoItpXuaAsStateChange notifications."
        ::= { cItpXuaMIBNotifObjects 3 }

--  *************************************************************
--  *                                                           *
--  * Notifications                                             *
--  *                                                           *
--  *************************************************************

ciscoItpXuaAspStateChange NOTIFICATION-TYPE
        OBJECTS {
                cItpSpCLLICode,
                cItpXuaAspDisplayName,
                cItpXuaAsDisplayName,
                cItpXuaAspAsState
        }
        STATUS  current
        DESCRIPTION
                "The notification generated when an ASP changes
                 to a new state. The value of cItpXuaAspAsState
                 indicates the new state for the ASP that is 
                 serving the AS specified by cItpXuaAsDisplayName."
        ::= { ciscoItpXuaMIBNotifs 1 }

ciscoItpXuaSgmStateChange NOTIFICATION-TYPE
        OBJECTS {
                cItpSpCLLICode,
                cItpXuaSgmDisplayName,
                cItpXuaSgmState
        }
        STATUS  current
        DESCRIPTION
                "The notification generated when an SG Mate
                 changes to a new state. The value of
                 cItpXuaSgmState indicates the new state for
                 the SG Mate."
        ::= { ciscoItpXuaMIBNotifs 2 }

ciscoItpXuaAsStateChange NOTIFICATION-TYPE
        OBJECTS {
                cItpSpCLLICode,
                cItpXuaAsDisplayName,
                cItpXuaAsState
        }
        STATUS  current
        DESCRIPTION
                "The notification generated when an AS changes
                 to a new state. The value of cItpXuaAsState
                 indicates the new state for the AS."
        ::= { ciscoItpXuaMIBNotifs 3 }

--  *************************************************************
--  *                                                           *
--  *  Conformance Information                                  *
--  *                                                           *
--  *************************************************************
ciscoItpXuaMIBCompliances OBJECT IDENTIFIER
        ::= { ciscoItpXuaConformance 1 }
ciscoItpXuaMIBGroups      OBJECT IDENTIFIER
        ::= { ciscoItpXuaConformance 2 }

-- Compliance

ciscoItpXuaMIBCompliance MODULE-COMPLIANCE
        STATUS current
        DESCRIPTION
                "The compliance statement for entities which
                 implement the Cisco ITP XUA MIB"
        MODULE -- this module
                MANDATORY-GROUPS {
                        ciscoItpXuaScalarsGroup,
                        ciscoItpXuaInstGroup,
                        ciscoItpXuaInstLocalIpGroup,
                        ciscoItpXuaSgmGroup,
                        ciscoItpXuaAspGroup,
                        ciscoItpXuaAspRemoteIpGroup,
                        ciscoItpXuaAsGroup,
                        ciscoItpXuaAspAsGroup,
                        ciscoItpXuaNotifObjectsGroup,
                        ciscoItpXuaNotificationsGroup
                }
        ::= { ciscoItpXuaMIBCompliances 1 }

-- Units of Conformance

ciscoItpXuaScalarsGroup OBJECT-GROUP
        OBJECTS {
                cItpXuaInstConfigLastChanged,
                cItpXuaSgmConfigLastChanged,
                cItpXuaAspConfigLastChanged,
                cItpXuaAsConfigLastChanged,
                cItpXuaStateChangeNotifEnabled
        }
        STATUS current
        DESCRIPTION
                "M3UA/SUA main objects."
        ::= { ciscoItpXuaMIBGroups 1 }

ciscoItpXuaInstGroup OBJECT-GROUP
        OBJECTS {
                cItpXuaInstProtocol,
                cItpXuaInstShut,
                cItpXuaInstActiveASPs,
                cItpXuaInstRowStatus
        }
        STATUS current
        DESCRIPTION
                "M3UA/SUA Instance objects."
        ::= { ciscoItpXuaMIBGroups 2 }

ciscoItpXuaInstLocalIpGroup OBJECT-GROUP
        OBJECTS {
                cItpXuaInstLocalIpType,
                cItpXuaInstLocalIpAddr,
                cItpXuaInstLocalIpRowStatus
        }
        STATUS current
        DESCRIPTION
                "The Local IP address for M3UA/SUA Instance
                 objects."
        ::= { ciscoItpXuaMIBGroups 3 }

ciscoItpXuaSgmGroup OBJECT-GROUP
        OBJECTS {
                cItpXuaSgmAssocId,
                cItpXuaSgmLocalPort,
                cItpXuaSgmRemotePort,
                cItpXuaSgmShut,
                cItpXuaSgmActiveTS,
                cItpXuaSgmQosClass,
                cItpXuaSgmPassive,
                cItpXuaSgmState,
                cItpXuaSgmRowStatus
        }
        STATUS current
        DESCRIPTION
                "SG Mate objects."
        ::= { ciscoItpXuaMIBGroups 4 }

ciscoItpXuaAspGroup OBJECT-GROUP
        OBJECTS {
                cItpXuaAspAssocId,
                cItpXuaAspLocalPort,
                cItpXuaAspRemotePort,
                cItpXuaAspProtocol,
                cItpXuaAspShut,
                cItpXuaAspBlocked,
                cItpXuaAspQosClass,
                cItpXuaAspIdentifier,
                cItpXuaAspRowStatus
        }
        STATUS current
        DESCRIPTION
                "M3UA/SUA ASP objects."
        ::= { ciscoItpXuaMIBGroups 5 }

ciscoItpXuaAspRemoteIpGroup OBJECT-GROUP
        OBJECTS {
                cItpXuaAspRemoteIpType,
                cItpXuaAspRemoteIpAddr,
                cItpXuaAspRemoteIpRowStatus
        }
        STATUS current
        DESCRIPTION
                "Remote IP address for M3UA/SUA ASP objects."
        ::= { ciscoItpXuaMIBGroups 6 }

ciscoItpXuaAspStatsGroup OBJECT-GROUP
        OBJECTS {
                cItpXuaAspPktsFromAsp,
                cItpXuaAspPktsToAsp,
                cItpXuaAspPktsFromMtp3,
                cItpXuaAspPktsToMtp3,
                cItpXuaAspASPUPsRcvd,
                cItpXuaAspASPUPACKsSent,
                cItpXuaAspASPDNsRcvd,
                cItpXuaAspASPDNACKsSent,
                cItpXuaAspASPACsRcvd,
                cItpXuaAspASPACACKsSent,
                cItpXuaAspASPIAsRcvd,
                cItpXuaAspASPIAACKsSent,
                cItpXuaAspErrorsRcvd,
                cItpXuaAspErrorsSent,
                cItpXuaAspNotifysSent,
                cItpXuaAspDUNAsRcvd,
                cItpXuaAspDUNAsSent,
                cItpXuaAspDAVAsRcvd,
                cItpXuaAspDAVAsSent,
                cItpXuaAspDUPUsRcvd,
                cItpXuaAspDUPUsSent,
                cItpXuaAspDAUDsRcvd,
                cItpXuaAspDAUDsSent,
                cItpXuaAspSCON0sRcvd,
                cItpXuaAspSCON1sRcvd,
                cItpXuaAspSCON2sRcvd,
                cItpXuaAspSCON3sRcvd,
                cItpXuaAspSCON0sSent,
                cItpXuaAspSCON1sSent,
                cItpXuaAspSCON2sSent,
                cItpXuaAspSCON3sSent
        }
        STATUS current
        DESCRIPTION
                "M3UA/SUA ASP Statistics objects."
        ::= { ciscoItpXuaMIBGroups 7 }

ciscoItpXuaAsGroup OBJECT-GROUP
        OBJECTS {
                cItpXuaAsProtocol,
                cItpXuaAsShut,
                cItpXuaAsState,
                cItpXuaAsStateOnSgMate,
                cItpXuaAsActiveTS,
                cItpXuaAsQosClass,
                cItpXuaAsTrafMode,
                cItpXuaAsRerouting,
                cItpXuaAsRoutingContext,
                cItpXuaAsRkParameters,
                cItpXuaAsRkDpc,
                cItpXuaAsRkOpc,
                cItpXuaAsRkOpcMask,
                cItpXuaAsRkSi,
                cItpXuaAsRkSsn,
                cItpXuaAsRkGtt,
                cItpXuaAsRkCicMin,
                cItpXuaAsRkCicMax,
                cItpXuaAsPktsFromMtp3,
                cItpXuaAsPktsToASPsOfAs,
                cItpXuaAsRowStatus
        }
        STATUS current
        DESCRIPTION
                "M3UA/SUA AS objects."
        ::= { ciscoItpXuaMIBGroups 8 }

ciscoItpXuaAspAsGroup OBJECT-GROUP
        OBJECTS {
                cItpXuaAspAsState,
                cItpXuaAspAsActiveTS,
                cItpXuaAspAsRowStatus
        }
        STATUS current
        DESCRIPTION
                "M3UA/SUA ASP-AS objects."
        ::= { ciscoItpXuaMIBGroups 9 }

ciscoItpXuaNotifObjectsGroup OBJECT-GROUP
        OBJECTS {
                cItpXuaSgmDisplayName,
                cItpXuaAspDisplayName,
                cItpXuaAsDisplayName
        }                      
        STATUS current
        DESCRIPTION
                "M3UA/SUA notification objects."
        ::= { ciscoItpXuaMIBGroups 10 }

ciscoItpXuaNotificationsGroup NOTIFICATION-GROUP
        NOTIFICATIONS {
                  ciscoItpXuaAspStateChange,
                  ciscoItpXuaSgmStateChange,
                  ciscoItpXuaAsStateChange
        }                      
        STATUS current
        DESCRIPTION
                "M3UA/SUA notifications."
        ::= { ciscoItpXuaMIBGroups 11 }

END
