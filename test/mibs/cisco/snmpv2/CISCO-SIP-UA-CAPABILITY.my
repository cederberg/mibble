-- *****************************************************************
-- CISCO-SIP-UA-CAPABILITY.my:  Session Initiation Protocol User
--                              Agent capability mib
--
-- August 2000, Kevin Lingle
--
-- Copyright (c) 2000, 2001 by cisco Systems, Inc.
-- All rights reserved.
-- *****************************************************************
CISCO-SIP-UA-CAPABILITY DEFINITIONS ::= BEGIN

IMPORTS
        MODULE-IDENTITY
                FROM SNMPv2-SMI
        AGENT-CAPABILITIES
                FROM SNMPv2-CONF
        ciscoAgentCapability
                FROM CISCO-SMI;


ciscoSipUaCapability MODULE-IDENTITY
                LAST-UPDATED    "200106110000Z"
                ORGANIZATION    "Cisco Systems, Inc."
                CONTACT-INFO
                        "       Cisco Systems
                                Customer Service
                        
                        Postal: 170 West Tasman Drive
                                San Jose, CA  95134
                                USA
                        
                           Tel: +1 800 553-NETS
                        
                        E-mail: cs-sip@cisco.com"
                DESCRIPTION
                        "Agent capabilities for the CISCO-SIP-UA-MIB."
                REVISION        "200106110000Z"
                DESCRIPTION
                        "Initial version of this MIB module."
        ::= { ciscoAgentCapability 172 }

ciscoSipUaCapabilityV12R0202 AGENT-CAPABILITIES

PRODUCT-RELEASE "Cisco IOS 12.2(2)."
  STATUS          current
  DESCRIPTION     "IOS 12.2 Cisco SIP User Agent MIB capabilities."

SUPPORTS        CISCO-SIP-UA-MIB
  INCLUDES      { ciscoSipBaseConfigGroup,
                  ciscoSipStatsInfoStatusCodesGroup,
                  ciscoSipStatsSuccessStatusCodesGroup,
                  ciscoSipStatsGlobalStatusCodesGroup,
                  ciscoSipTrafficStatsGroup,
                  ciscoSipTimerConfigGroup,
                  ciscoSipRetryConfigGroup,
                  ciscoSipRetryStatsGroup,
                  ciscoSipStatsRedirStatusCodesGroup,
                  ciscoSipStatsClientStatusCodesGroup,
                  ciscoSipStatsServerStatusCodesGroup }

VARIATION cSipCfgRetryRegister
  ACCESS    not-implemented
  DESCRIPTION "Not implemented."

VARIATION cSipStatsTrafficRegisterIns
  ACCESS    not-implemented
  DESCRIPTION "Not implemented."

VARIATION cSipStatsTrafficRegisterOuts
  ACCESS    not-implemented
  DESCRIPTION "Not implemented."

::= { ciscoSipUaCapability 1 }

END
