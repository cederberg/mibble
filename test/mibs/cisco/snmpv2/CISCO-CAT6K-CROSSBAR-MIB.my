-- *****************************************************************
-- CISCO-CAT6K-CROSSBAR-MIB.my 
--
-- Mar 2001, Padma Pullela
-- 
--
-- Copyright (c) 2001 by cisco Systems, Inc.
-- All rights reserved.
-- *****************************************************************
--
CISCO-CAT6K-CROSSBAR-MIB DEFINITIONS ::= BEGIN

IMPORTS
    MODULE-IDENTITY,
    OBJECT-TYPE,
    Counter32
        FROM SNMPv2-SMI
    MODULE-COMPLIANCE,
    OBJECT-GROUP
        FROM SNMPv2-CONF
    ciscoMgmt
        FROM CISCO-SMI
    Percent
        FROM CISCO-QOS-PIB-MIB
    Unsigned32
        FROM CISCO-TC
    TEXTUAL-CONVENTION,
    TruthValue,
    DisplayString
        FROM SNMPv2-TC;

ciscoCat6kCrossbarMIB MODULE-IDENTITY
    LAST-UPDATED        "200106250000Z"
    ORGANIZATION        "Cisco Systems, Inc."
    CONTACT-INFO
       "Cisco Systems
        Customer Service
        Postal: 170 W Tasman Drive
        San Jose, CA  95134
        USA
        Tel: +1 800 553-NETS

        E-mail: cs-cat6000@cisco.com"
    DESCRIPTION
        "The Catalyst 6000 Crossbar MIB provides instrumentation for
        configuration and operation of the crossbar switching fabric
        module.
        "
    REVISION        "200106250000Z"
    DESCRIPTION
        "Initial version of this MIB module."
    ::= { ciscoMgmt 217 }

ciscoCat6kXbarMIBObjects OBJECT IDENTIFIER ::=  
                                  { ciscoCat6kCrossbarMIB 1 }

cc6kxbarConfiguration OBJECT IDENTIFIER ::=  
                                  { ciscoCat6kXbarMIBObjects 1 }
cc6kxbarStatus        OBJECT IDENTIFIER ::=  
                                  { ciscoCat6kXbarMIBObjects 2 }
cc6kxbarStatistics    OBJECT IDENTIFIER ::=  
                                  { ciscoCat6kXbarMIBObjects 3 }


-- Textual Conventions

ModuleSlotNumber ::= TEXTUAL-CONVENTION
  STATUS  current
  DESCRIPTION
          "Slot number of the module."
  SYNTAX  Unsigned32

FabricChannelNumber ::= TEXTUAL-CONVENTION
  STATUS  current
  DESCRIPTION
          "Fabric channel number."
  SYNTAX  Unsigned32

ChannelStatus ::= TEXTUAL-CONVENTION
  STATUS  current
  DESCRIPTION
          "Status of the Channel."
  SYNTAX  INTEGER{
                   ok(1),
                   syncError(2),
                   heartbeatError(3),
                   crcError(4),
                   bufferError(5),
                   timeoutError(6),
                   unused(7)
                 }

--
-- Configuration objects
--

cc6kxbarFallbackMode OBJECT-TYPE
    SYNTAX TruthValue
    MAX-ACCESS read-write
    STATUS current
    DESCRIPTION
        "cc6kxbarFallbackMode controls system fallback to bus-mode
        after loss of switching fabric module.
        'true'  - When the last fabric card is removed
                  system will adjust the supervisor and
                  line cards switching mode automatically without
                  resetting the system. With this feature enabled,
                  the switch might lose traffic while it's
                  changing the switching mode.
        'false'  - All the ports in the system will be
                  disabled when the last fabric card is removed."
    DEFVAL { true }
    ::= { cc6kxbarConfiguration 1 }

cc6kxbarBusOnlyModeAllowed OBJECT-TYPE
    SYNTAX TruthValue
    MAX-ACCESS read-write
    STATUS current
    DESCRIPTION
        "This object determines the value of
         cc6kxbarModuleModeSwitchingMode of each module.
         'true' - Each and every module is allowed to run in bus-only 
                  mode.
         'false' - None of the modules are allowed to run in bus-only 
                   mode.i.e., All the non-fabric capable modules will 
                   be powered off.  Absence of fabric module results 
                   in all the fabric capable modules being powered 
                   off."
    DEFVAL { true }
    ::= { cc6kxbarConfiguration 2 }

cc6kxbarTruncatedModeAllowed OBJECT-TYPE
    SYNTAX TruthValue
    MAX-ACCESS read-write
    STATUS current
    DESCRIPTION
        "This object determines the value of
         cc6kxbarModuleModeSwitchingMode of each module.
         'true' - With the cc6kxbarMinFabricPresent fabric capable
                  modules present in the system, 
                  cc6kxbarModuleModeSwitchingMode
                  will be 'crossbarmode' for each module.
         'false' - truncation mode is not allowed."
    DEFVAL { true }
    ::= { cc6kxbarConfiguration 3 }

cc6kxbarMinFabricPresent  OBJECT-TYPE
    SYNTAX ModuleSlotNumber
    MAX-ACCESS read-write
    STATUS current
    DESCRIPTION
        "This object indicates the minimum number 
         of switching fabric capable modules to be present in the 
         system, for any switching fabric capable module to be in
         'crossbarmode' indicated by  cc6kxbarModuleModeSwitchingMode,
         when cc6kxbarTruncatedModeAllowed is set to 'true'.
         When cc6kxbarMinFabricPresent has a 
         value larger than the number of slots in the system then 
         the value of cc6kxbarTruncatedModeAllowed has no effect."
    DEFVAL { 2 }
    ::= { cc6kxbarConfiguration 4 }

cc6kxbarLcdBannerTable OBJECT-TYPE
    SYNTAX SEQUENCE OF Cc6kxbarLcdBannerEntry
    MAX-ACCESS not-accessible
    STATUS current
    DESCRIPTION
        "cc6kxbarLcdBannerTable configures the Lcd banner of the
         fabric module."
    ::= { cc6kxbarConfiguration 5 }

cc6kxbarLcdBannerEntry OBJECT-TYPE
    SYNTAX Cc6kxbarLcdBannerEntry
    MAX-ACCESS not-accessible
    STATUS     current
    DESCRIPTION
        "An entry in cc6kxbarLcdBannerTable.
         Entries are created by the agent based on the
         size of the lcd banner." 
    INDEX { cc6kxbarLcdBannerIndex }
    ::= { cc6kxbarLcdBannerTable 1 }

Cc6kxbarLcdBannerEntry ::= SEQUENCE {
    cc6kxbarLcdBannerIndex    Unsigned32,
    cc6kxbarLcdBannerBanner   DisplayString,
    cc6kxbarLcdBannerMaxSize  Unsigned32
    }
cc6kxbarLcdBannerIndex OBJECT-TYPE
    SYNTAX     Unsigned32
    MAX-ACCESS not-accessible
    STATUS current
    DESCRIPTION
           "Object which specifies a unique entry in the
            table."
   ::= { cc6kxbarLcdBannerEntry 1}

cc6kxbarLcdBannerBanner OBJECT-TYPE
   SYNTAX     DisplayString
   MAX-ACCESS read-write
   STATUS current
   DESCRIPTION
          "Message that would be displayed on the fabric card LCD.
           The size of cc6kxbarLcdBannerBanner should be less than 
           or equal to the cc6kxbarLcdBannerMaxSize value."
   ::= { cc6kxbarLcdBannerEntry 2}

cc6kxbarLcdBannerMaxSize OBJECT-TYPE
   SYNTAX     Unsigned32
   MAX-ACCESS read-only
   STATUS     current
   DESCRIPTION
          "Maximum size of the associated cc6kxbarLcdBannerBanner
           object."
   ::= { cc6kxbarLcdBannerEntry 3}


--
-- Status objects
--

cc6kxbarFabricActiveSlot OBJECT-TYPE
    SYNTAX ModuleSlotNumber
    MAX-ACCESS read-only
    STATUS current
    DESCRIPTION
        "cc6kxbarFabricActiveSlot indicates the slot number of the 
         active switching fabric module. A value of zero indicates 
         that the active switching fabric module is either powered 
         down or not present in the chassis."
    ::= { cc6kxbarStatus 1 }

cc6kxbarFabricBackupSlot OBJECT-TYPE
    SYNTAX ModuleSlotNumber
    MAX-ACCESS read-only
    STATUS current
    DESCRIPTION
        "cc6kxbarFabricBackupSlot indicates the slot number of the 
         backup switching fabric module. A value of zero indicates 
         that the backup switching fabric module is either powered
         down or not present in the chassis." 
    ::= { cc6kxbarStatus 2 }


cc6kxbarModuleModeTable OBJECT-TYPE
    SYNTAX SEQUENCE OF Cc6kxbarModuleModeEntry
    MAX-ACCESS not-accessible
    STATUS current
    DESCRIPTION
        "cc6kxbarModuleModeTable indicates the switching mode of each 
         module in the system."
    ::= { cc6kxbarStatus 3 }

cc6kxbarModuleModeEntry OBJECT-TYPE
    SYNTAX Cc6kxbarModuleModeEntry
    MAX-ACCESS not-accessible
    STATUS     current
    DESCRIPTION
        "An entry in cc6kxbarModuleModeTable. The agent creates
        an entry when a non switching fabric module 
        is inserted in the chassis.
        The agent destroys an entry when a non switching fabric
        module is power down or reset or removed from the chassis."
    INDEX { cc6kxbarModuleModeModule }
    ::= { cc6kxbarModuleModeTable 1 }

Cc6kxbarModuleModeEntry ::= SEQUENCE {
    cc6kxbarModuleModeModule          ModuleSlotNumber,
    cc6kxbarModuleModeSwitchingMode   INTEGER
    }
cc6kxbarModuleModeModule  OBJECT-TYPE
    SYNTAX ModuleSlotNumber
    MAX-ACCESS not-accessible
    STATUS current
    DESCRIPTION
        "The module slot number."
    ::= { cc6kxbarModuleModeEntry 1} 

cc6kxbarModuleModeSwitchingMode  OBJECT-TYPE
    SYNTAX INTEGER{
               busmode(1),
               crossbarmode(2),
               dcefmode(3)
            }
    MAX-ACCESS read-only
    STATUS current
    DESCRIPTION
        "cc6kxbarModuleModeSwitchingMode indicates switching mode 
         of the cc6kxbarModuleModeModule.
         'busmode'     -  Modules  in this mode don't use fabric.
                          Backplane is used for both lookup and data
                          forwarding.
         'crossbarmode' -  Modules in this mode use backplane 
                           for forwarding decision and fabric for data 
                           forwarding
         'dcefmode'    -  Modules in this mode use fabric for data 
                          forwarding and local forwarding is enabled."
    ::= { cc6kxbarModuleModeEntry 2 }


cc6kxbarModuleChannelTable OBJECT-TYPE
    SYNTAX SEQUENCE OF Cc6kxbarModuleChannelEntry
    MAX-ACCESS not-accessible
    STATUS current
    DESCRIPTION
        "cc6kxbarModuleChannelTable shows the operational status
        of fabric channels. This table will be instantiated only when 
        cc6kxbarFabricActiveSlot has a valid value other than zero."
        ::= { cc6kxbarStatus 4 }

cc6kxbarModuleChannelEntry OBJECT-TYPE
    SYNTAX Cc6kxbarModuleChannelEntry
    MAX-ACCESS not-accessible
    STATUS     current
    DESCRIPTION
        "An entry in cc6kxbarModuleChannelTable." 
    INDEX { cc6kxbarModuleChannelModule, cc6kxbarModuleChannelChannel }
    ::= { cc6kxbarModuleChannelTable 1 }

Cc6kxbarModuleChannelEntry ::= SEQUENCE {
    cc6kxbarModuleChannelModule               ModuleSlotNumber,
    cc6kxbarModuleChannelChannel              FabricChannelNumber,
    cc6kxbarModuleChannelModStatus            ChannelStatus,
    cc6kxbarModuleChannelFabStatus            ChannelStatus
    }

cc6kxbarModuleChannelModule  OBJECT-TYPE
    SYNTAX ModuleSlotNumber
    MAX-ACCESS not-accessible
    STATUS current
    DESCRIPTION
        "The module slot number."
    ::= { cc6kxbarModuleChannelEntry 1 }

cc6kxbarModuleChannelChannel OBJECT-TYPE
    SYNTAX FabricChannelNumber
    MAX-ACCESS not-accessible
    STATUS current
    DESCRIPTION
        "Fabric channel number of the  cc6kxbarModuleChannelModule."
    ::= { cc6kxbarModuleChannelEntry 2 }

cc6kxbarModuleChannelModStatus  OBJECT-TYPE
    SYNTAX     ChannelStatus
    MAX-ACCESS read-only
    STATUS current
    DESCRIPTION
        "The status of the fabric channel at the 
         cc6kxbarModuleChannelModule."
    ::= { cc6kxbarModuleChannelEntry 3 }

cc6kxbarModuleChannelFabStatus  OBJECT-TYPE
    SYNTAX ChannelStatus 
    MAX-ACCESS read-only
    STATUS current
    DESCRIPTION
        "The status of the fabric channel at the 
         cc6kxbarFabricActiveSlot."
    ::= { cc6kxbarModuleChannelEntry 4 }

--
-- Statistics Objects
--
cc6kxbarStatisticsTable OBJECT-TYPE
    SYNTAX SEQUENCE OF Cc6kxbarStatisticsEntry
    MAX-ACCESS not-accessible
    STATUS current
    DESCRIPTION
        "cc6kxbarStatisticsTable gives the 
         fabric channel counters and utilization
         information.  This table will be instantiated when 
         cc6kxbarFabricActiveSlot has a valid value other than
         zero."
    ::= { cc6kxbarStatistics 1 }

cc6kxbarStatisticsEntry OBJECT-TYPE
    SYNTAX Cc6kxbarStatisticsEntry
    MAX-ACCESS not-accessible
    STATUS     current
    DESCRIPTION
        "An entry in cc6kxbarStatisticsTable."  
    INDEX { cc6kxbarStatisticsModule, cc6kxbarStatisticsChannel }
    ::= { cc6kxbarStatisticsTable 1 }

Cc6kxbarStatisticsEntry ::= SEQUENCE {
    cc6kxbarStatisticsModule         ModuleSlotNumber,
    cc6kxbarStatisticsChannel        FabricChannelNumber,
    cc6kxbarStatisticsInErrors       Counter32,
    cc6kxbarStatisticsOutErrors      Counter32,
    cc6kxbarStatisticsOutDropped     Counter32,
    cc6kxbarStatisticsInUtil         Percent,
    cc6kxbarStatisticsOutUtil        Percent

    }

cc6kxbarStatisticsModule  OBJECT-TYPE
    SYNTAX ModuleSlotNumber
    MAX-ACCESS not-accessible
    STATUS current
    DESCRIPTION
        "The module slot number."
    ::= { cc6kxbarStatisticsEntry 1 }

cc6kxbarStatisticsChannel OBJECT-TYPE
    SYNTAX FabricChannelNumber
    MAX-ACCESS not-accessible
    STATUS current
    DESCRIPTION
        "Fabric channel number associated with the  
         cc6kxbarStatisticsModule."
    ::= { cc6kxbarStatisticsEntry 2 }

cc6kxbarStatisticsInErrors  OBJECT-TYPE
    SYNTAX Counter32
    MAX-ACCESS read-only
    STATUS current
    DESCRIPTION
        "The total number of error packets received on 
         cc6kxbarStatisticsChannel for cc6kxbarStatisticsModule
         since this entry was last initialized."
    ::= { cc6kxbarStatisticsEntry 3 }

cc6kxbarStatisticsOutErrors  OBJECT-TYPE
    SYNTAX Counter32
    MAX-ACCESS read-only
    STATUS current
    DESCRIPTION
        "The total number of error packets transmitted on 
         cc6kxbarStatisticsModule through the 
         cc6kxbarStatisticsChannel since this entry was 
         last initialized."
    ::= { cc6kxbarStatisticsEntry 4 }

cc6kxbarStatisticsOutDropped  OBJECT-TYPE
    SYNTAX Counter32
    MAX-ACCESS read-only
    STATUS current
    DESCRIPTION
        "The total number of  dropped packets transmitted on the
         cc6kxbarStatisticsChannel for cc6kxbarStatisticsModule
         since this entry was last initialized."
    ::= { cc6kxbarStatisticsEntry 5 }


cc6kxbarStatisticsInUtil OBJECT-TYPE
    SYNTAX Percent
    MAX-ACCESS read-only
    STATUS current
    DESCRIPTION
        "Input utilization of the cc6kxbarStatisticsChannel for 
         cc6kxbarStatisticsModule."
    ::= {cc6kxbarStatisticsEntry 6}

cc6kxbarStatisticsOutUtil OBJECT-TYPE
    SYNTAX Percent
    MAX-ACCESS read-only
    STATUS current
    DESCRIPTION
        "Output utilization of the cc6kxbarStatisticsChannel for
         cc6kxbarStatisticsModule."
    ::= {cc6kxbarStatisticsEntry 7}

-- Conformance and Compliance

cc6kxbarMIBConformance OBJECT IDENTIFIER ::= 
                                 { ciscoCat6kCrossbarMIB  3 }
cc6kxbarMIBCompliances OBJECT IDENTIFIER ::= 
                                 { cc6kxbarMIBConformance 1 }
cc6kxbarMIBGroups      OBJECT IDENTIFIER ::= 
                                 { cc6kxbarMIBConformance 2 }


-- Conformance

cc6kxbarMIBCompliance MODULE-COMPLIANCE
     STATUS current
        DESCRIPTION
          "The compliance statement for
           the CISCO-CROSSBAR-MIB."
     MODULE  --this module
     MANDATORY-GROUPS { 
                      cc6kxbarModuleStatusGroup,
                      cc6kxbarChannelStatusGroup,
                      cc6kxbarChannelStatisticsGroup
                      }
     GROUP  cc6kxbarFallbackGroup
     DESCRIPTION
         "This group is mandatory only for those platforms which
         support fallback mode feature."

     GROUP cc6kxbarBusOnlyAllowedGroup
     DESCRIPTION
          "This group is mandatory only for those platforms which
          support fallback mode feature."
     ::= { cc6kxbarMIBCompliances 2 }

-- Units of Conformance

cc6kxbarModuleStatusGroup OBJECT-GROUP
       OBJECTS{
            cc6kxbarLcdBannerMaxSize,
            cc6kxbarLcdBannerBanner,
            cc6kxbarTruncatedModeAllowed,
            cc6kxbarMinFabricPresent,
            cc6kxbarFabricActiveSlot,
            cc6kxbarFabricBackupSlot,
            cc6kxbarModuleModeSwitchingMode
       }
       STATUS current
       DESCRIPTION
            "A collection of objects providing 
             configuration and operation of the crossbar 
             switching fabric module and switching capable 
             module."
       ::= { cc6kxbarMIBGroups 1 }

cc6kxbarChannelStatusGroup OBJECT-GROUP
     OBJECTS{
              cc6kxbarModuleChannelModStatus,
              cc6kxbarModuleChannelFabStatus
     }
     STATUS current
     DESCRIPTION
             "A collection of objects providing 
             status and configuration of the fabric channel."
     ::= { cc6kxbarMIBGroups 2 }

cc6kxbarChannelStatisticsGroup OBJECT-GROUP
     OBJECTS{
              cc6kxbarStatisticsInErrors,
              cc6kxbarStatisticsOutErrors,
              cc6kxbarStatisticsOutDropped,
              cc6kxbarStatisticsInUtil,
              cc6kxbarStatisticsOutUtil
            }
     STATUS current
     DESCRIPTION
            "A collection of objects providing statistics for
             the fabric channel."
        ::= { cc6kxbarMIBGroups 3 }

cc6kxbarFallbackGroup OBJECT-GROUP
    OBJECTS { cc6kxbarFallbackMode }
    STATUS  current
    DESCRIPTION
      "This object controls system fallback to bus-mode
       after loss of switching fabric module."
    ::= { cc6kxbarMIBGroups 4 }

cc6kxbarBusOnlyAllowedGroup OBJECT-GROUP
    OBJECTS { cc6kxbarBusOnlyModeAllowed }
    STATUS  current
    DESCRIPTION
      "This object determines the value of
       cc6kxbarModuleModeSwitchingMode of each module."
    ::= { cc6kxbarMIBGroups 5 }
END
