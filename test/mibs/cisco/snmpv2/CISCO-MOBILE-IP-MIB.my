-- *****************************************************************
-- CISCO-MOBILE-IP-MIB.my: Cisco Enterprise Mobile IP MIB file
--
-- July 2000, Ravindra Rathi
--
-- Copyright (c) 2000, 2001 by Cisco Systems, Inc.
-- All rights reserved.
--
-- *****************************************************************


CISCO-MOBILE-IP-MIB DEFINITIONS ::= BEGIN

    IMPORTS
        MODULE-IDENTITY,
        OBJECT-TYPE,
        Gauge32
                FROM SNMPv2-SMI
        MODULE-COMPLIANCE,
        OBJECT-GROUP
                FROM SNMPv2-CONF
        ciscoMgmt
                FROM CISCO-SMI;

    ciscoMobileIpMIB    MODULE-IDENTITY
        LAST-UPDATED    "200101250000Z"
        ORGANIZATION    "Cisco Systems, Inc."
        CONTACT-INFO
                "       Cisco Systems
                        Customer Service

                Postal: 170 W. Tasman Drive
                        San Jose, CA  95134
                        USA

                   Tel: +1 800 553-NETS

                E-mail: cs-mobileip@cisco.com"
        DESCRIPTION
                "An extension to the IETF MIB module defined in
                RFC2006 for managing Mobile IP implementations."
        REVISION        "200101250000Z"
        DESCRIPTION
                "Initial version of this MIB module."
        ::= { ciscoMgmt 174 }

    ciscoMobileIpMIBObjects
                OBJECT IDENTIFIER ::= { ciscoMobileIpMIB 1 }

    -- Groups under ciscoMobileIpMIBObjects.
    -- There are three different types of Mobile IP entities
    -- i.e. Home Agent, Foreign Agent and Mobile Node. The IETF
    -- Mobile IP MIB module [RFC2006] has three main groups 
    -- representing each of these entities i.e. 'MipFA': foreign 
    -- agent, 'MipHA': home agent and 'MipMN': mobile node. Each of 
    -- these groups have been further subdivided into different 
    -- subgroups. Each of these subgroups is a collection of 
    -- objects related to a particular function, performed by the 
    -- entity represented by its main group e.g. 'faRegistration' 
    -- is a subgroup under group 'MipFA' which has collection of 
    -- objects for registration function within a foreign agent. 
    -- This MIB also follows the same hierarchical structure to 
    -- maintain the modularity with respect to Mobile IP.


    cmiFa    OBJECT IDENTIFIER ::= { ciscoMobileIpMIBObjects 1 }
    cmiHa    OBJECT IDENTIFIER ::= { ciscoMobileIpMIBObjects 2 }

    cmiFaReg    OBJECT IDENTIFIER ::= { cmiFa 1 }

    cmiHaReg    OBJECT IDENTIFIER ::= { cmiHa 1 }

    -- Foreign Agent Registration Group

    cmiFaRegTotalVisitors  OBJECT-TYPE
         SYNTAX      Gauge32
         MAX-ACCESS  read-only
         STATUS      current
         DESCRIPTION
                 "The current number of entries in faVisitorTable.
                 faVisitorTable contains the foreign agent's visitor 
                 list. The foreign agent updates this table in 
                 response to registration events from mobile nodes."
         REFERENCE
                 "RFC2006 - Mobile IP MIB Definition using SMIv2"
         ::= { cmiFaReg 1 }


    -- Home Agent Registration Group 

    cmiHaRegTotalMobilityBindings  OBJECT-TYPE
         SYNTAX      Gauge32
         MAX-ACCESS  read-only
         STATUS      current
         DESCRIPTION
                 "The current number of entries in 
                 haMobilityBindingTable. haMobilityBindingTable
                 contains the home agent's mobility binding list. 
                 The home agent updates this table in response to 
                 registration events from mobile nodes."  
         REFERENCE 
                 "RFC2006 - Mobile IP MIB Definition using SMIv2"
         ::= { cmiHaReg 1 }

    -- conformance information

    ciscoMobileIpMIBConformance 
        OBJECT IDENTIFIER ::= { ciscoMobileIpMIB 3 }

    ciscoMobileIpCompliances
                OBJECT IDENTIFIER ::= { ciscoMobileIpMIBConformance 1 }
    ciscoMobileIpGroups
                OBJECT IDENTIFIER ::= { ciscoMobileIpMIBConformance 2 }

    -- compliance statements

    ciscoMobileIpCompliance    MODULE-COMPLIANCE
        STATUS    current
        DESCRIPTION
                "The compliance statement for management entities
                which implement the Cisco Mobile IP MIB."
        MODULE
            GROUP     ciscoMobileIpFaRegGroup
            DESCRIPTION
                "This group is mandatory for foreign agents."
            GROUP    ciscoMobileIpHaRegGroup
            DESCRIPTION
                "This group is mandatory for home agents."
       ::= { ciscoMobileIpCompliances 1 }

    -- Units of conformance

    ciscoMobileIpFaRegGroup    OBJECT-GROUP
        OBJECTS   {  cmiFaRegTotalVisitors }
        STATUS    current
        DESCRIPTION
                "A collection of objects providing management
                information for the registration function within
                a foreign agent."
        ::= { ciscoMobileIpGroups 1 }

    ciscoMobileIpHaRegGroup    OBJECT-GROUP
        OBJECTS   {  cmiHaRegTotalMobilityBindings }
        STATUS    current
        DESCRIPTION
                "A collection of objects providing management
                information for the registration function within
                a home agent."
        ::= { ciscoMobileIpGroups 2 }

END
