-- *****************************************************************
-- CISCO-IETF-SCTP-EXT-CAPABILITY.my: 
--            Stream Control Transmission Protocol Extension
--            Agent capability MIB
--
-- November 2001, John Linton
--
-- Copyright (c) 2001-2002 by cisco Systems, Inc.
-- All rights reserved.
-- *****************************************************************
CISCO-IETF-SCTP-EXT-CAPABILITY DEFINITIONS ::= BEGIN

IMPORTS
        MODULE-IDENTITY
                FROM SNMPv2-SMI
                
        AGENT-CAPABILITIES
                FROM SNMPv2-CONF
                
        ciscoAgentCapability
                FROM CISCO-SMI;



ciscoSctpExtCapability MODULE-IDENTITY
        LAST-UPDATED    "200201210000Z"
        ORGANIZATION    "Cisco Systems, Inc."
        CONTACT-INFO
                "       Cisco Systems
                        Customer Service
                
                Postal: 170 West Tasman Drive
                        San Jose, CA  95134
                        USA
                
                   Tel: +1 800 553-NETS
                
                E-mail: cs-sctp@cisco.com"
        DESCRIPTION
                "Agent capabilities for the CISCO-IETF-SCTP-EXT-MIB."
                
        REVISION        "200201210000Z"
        DESCRIPTION
                "Updated capabilities to support additional objects
                 and a new notification."
                
        REVISION        "200111300000Z"
        DESCRIPTION
                "Initial version of this MIB module."
        ::= { ciscoAgentCapability 221 } 

ciscoSctpExtCapabilityV12R024MB1 AGENT-CAPABILITIES

    PRODUCT-RELEASE  "Cisco IOS 12.2(4)MB1"
    STATUS           current
    DESCRIPTION      "IOS 12.2(4)MB1 Cisco CISCO-IETF-SCTP-EXT-MIB.my
                      User Agent MIB capabilities."

    SUPPORTS         CISCO-IETF-SCTP-EXT-MIB
        INCLUDES     { 
                         cSctpExtStatGroup, 
                         cSctpExtCtrlGroup, 
                         cSctpExtAssocCtrlGroup,  
                         cSctpExtAssocStatGroup,  
                         cSctpExtAssocRemAddrGroup  
                     }  

    ::= { ciscoSctpExtCapability 1 }


ciscoSctpExtCapabilityV12R0204MB3 AGENT-CAPABILITIES

    PRODUCT-RELEASE "Cisco IOS 12.2(4)MB3"
    STATUS          current
    DESCRIPTION     "IOS 12.2(4)MB3 Cisco CISCO-IETF-SCTP-EXT-MIB.my
                     User Agent MIB capabilities."
                      
    SUPPORTS        CISCO-IETF-SCTP-EXT-MIB
        INCLUDES    { 
                        cSctpExtStatGroup, 
                        cSctpExtAssocCtrlGroup,  
                        cSctpExtAssocRemAddrGroup, 
                        cSctpExtAssocNotificationsGroup,
                        cSctpExtCtrlGroupRev1, 
                        cSctpExtAssocStatGroupRev1
                    }  

    ::= { ciscoSctpExtCapability 2 }

END
