EtherLike-MIB DEFINITIONS ::= BEGIN

       IMPORTS
           MODULE-IDENTITY, OBJECT-TYPE, OBJECT-IDENTITY,
           Counter32, mib-2, transmission
               FROM SNMPv2-SMI
           MODULE-COMPLIANCE, OBJECT-GROUP
               FROM SNMPv2-CONF
           ifIndex, InterfaceIndex
               FROM IF-MIB;

       etherMIB MODULE-IDENTITY
           LAST-UPDATED "9806032150Z"  -- June 3, 1998
           ORGANIZATION "IETF 802.3 Hub MIB Working Group"
           CONTACT-INFO
               "WG E-mail: hubmib@hprnd.rose.hp.com
             To subscribe: hubmib-request@hprnd.rose.hp.com

                    Chair: Dan Romascanu
                   Postal: LANNET Ltd.
                           Atidum Technology Park, Bldg. 3
                           Tel Aviv 61131
                           Israel
                      Tel: +972 3 645 8414
                   E-mail: dromasca@lannet.com

                  Editor: John Flick
                  Postal: Hewlett-Packard Company
                          8000 Foothills Blvd. M/S 5556
                          Roseville, CA 95747-5556
                          USA
                     Tel: +1 916 785 4018
                     Fax: +1 916 785 3583
                  E-mail: johnf@hprnd.rose.hp.com

                  Editor: Jeffrey Johnson
                  Postal: RedBack Networks
                          2570 North First Street, Suite 410
                          San Jose, CA, 95131
                          USA
                     Tel: +1 408 571 2699
                     Fax: +1 408 571 2698
                  E-Mail: jeff@redbacknetworks.com"

           DESCRIPTION "The MIB module to describe generic objects for
                       Ethernet-like network interfaces. This MIB is an
                       updated version of the Ethernet-like MIB in RFC
                       1650."

           REVISION    "9806032150Z"
           DESCRIPTION "Updated to include support for 100 Mb/sec
                       interfaces."

           REVISION    "9402030400Z"
           DESCRIPTION "Version published as RFC 1650."
           ::= { mib-2 35 }

       etherMIBObjects OBJECT IDENTIFIER ::= { etherMIB 1 }

       dot3    OBJECT IDENTIFIER ::= { transmission 7 }

       -- the Ethernet-like Statistics group

       dot3StatsTable OBJECT-TYPE
           SYNTAX     SEQUENCE OF Dot3StatsEntry
           MAX-ACCESS not-accessible
           STATUS     current
           DESCRIPTION "Statistics for a collection of ethernet-like
                       interfaces attached to a particular system."
           ::= { dot3 2 }

       dot3StatsEntry OBJECT-TYPE
           SYNTAX     Dot3StatsEntry
           MAX-ACCESS not-accessible
           STATUS     current
           DESCRIPTION "Statistics for a particular interface to an
                       ethernet-like medium."
           INDEX       { dot3StatsIndex }
           ::= { dot3StatsTable 1 }

       Dot3StatsEntry ::=
           SEQUENCE {
               dot3StatsIndex                      InterfaceIndex,
               dot3StatsAlignmentErrors            Counter32,
               dot3StatsFCSErrors                  Counter32,
               dot3StatsSingleCollisionFrames      Counter32,
               dot3StatsMultipleCollisionFrames    Counter32,
               dot3StatsSQETestErrors              Counter32,
               dot3StatsDeferredTransmissions      Counter32,
               dot3StatsLateCollisions             Counter32,
               dot3StatsExcessiveCollisions        Counter32,
               dot3StatsInternalMacTransmitErrors  Counter32,
               dot3StatsCarrierSenseErrors         Counter32,
               dot3StatsFrameTooLongs              Counter32,
               dot3StatsInternalMacReceiveErrors   Counter32,
               dot3StatsEtherChipSet               OBJECT IDENTIFIER,
               dot3StatsSymbolErrors               Counter32
           }

       dot3StatsIndex OBJECT-TYPE
           SYNTAX      InterfaceIndex
           MAX-ACCESS  read-only
           STATUS      current
           DESCRIPTION "An index value that uniquely identifies an
                       interface to an ethernet-like medium.  The
                       interface identified by a particular value of
                       this index is the same interface as identified
                       by the same value of ifIndex."
           ::= { dot3StatsEntry 1 }

       dot3StatsAlignmentErrors OBJECT-TYPE
           SYNTAX      Counter32
           MAX-ACCESS  read-only
           STATUS      current


           DESCRIPTION "A count of frames received on a particular
                       interface that are not an integral number of
                       octets in length and do not pass the FCS check.

                       The count represented by an instance of this
                       object is incremented when the alignmentError
                       status is returned by the MAC service to the
                       LLC (or other MAC user). Received frames for
                       which multiple error conditions obtain are,
                       according to the conventions of IEEE 802.3
                       Layer Management, counted exclusively according
                       to the error status presented to the LLC."
           REFERENCE   "IEEE 802.3 Layer Management"
           ::= { dot3StatsEntry 2 }

       dot3StatsFCSErrors OBJECT-TYPE
           SYNTAX      Counter32
           MAX-ACCESS  read-only
           STATUS      current
           DESCRIPTION "A count of frames received on a particular
                       interface that are an integral number of octets
                       in length but do not pass the FCS check.

                       The count represented by an instance of this
                       object is incremented when the frameCheckError
                       status is returned by the MAC service to the
                       LLC (or other MAC user). Received frames for
                       which multiple error conditions obtain are,
                       according to the conventions of IEEE 802.3
                       Layer Management, counted exclusively according
                       to the error status presented to the LLC."
           REFERENCE   "IEEE 802.3 Layer Management"
           ::= { dot3StatsEntry 3 }

       dot3StatsSingleCollisionFrames OBJECT-TYPE
           SYNTAX      Counter32
           MAX-ACCESS  read-only
           STATUS      current
           DESCRIPTION "A count of successfully transmitted frames on
                       a particular interface for which transmission
                       is inhibited by exactly one collision.

                       A frame that is counted by an instance of this
                       object is also counted by the corresponding
                       instance of either the ifOutUcastPkts,
                       ifOutMulticastPkts, or ifOutBroadcastPkts,
                       and is not counted by the corresponding
                       instance of the dot3StatsMultipleCollisionFrames
                       object."
           REFERENCE   "IEEE 802.3 Layer Management"
           ::= { dot3StatsEntry 4 }

       dot3StatsMultipleCollisionFrames OBJECT-TYPE
           SYNTAX      Counter32
           MAX-ACCESS  read-only
           STATUS      current
           DESCRIPTION "A count of successfully transmitted frames on
                       a particular interface for which transmission
                       is inhibited by more than one collision.

                       A frame that is counted by an instance of this
                       object is also counted by the corresponding
                       instance of either the ifOutUcastPkts,
                       ifOutMulticastPkts, or ifOutBroadcastPkts,
                       and is not counted by the corresponding
                       instance of the dot3StatsSingleCollisionFrames
                       object."
           REFERENCE   "IEEE 802.3 Layer Management"
           ::= { dot3StatsEntry 5 }

       dot3StatsSQETestErrors OBJECT-TYPE
           SYNTAX      Counter32
           MAX-ACCESS  read-only
           STATUS      current
           DESCRIPTION "A count of times that the SQE TEST ERROR
                       message is generated by the PLS sublayer for a
                       particular interface. The SQE TEST ERROR
                       message is defined in section 7.2.2.2.4 of
                       ANSI/IEEE 802.3-1985 and its generation is
                       described in section 7.2.4.6 of the same
                       document."
           REFERENCE   "ANSI/IEEE Std 802.3-1985 Carrier Sense
                       Multiple Access with Collision Detection Access
                       Method and Physical Layer Specifications"
           ::= { dot3StatsEntry 6 }

       dot3StatsDeferredTransmissions OBJECT-TYPE
           SYNTAX      Counter32
           MAX-ACCESS  read-only
           STATUS      current
           DESCRIPTION "A count of frames for which the first
                       transmission attempt on a particular interface
                       is delayed because the medium is busy.

                       The count represented by an instance of this
                       object does not include frames involved in
                       collisions."
           REFERENCE   "IEEE 802.3 Layer Management"
           ::= { dot3StatsEntry 7 }

       dot3StatsLateCollisions OBJECT-TYPE
           SYNTAX      Counter32
           MAX-ACCESS  read-only
           STATUS      current
           DESCRIPTION "The number of times that a collision is
                       detected on a particular interface later than
                       512 bit-times into the transmission of a
                       packet.

                       Five hundred and twelve bit-times corresponds
                       to 51.2 microseconds on a 10 Mbit/s system. A
                       (late) collision included in a count
                       represented by an instance of this object is
                       also considered as a (generic) collision for
                       purposes of other collision-related
                       statistics."
           REFERENCE   "IEEE 802.3 Layer Management"
           ::= { dot3StatsEntry 8 }

       dot3StatsExcessiveCollisions OBJECT-TYPE
           SYNTAX      Counter32
           MAX-ACCESS  read-only
           STATUS      current
           DESCRIPTION "A count of frames for which transmission on a
                       particular interface fails due to excessive
                       collisions."
           REFERENCE   "IEEE 802.3 Layer Management"
           ::= { dot3StatsEntry 9 }

       dot3StatsInternalMacTransmitErrors OBJECT-TYPE
           SYNTAX      Counter32
           MAX-ACCESS  read-only
           STATUS      current
           DESCRIPTION "A count of frames for which transmission on a
                       particular interface fails due to an internal
                       MAC sublayer transmit error. A frame is only
                       counted by an instance of this object if it is
                       not counted by the corresponding instance of
                       either the dot3StatsLateCollisions object, the
                       dot3StatsExcessiveCollisions object, or the
                       dot3StatsCarrierSenseErrors object.

                       The precise meaning of the count represented by
                       an instance of this object is implementation-
                       specific.  In particular, an instance of this
                       object may represent a count of transmission
                       errors on a particular interface that are not
                       otherwise counted."
           REFERENCE   "IEEE 802.3 Layer Management"
           ::= { dot3StatsEntry 10 }

       dot3StatsCarrierSenseErrors OBJECT-TYPE
           SYNTAX      Counter32
           MAX-ACCESS  read-only
           STATUS      current
           DESCRIPTION "The number of times that the carrier sense
                       condition was lost or never asserted when
                       attempting to transmit a frame on a particular
                       interface.

                       The count represented by an instance of this
                       object is incremented at most once per
                       transmission attempt, even if the carrier sense
                       condition fluctuates during a transmission
                       attempt."
           REFERENCE   "IEEE 802.3 Layer Management"
           ::= { dot3StatsEntry 11 }

       -- { dot3StatsEntry 12 } is not assigned

       dot3StatsFrameTooLongs OBJECT-TYPE
           SYNTAX      Counter32
           MAX-ACCESS  read-only
           STATUS      current
           DESCRIPTION "A count of frames received on a particular
                       interface that exceed the maximum permitted
                       frame size.

                       The count represented by an instance of this
                       object is incremented when the frameTooLong
                       status is returned by the MAC service to the
                       LLC (or other MAC user). Received frames for
                       which multiple error conditions obtain are,
                       according to the conventions of IEEE 802.3
                       Layer Management, counted exclusively according
                       to the error status presented to the LLC."
           REFERENCE   "IEEE 802.3 Layer Management"
           ::= { dot3StatsEntry 13 }

       -- { dot3StatsEntry 14 } is not assigned

       -- { dot3StatsEntry 15 } is not assigned

       dot3StatsInternalMacReceiveErrors OBJECT-TYPE
           SYNTAX      Counter32
           MAX-ACCESS  read-only
           STATUS      current
           DESCRIPTION "A count of frames for which reception on a
                       particular interface fails due to an internal
                       MAC sublayer receive error. A frame is only
                       counted by an instance of this object if it is
                       not counted by the corresponding instance of
                       either the dot3StatsFrameTooLongs object, the
                       dot3StatsAlignmentErrors object, or the
                       dot3StatsFCSErrors object.
                       The precise meaning of the count represented by
                       an instance of this object is implementation-
                       specific.  In particular, an instance of this
                       object may represent a count of receive errors
                       on a particular interface that are not
                       otherwise counted."
           REFERENCE   "IEEE 802.3 Layer Management"
           ::= { dot3StatsEntry 16 }

       dot3StatsEtherChipSet OBJECT-TYPE
           SYNTAX      OBJECT IDENTIFIER
           MAX-ACCESS  read-only
           STATUS      current
           DESCRIPTION "This object contains an OBJECT IDENTIFIER
                       which identifies the chipset used to
                       realize the interface. Ethernet-like
                       interfaces are typically built out of
                       several different chips. The MIB implementor
                       is presented with a decision of which chip
                       to identify via this object. The implementor
                       should identify the chip which is usually
                       called the Medium Access Control chip.
                       If no such chip is easily identifiable,
                       the implementor should identify the chip
                       which actually gathers the transmit
                       and receive statistics and error
                       indications. This would allow a
                       manager station to correlate the
                       statistics and the chip generating
                       them, giving it the ability to take
                       into account any known anomalies
                       in the chip."
           ::= { dot3StatsEntry 17 }

       dot3StatsSymbolErrors OBJECT-TYPE
           SYNTAX      Counter32
           MAX-ACCESS  read-only
           STATUS      current
           DESCRIPTION "The number of times there was an invalid data
                       symbol when a valid carrier was present on a
                       particular interface.

                       The count represented by an instance of this
                       object is incremented at most once per carrier
                       event, even if multiple symbol errors occur
                       during the carrier event."
           REFERENCE   "IEEE 802.3u-1995 10 & 100 Mb/s Management"
           ::= { dot3StatsEntry 18 }

       -- the Ethernet-like Collision Statistics group

       -- Implementation of this group is optional; it is appropriate
       -- for all systems which have the necessary metering

       dot3CollTable OBJECT-TYPE
           SYNTAX      SEQUENCE OF Dot3CollEntry
           MAX-ACCESS  not-accessible
           STATUS      current
           DESCRIPTION "A collection of collision histograms for a
                       particular set of interfaces."
           ::= { dot3 5 }

       dot3CollEntry OBJECT-TYPE
           SYNTAX      Dot3CollEntry
           MAX-ACCESS  not-accessible
           STATUS      current
           DESCRIPTION "A cell in the histogram of per-frame
                       collisions for a particular interface.  An
                       instance of this object represents the
                       frequency of individual MAC frames for which
                       the transmission (successful or otherwise) on a
                       particular interface is accompanied by a
                       particular number of media collisions."
           INDEX       { ifIndex, dot3CollCount }
           ::= { dot3CollTable 1 }

       Dot3CollEntry ::=
           SEQUENCE {
               dot3CollCount        INTEGER,
               dot3CollFrequencies  Counter32
           }


       -- { dot3CollEntry 1 } is no longer in use

       dot3CollCount OBJECT-TYPE
           SYNTAX      INTEGER (1..16)
           MAX-ACCESS  not-accessible
           STATUS      current
           DESCRIPTION "The number of per-frame media collisions for
                       which a particular collision histogram cell
                       represents the frequency on a particular
                       interface."
           ::= { dot3CollEntry 2 }

       dot3CollFrequencies OBJECT-TYPE
           SYNTAX      Counter32
           MAX-ACCESS  read-only
           STATUS      current
           DESCRIPTION "A count of individual MAC frames for which the
                       transmission (successful or otherwise) on a
                       particular interface occurs after the
                       frame has experienced exactly the number
                       of collisions in the associated
                       dot3CollCount object.

                       For example, a frame which is transmitted
                       on interface 77 after experiencing
                       exactly 4 collisions would be indicated
                       by incrementing only dot3CollFrequencies.77.4.
                       No other instance of dot3CollFrequencies would
                       be incremented in this example."
           ::= { dot3CollEntry 3 }

       --  802.3 Tests

       dot3Tests   OBJECT IDENTIFIER ::= { dot3 6 }

       dot3Errors  OBJECT IDENTIFIER ::= { dot3 7 }

       --  TDR Test

       dot3TestTdr OBJECT-IDENTITY
           STATUS      current
           DESCRIPTION "The Time-Domain Reflectometry (TDR) test is
                       specific to ethernet-like interfaces of type
                       10Base5 and 10Base2.  The TDR value may be
                       useful in determining the approximate distance
                       to a cable fault.  It is advisable to repeat
                       this test to check for a consistent resulting
                       TDR value, to verify that there is a fault.

                       A TDR test returns as its result the time
                       interval, measured in 10 MHz ticks or 100 nsec
                       units, between the start of TDR test
                       transmission and the subsequent detection of a
                       collision or deassertion of carrier.  On
                       successful completion of a TDR test, the result
                       is stored as the value of an appropriate
                       instance of an appropriate vendor specific MIB
                       object, and the OBJECT IDENTIFIER of that
                       instance is stored in the appropriate instance
                       of the appropriate test result code object
                       (thereby indicating where the result has been
                       stored)."
           ::= { dot3Tests 1 }

       -- Loopback Test

       dot3TestLoopBack OBJECT-IDENTITY
           STATUS      current
           DESCRIPTION "This test configures the MAC chip and executes
                       an internal loopback test of memory, data paths,
                       and the MAC chip logic.  This loopback test can
                       only be executed if the interface is offline.
                       Once the test has completed, the MAC chip should
                       be reinitialized for network operation, but it
                       should remain offline.

                       If an error occurs during a test, the
                       appropriate test result object will be set
                       to indicate a failure.  The two OBJECT
                       IDENTIFIER values dot3ErrorInitError and
                       dot3ErrorLoopbackError may be used to provided
                       more information as values for an appropriate
                       test result code object."
           ::= { dot3Tests 2 }

       dot3ErrorInitError OBJECT-IDENTITY
           STATUS      current
           DESCRIPTION "Couldn't initialize MAC chip for test."
           ::= { dot3Errors 1 }

       dot3ErrorLoopbackError OBJECT-IDENTITY
           STATUS      current
           DESCRIPTION "Expected data not received (or not received
                       correctly) in loopback test."
           ::= { dot3Errors 2 }

       --  802.3 Hardware Chipsets

       -- The object dot3StatsEtherChipSet is provided to
       -- identify the MAC hardware used to communicate on an
       -- interface.  The following hardware chipsets are
       -- registered:

       dot3ChipSets          OBJECT IDENTIFIER ::= { dot3 8 }

       dot3ChipSetAMD        OBJECT IDENTIFIER ::= { dot3ChipSets 1 }

       dot3ChipSetAMD7990 OBJECT-IDENTITY
           STATUS      current
           DESCRIPTION "The authoritative identifier for the Advanced
                       Micro Devices Am7990 Local Area Network
                       Controller for Ethernet (LANCE)."
           ::= { dot3ChipSetAMD 1 }

       dot3ChipSetAMD79900 OBJECT-IDENTITY
           STATUS      current
           DESCRIPTION "The authoritative identifier for the Advanced
                       Micro Devices Am79900 chip."
           ::= { dot3ChipSetAMD 2 }

       dot3ChipSetAMD79C940 OBJECT-IDENTITY
           STATUS      current
           DESCRIPTION "The authoritative identifier for the Advanced
                       Micro Devices Am79C940 Media Access Controller
                       for Ethernet (MACE)."
           ::= { dot3ChipSetAMD 3 }

       dot3ChipSetAMD79C90 OBJECT-IDENTITY
           STATUS      current
           DESCRIPTION "The authoritative identifier for the Advanced
                       Micro Devices Am79C90 CMOS Local Area Network
                       Controller for Ethernet (C-LANCE)."
           ::= { dot3ChipSetAMD 4 }

       dot3ChipSetAMD79C960 OBJECT-IDENTITY
           STATUS      current
           DESCRIPTION "The authoritative identifier for the Advanced
                       Micro Devices Am79C960 PCnet-ISA Single Chip
                       Ethernet Controller for ISA."
           ::= { dot3ChipSetAMD 5 }

       dot3ChipSetAMD79C961 OBJECT-IDENTITY
           STATUS      current
           DESCRIPTION "The authoritative identifier for the Advanced
                       Micro Devices Am79C961 PCnet-ISA+ Single Chip
                       Plug & Play Full-Duplex Ethernet Controller
                       for ISA."
           ::= { dot3ChipSetAMD 6 }

       dot3ChipSetAMD79C961A OBJECT-IDENTITY
           STATUS      current
           DESCRIPTION "The authoritative identifier for the Advanced
                       Micro Devices Am79C961A PCnet-ISA II Single Chip
                       Plug & Play Full-Duplex Ethernet Controller
                       for ISA."
           ::= { dot3ChipSetAMD 7 }

       dot3ChipSetAMD79C965 OBJECT-IDENTITY
           STATUS      current
           DESCRIPTION "The authoritative identifier for the Advanced
                       Micro Devices Am79C965 PCnet-32 Single Chip
                       Ethernet Controller for PCI."
           ::= { dot3ChipSetAMD 8 }

       dot3ChipSetAMD79C970 OBJECT-IDENTITY
           STATUS      current
           DESCRIPTION "The authoritative identifier for the Advanced
                       Micro Devices Am79C970 PCnet PCI Single Chip
                       Ethernet Controller for PCI Local Bus."
           ::= { dot3ChipSetAMD 9 }

       dot3ChipSetAMD79C970A OBJECT-IDENTITY
           STATUS      current
           DESCRIPTION "The authoritative identifier for the Advanced
                       Micro Devices AM79C970A PCnet PCI II Single Chip
                       Full-Duplex Ethernet Controller for PCI Local
                       Bus."
           ::= { dot3ChipSetAMD 10 }

       dot3ChipSetAMD79C971 OBJECT-IDENTITY
           STATUS      current
           DESCRIPTION "The authoritative identifier for the Advanced
                       Micro Devices Am79C971 PCnet-FAST Single Chip
                       Full-Duplex 10/100 Mbps Ethernet Controller for
                       PCI Local Bus."
           ::= { dot3ChipSetAMD 11 }

       dot3ChipSetAMD79C972 OBJECT-IDENTITY
           STATUS      current
           DESCRIPTION "The authoritative identifier for the Advanced
                       Micro Devices Am79C972 PCnet-FAST+ Enhanced
                       10/100 Mbps PCI Ethernet Controller with OnNow
                       Support."
           ::= { dot3ChipSetAMD 12 }

       dot3ChipSetIntel      OBJECT IDENTIFIER ::= { dot3ChipSets 2 }

       dot3ChipSetIntel82586 OBJECT-IDENTITY
           STATUS      current
           DESCRIPTION "The authoritative identifier for the Intel
                       82586 IEEE 802.3 Ethernet LAN Coprocessor."
           ::= { dot3ChipSetIntel 1 }

       dot3ChipSetIntel82596 OBJECT-IDENTITY
           STATUS      current
           DESCRIPTION "The authoritative identifier for the Intel
                       82596 High-Performance 32-Bit Local Area Network
                       Coprocessor."
           ::= { dot3ChipSetIntel 2 }

       dot3ChipSetIntel82595 OBJECT-IDENTITY
           STATUS      current
           DESCRIPTION "The authoritative identifier for the Intel
                       82595 High Integration Ethernet Controller."
           ::= { dot3ChipSetIntel 3 }

       dot3ChipSetIntel82557 OBJECT-IDENTITY
           STATUS      current
           DESCRIPTION "The authoritative identifier for the Intel
                       82557 Fast Ethernet PCI Bus Lan Controller."
           ::= { dot3ChipSetIntel 4 }

       dot3ChipSetIntel82558 OBJECT-IDENTITY
           STATUS      current
           DESCRIPTION "The authoritative identifier for the Intel
                       82558 Fast Ethernet PCI Bus LAN Controller with
                       Integrated PHY."
           ::= { dot3ChipSetIntel 5 }

       dot3ChipSetSeeq       OBJECT IDENTIFIER ::= { dot3ChipSets 3 }

       dot3ChipSetSeeq8003 OBJECT-IDENTITY
           STATUS      current
           DESCRIPTION "The authoritative identifier for the SEEQ
                       8003 chip set."
           ::= { dot3ChipSetSeeq 1 }

       dot3ChipSetSeeq80C03 OBJECT-IDENTITY
           STATUS      current
           DESCRIPTION "The authoritative identifier for the SEEQ
                       80C03 Full-Duplex CMOS Ethernet Data Link
                       Controller (MAC)."
           ::= { dot3ChipSetSeeq 2 }

       dot3ChipSetSeeq84C30 OBJECT-IDENTITY
           STATUS      current
           DESCRIPTION "The authoritative identifier for the SEEQ
                       4-Port 84C30 Full-Duplex CMOS Ethernet 10
                       MBit/Sec Data Link Controller (MAC)."
           ::= { dot3ChipSetSeeq 3 }

       dot3ChipSetSeeq8431 OBJECT-IDENTITY
           STATUS      current
           DESCRIPTION "The authoritative identifier for the SEEQ
                       4-Port 8431 Full-Duplex CMOS Ethernet 10
                       MBit/Sec Data Link Controller (MAC)."
           ::= { dot3ChipSetSeeq 4 }

       dot3ChipSetSeeq80C300 OBJECT-IDENTITY
           STATUS      current
           DESCRIPTION "The authoritative identifier for the SEEQ
                       80C300 Full-Duplex CMOS Ethernet 10/100
                       Mbit/Sec Data Link Controller (MAC)."
           ::= { dot3ChipSetSeeq 5 }

       dot3ChipSetSeeq84C300 OBJECT-IDENTITY
           STATUS      current
           DESCRIPTION "The authoritative identifier for the SEEQ
                       4-Port 84C300 Fast Ethernet Controller (MAC)."
           ::= { dot3ChipSetSeeq 6 }

       dot3ChipSetSeeq84301 OBJECT-IDENTITY
           STATUS      current
           DESCRIPTION "The authoritative identifier for the SEEQ
                       4-Port 84301 Fast Ethernet Controller (MAC)."
           ::= { dot3ChipSetSeeq 7 }

       dot3ChipSetSeeq84302 OBJECT-IDENTITY
           STATUS      current
           DESCRIPTION "The authoritative identifier for the SEEQ
                       4-Port 84302 Fast Ethernet Controller (MAC)."
           ::= { dot3ChipSetSeeq 8 }

       dot3ChipSetSeeq8100 OBJECT-IDENTITY
           STATUS      current
           DESCRIPTION "The authoritative identifier for the SEEQ
                       8100 Gigabit Ethernet Controller (MAC & PCS)."
           ::= { dot3ChipSetSeeq 9 }

       dot3ChipSetNational   OBJECT IDENTIFIER ::= { dot3ChipSets 4 }

       dot3ChipSetNational8390 OBJECT-IDENTITY
           STATUS      current
           DESCRIPTION "The authoritative identifier for the National
                       Semiconductor DP8390 Network Interface
                       Controller."
           ::= { dot3ChipSetNational 1 }

       dot3ChipSetNationalSonic OBJECT-IDENTITY
           STATUS      current
           DESCRIPTION "The authoritative identifier for the National
                       Semiconductor DP83932 Systems-Oriented Network
                       Interface Controller (SONIC)."
           ::= { dot3ChipSetNational 2 }

       dot3ChipSetNational83901 OBJECT-IDENTITY
           STATUS      current
           DESCRIPTION "The authoritative identifier for the National
                       Semiconductor DP83901 Serial Network Interface
                       Controller (SNIC)."
           ::= { dot3ChipSetNational 3 }

       dot3ChipSetNational83902 OBJECT-IDENTITY
           STATUS      current
           DESCRIPTION "The authoritative identifier for the National
                       Semiconductor DP83902 Serial Network Interface
                       Controller for Twisted Pair (ST-NIC)."
           ::= { dot3ChipSetNational 4 }

       dot3ChipSetNational83905 OBJECT-IDENTITY
           STATUS      current
           DESCRIPTION "The authoritative identifier for the National
                       Semiconductor DP83905 AT Local Area Network
                       Twisted-Pair Interface (AT/LANTIC)."
           ::= { dot3ChipSetNational 5 }

       dot3ChipSetNational83907 OBJECT-IDENTITY
           STATUS      current
           DESCRIPTION "The authoritative identifier for the National
                       Semiconductor DP83907 AT Twisted-Pair Enhanced
                       Coaxial Network Interface Controller
                       (AT/LANTIC II)."
           ::= { dot3ChipSetNational 6 }

       dot3ChipSetNational83916 OBJECT-IDENTITY
           STATUS      current
           DESCRIPTION "The authoritative identifier for the National
                       Semiconductor DP83916 Systems-Oriented Network
                       Interface Controller (SONIC-16)."
           ::= { dot3ChipSetNational 7 }

       dot3ChipSetNational83934 OBJECT-IDENTITY
           STATUS      current
           DESCRIPTION "The authoritative identifier for the National
                       Semiconductor DP83934 Systems-Oriented Network
                       Interface Controller with Twisted Pair Interface
                       (SONIC-T)."
           ::= { dot3ChipSetNational 8 }

       dot3ChipSetNational83936 OBJECT-IDENTITY
           STATUS      current
           DESCRIPTION "The authoritative identifier for the National
                       Semiconductor DP83936AVUL Full-Duplex Systems-
                       Oriented Network Interface Controller with
                       Twisted Pair Interface (SONIC-T)."
           ::= { dot3ChipSetNational 9 }

       dot3ChipSetFujitsu    OBJECT IDENTIFIER ::= { dot3ChipSets 5 }

       dot3ChipSetFujitsu86950 OBJECT-IDENTITY
           STATUS      current
           DESCRIPTION "The authoritative identifier for the Fujitsu
                       86950 chip."
           ::= { dot3ChipSetFujitsu 1 }

       dot3ChipSetFujitsu86960 OBJECT-IDENTITY
           STATUS      current
           DESCRIPTION "The authoritative identifier for the Fujitsu
                       MB86960 Network Interface Controller with
                       Encoder/Decoder (NICE)."
           ::= { dot3ChipSetFujitsu 2 }

       dot3ChipSetFujitsu86964 OBJECT-IDENTITY
           STATUS      current
           DESCRIPTION "The authoritative identifier for the Fujitsu
                       MB86964 Ethernet Controller with 10BASE-T
                       Tranceiver."
           ::= { dot3ChipSetFujitsu 3 }

       dot3ChipSetFujitsu86965A OBJECT-IDENTITY
           STATUS      current
           DESCRIPTION "The authoritative identifier for the Fujitsu
                       MB86965A EtherCoupler Single-Chip Ethernet
                       Controller."
           ::= { dot3ChipSetFujitsu 4 }

       dot3ChipSetFujitsu86965B OBJECT-IDENTITY
           STATUS      current
           DESCRIPTION "The authoritative identifier for the Fujitsu
                       MB86965B EtherCoupler Single-Chip Ethernet
                       Controller (supports full-duplex)."
           ::= { dot3ChipSetFujitsu 5 }

       dot3ChipSetDigital    OBJECT IDENTIFIER ::= { dot3ChipSets 6 }

       dot3ChipSetDigitalDC21040 OBJECT-IDENTITY
           STATUS      current
           DESCRIPTION "The authoritative identifier for the Digital
                       Semiconductor DC21040 chip."
           ::= { dot3ChipSetDigital 1 }

       dot3ChipSetDigital21041 OBJECT-IDENTITY
           STATUS      current
           DESCRIPTION "The authoritative identifier for the Digital
                       Semiconductor 21041 PCI Ethernet LAN
                       Controller."
           ::= { dot3ChipSetDigital 2 }

       dot3ChipSetDigital21140 OBJECT-IDENTITY
           STATUS      current
           DESCRIPTION "The authoritative identifier for the Digital
                       Semiconductor 21140 PCI Fast Ethernet LAN
                       Controller."
           ::= { dot3ChipSetDigital 3 }

       dot3ChipSetDigital21143 OBJECT-IDENTITY
           STATUS      current
           DESCRIPTION "The authoritative identifier for the Digital
                       Semiconductor 21143 PCI/CardBus 10/100-Mb/s
                       Ethernet LAN Controller."
           ::= { dot3ChipSetDigital 4 }

       dot3ChipSetDigital21340 OBJECT-IDENTITY
           STATUS      current
           DESCRIPTION "The authoritative identifier for the Digital
                       Semiconductor 21340 10/100-MB/s managed buffered
                       port switch."
           ::= { dot3ChipSetDigital 5 }

       dot3ChipSetDigital21440 OBJECT-IDENTITY
           STATUS      current
           DESCRIPTION "The authoritative identifier for the Digital
                       Semiconductor 21440 Multiport 10/100Mbps
                       Ethernet Controller."
           ::= { dot3ChipSetDigital 6 }

       dot3ChipSetDigital21540 OBJECT-IDENTITY
           STATUS      current
           DESCRIPTION "The authoritative identifier for the Digital
                       Semiconductor 21540 PCI/CardBus Ethernet LAN
                       Controller with Modem Interface."
           ::= { dot3ChipSetDigital 7 }

       dot3ChipSetTI         OBJECT IDENTIFIER ::= { dot3ChipSets 7 }

       dot3ChipSetTIE100 OBJECT-IDENTITY
           STATUS      current
           DESCRIPTION "The authoritative identifier for the Texas
                       Instruments TNETE100 ThunderLAN PCI Fast
                       Ethernet Controller."
           ::= { dot3ChipSetTI 1 }

       dot3ChipSetTIE110 OBJECT-IDENTITY
           STATUS      current
           DESCRIPTION "The authoritative identifier for the Texas
                       Instruments TNETE110 ThunderLAN PCI 10BASE-T
                       Ethernet Adapter."
           ::= { dot3ChipSetTI 2 }

       dot3ChipSetTIX3100 OBJECT-IDENTITY
           STATUS      current
           DESCRIPTION "The authoritative identifier for the Texas
                       Instruments TNETX3100 Desktop ThunderSWITCH
                       8/2."
           ::= { dot3ChipSetTI 3 }

       dot3ChipSetTIX3150 OBJECT-IDENTITY
           STATUS      current
           DESCRIPTION "The authoritative identifier for the Texas
                       Instruments TNETX3150 ThunderSWITCH 12/3."
           ::= { dot3ChipSetTI 4 }

       dot3ChipSetTIX3270 OBJECT-IDENTITY
           STATUS      current
           DESCRIPTION "The authoritative identifier for the Texas
                       Instruments TNETX3270 ThunderSWITCH 24/3."
           ::= { dot3ChipSetTI 5 }

       dot3ChipSetToshiba    OBJECT IDENTIFIER ::= { dot3ChipSets 8 }

       dot3ChipSetToshibaTC35815F OBJECT-IDENTITY
           STATUS      current
           DESCRIPTION "The authoritative identifier for the Toshiba
                       TC35815F PCI-Based 100/10Mbps Ethernet
                       Controller."
           ::= { dot3ChipSetToshiba 1 }

       dot3ChipSetLucent     OBJECT IDENTIFIER ::= { dot3ChipSets 9 }

       dot3ChipSetLucentATT1MX10 OBJECT-IDENTITY
           STATUS      current
           DESCRIPTION "The authoritative identifier for the Lucent
                       Technologies ATT1MX10 (Spinnaker) Quad MAC and
                       Tranceiver for Ethernet Frame Switching."
           ::= { dot3ChipSetLucent 1 }

       dot3ChipSetLucentLUC3M08 OBJECT-IDENTITY
           STATUS      current
           DESCRIPTION "The authoritative identifier for the Lucent
                       Technologies LUC3M08 Eight Ethernet MACs for
                       10/100 Mbits/s Frame Switching."
           ::= { dot3ChipSetLucent 2 }

       dot3ChipSetGalileo    OBJECT IDENTIFIER ::= { dot3ChipSets 10 }

       dot3ChipSetGalileoGT48001 OBJECT-IDENTITY
           STATUS      current
           DESCRIPTION "The authoritative identifier for the Galileo
                       Technology GT-48001A Switched Ethernet
                       Controller."
           ::= { dot3ChipSetGalileo 1 }

       dot3ChipSetGalileoGT48002 OBJECT-IDENTITY
           STATUS      current
           DESCRIPTION "The authoritative identifier for the Galileo
                       Technology GT-48002A Switched Fast Ethernet
                       Controller."
           ::= { dot3ChipSetGalileo 2 }

       dot3ChipSetGalileoGT48004 OBJECT-IDENTITY
           STATUS      current
           DESCRIPTION "The authoritative identifier for the Galileo
                       Technology GT-48004A Four Port Fast Ethernet
                       Switch for Multiport 10/100BASE-X Systems."
           ::= { dot3ChipSetGalileo 3 }

       dot3ChipSetGalileoGT48207 OBJECT-IDENTITY
           STATUS      current
           DESCRIPTION "The authoritative identifier for the Galileo
                       Technology GT-48207 Low-Cost 10 Port Switched
                       Ethernet Controller for 10+10/100BASE-X."
           ::= { dot3ChipSetGalileo 4 }

       dot3ChipSetGalileoGT48208 OBJECT-IDENTITY
           STATUS      current
           DESCRIPTION "The authoritative identifier for the Galileo
                       Technology GT-48208 Advanced 10 Port Switched
                       Ethernet Controller for 10+10/100BASE-X."
           ::= { dot3ChipSetGalileo 5 }

       dot3ChipSetGalileoGT48212 OBJECT-IDENTITY
           STATUS      current
           DESCRIPTION "The authoritative identifier for the Galileo
                       Technology GT-48212 Advanced 14 Port Switched
                       Ethernet Controller for 10+10/100BASE-X."
           ::= { dot3ChipSetGalileo 6 }

       dot3ChipSetJato       OBJECT IDENTIFIER ::= { dot3ChipSets 11 }

       dot3ChipSetJatoJT1001 OBJECT-IDENTITY
           STATUS      current
           DESCRIPTION "The authoritative identifier for the Jato
                       Technologies JT1001 GigEMAC Server
                       10/100/1000Mbps Ethernet Controller with PCI
                       interface."
           ::= { dot3ChipSetJato 1 }

       dot3ChipSetXaQti      OBJECT IDENTIFIER ::= { dot3ChipSets 12 }

       dot3ChipSetXaQtiXQ11800FP OBJECT-IDENTITY
           STATUS      current
           DESCRIPTION "The authoritative identifier for the XaQTI
                       XQ11800FP XMAC II Gigabit Ethernet Media Access
                       Controller."
           ::= { dot3ChipSetXaQti 1 }

       dot3ChipSetXaQtiXQ18110FP OBJECT-IDENTITY
           STATUS      current
           DESCRIPTION "The authoritative identifier for the XaQTI
                       XQ18110FP GigaPower Protocol Accelerator."
           ::= { dot3ChipSetXaQti 2 }

       -- For those chipsets not represented above, OBJECT IDENTIFIER
       -- assignment is required in other documentation, e.g.,
       -- assignment within that part of the registration tree
       -- delegated to individual enterprises (see RFC 1155 and
       -- RFC 1902).
       --
       -- In the future, management of chipset registrations may be
       -- delegated to the Internet Assigned Numbers Authority (IANA).

       -- conformance information

       etherConformance OBJECT IDENTIFIER ::= { etherMIB 2 }

       etherGroups      OBJECT IDENTIFIER ::= { etherConformance 1 }
       etherCompliances OBJECT IDENTIFIER ::= { etherConformance 2 }

       -- compliance statements

       etherCompliance MODULE-COMPLIANCE
           STATUS      current
           DESCRIPTION "The compliance statement for managed network
                       entities which have ethernet-like network
                       interfaces."

           MODULE  -- this module
               MANDATORY-GROUPS { etherStatsGroup }

               GROUP       etherCollisionTableGroup
               DESCRIPTION "This group is optional. It is appropriate
                           for all systems which have the necessary
                           metering. Implementation in such systems is
                           highly recommended."
           ::= { etherCompliances 1 }

       ether100MbsCompliance MODULE-COMPLIANCE
           STATUS      current
           DESCRIPTION "The compliance statement for managed network
                       entities which have 100 Mb/sec ethernet-like
                       network interfaces."

           MODULE  -- this module
               MANDATORY-GROUPS { etherStats100MbsGroup }

               GROUP       etherCollisionTableGroup
               DESCRIPTION "This group is optional. It is appropriate
                           for all systems which have the necessary
                           metering. Implementation in such systems is
                           highly recommended."
           ::= { etherCompliances 2 }

       -- units of conformance

       etherStatsGroup OBJECT-GROUP
           OBJECTS     { dot3StatsIndex,
                         dot3StatsAlignmentErrors,
                         dot3StatsFCSErrors,
                         dot3StatsSingleCollisionFrames,
                         dot3StatsMultipleCollisionFrames,
                         dot3StatsSQETestErrors,
                         dot3StatsDeferredTransmissions,
                         dot3StatsLateCollisions,
                         dot3StatsExcessiveCollisions,
                         dot3StatsInternalMacTransmitErrors,
                         dot3StatsCarrierSenseErrors,
                         dot3StatsFrameTooLongs,
                         dot3StatsInternalMacReceiveErrors,
                         dot3StatsEtherChipSet
                       }
           STATUS      current
           DESCRIPTION "A collection of objects providing information
                       applicable to all ethernet-like network
                       interfaces."
           ::= { etherGroups 1 }

       etherCollisionTableGroup OBJECT-GROUP
           OBJECTS     { dot3CollFrequencies
                       }
           STATUS      current
           DESCRIPTION "A collection of objects providing a histogram
                       of packets successfully transmitted after
                       experiencing exactly N collisions."
           ::= { etherGroups 2 }

       etherStats100MbsGroup OBJECT-GROUP
           OBJECTS     { dot3StatsIndex,
                         dot3StatsAlignmentErrors,
                         dot3StatsFCSErrors,
                         dot3StatsSingleCollisionFrames,
                         dot3StatsMultipleCollisionFrames,
                         dot3StatsDeferredTransmissions,
                         dot3StatsLateCollisions,
                         dot3StatsExcessiveCollisions,
                         dot3StatsInternalMacTransmitErrors,
                         dot3StatsCarrierSenseErrors,
                         dot3StatsFrameTooLongs,
                         dot3StatsInternalMacReceiveErrors,
                         dot3StatsEtherChipSet,
                         dot3StatsSymbolErrors
                       }
           STATUS      current
           DESCRIPTION "A collection of objects providing information
                       applicable to 100 Mb/sec ethernet-like network
                       interfaces."
           ::= { etherGroups 3 }

END
