-- automatically generated by mosy 7.1 #1 (hprnljf), do not edit!

HP-ICF-LINKTEST DEFINITIONS ::= BEGIN


IMPORTS
	OBJECT-TYPE
		FROM RFC-1212
	hpicfCommon, hpicfObjectModules
		FROM HP-ICF-OID
	OwnerString
		FROM IF-MIB
	TimeInterval, RowStatus
		FROM SNMPv2-TC;
-- created from hpicfLinkTestMib (9703060338Z)

hpicfLinkTestMib OBJECT IDENTIFIER ::= { hpicfObjectModules  7 }

hpicfLinktest OBJECT IDENTIFIER ::= { hpicfCommon  6 }

hpicfLinkTestNextIndex OBJECT-TYPE
    SYNTAX  INTEGER (0..65535)
    ACCESS  read-write
    STATUS  mandatory
    DESCRIPTION
           "A currently unassigned value of hpicfLinkTestIndex.
                   The value 0 indicates that no unassigned values are
                   available.

                   In order to cause a non-zero value of this object to
                   be assigned for use as the hpicfLinkTestIndex of a
                   future link test, it must be successfully modified by
                   a set operation.  When modified by a set operation,
                   the new value must precisely match the value
                   presently held by the object.  If not, the management
                   protocol set operation will fail.

                   Immediately after the completion of a successful set
                   operation, the agent must modify the value of this
                   object.  The algorithm for modifying the value is
                   implementation-dependent, and may use a subset of
                   values within the legal range.  However, the agent
                   must guarantee that the new value is not assigned to
                   any in-use value of hpicfLinkTestIndex.

                   A management station creates a new link test using
                   this algorithm:

                      - issue a management protocol retrieval operation
                        to obtain the value of hpicfLinkTestNextIndex;
                        if the retrieved value is zero, a new link test
                        cannot be created at this time;

                      - issue a management protocol set operation for
                        hpicfLinkTestNextIndex, supplying the same value
                        as obtained in the previous step;

                      - if the set operation succeeds, use the supplied
                        value as the hpicfLinkTestIndex of the new
                        link test; if the set operation fails, go back
                        to the first step and obtain a new value for
                        hpicfLinkTestNextIndex;

                      - issue a management protocol set operation to
                        create an instance of the hpicfLinkTestStatus
                        object setting its value to 'createAndGo' or
                        'createAndWait' (as specified in the description
                        of the RowStatus textual convention).

                    Note that the set of hpicfLinkTestNextIndex and the
                    instance of hpicfLinkTestStatus may occur in the
                    same set operation if desired."
    ::= { hpicfLinktest  1 }

hpicfLinkTestTable OBJECT-TYPE
    SYNTAX  SEQUENCE OF HpicfLinkTestEntry
    ACCESS  not-accessible
    STATUS  mandatory
    DESCRIPTION
           "A table of in-progress link tests."
    ::= { hpicfLinktest  2 }

hpicfLinkTestEntry OBJECT-TYPE
    SYNTAX  HpicfLinkTestEntry
    ACCESS  not-accessible
    STATUS  mandatory
    DESCRIPTION
           "A row in the table, containing information about a
                   single link test."
    INDEX   { hpicfLinkTestIndex }
    ::= { hpicfLinkTestTable  1 }

HpicfLinkTestEntry ::=
    SEQUENCE {
    hpicfLinkTestIndex
        INTEGER,

    hpicfLinkTestType
        INTEGER,

    hpicfLinkTestAddress
        OCTET STRING,

    hpicfLinkTestIfIndex
        INTEGER,

    hpicfLinkTestTimeout
        TimeInterval,

    hpicfLinkTestRepetitions
        INTEGER,

    hpicfLinkTestAttempts
        INTEGER,

    hpicfLinkTestSuccesses
        INTEGER,

    hpicfLinkTestMinRespTime
        INTEGER,

    hpicfLinkTestMaxRespTime
        INTEGER,

    hpicfLinkTestTotalRespTime
        INTEGER,

    hpicfLinkTestOwner
        OwnerString,

    hpicfLinkTestStatus
        RowStatus,

    hpicfLinkTestDeleteMode
        INTEGER
    }

hpicfLinkTestIndex OBJECT-TYPE
    SYNTAX  INTEGER (1..65535)
    ACCESS  not-accessible
    STATUS  mandatory
    DESCRIPTION
           "The value of this object uniquely identifies this
                   link test."
    ::= { hpicfLinkTestEntry  1 }

hpicfLinkTestType OBJECT-TYPE
    SYNTAX  INTEGER {
                 icmpEcho(1),
                 ieee8022Test(2),
                 ipxDiagnostic(3)
               }
    ACCESS  read-write
    STATUS  mandatory
    DESCRIPTION
           "The type of test to run."
    ::= { hpicfLinkTestEntry  2 }

hpicfLinkTestAddress OBJECT-TYPE
    SYNTAX  OCTET STRING (SIZE(4|6|10))
    ACCESS  read-write
    STATUS  mandatory
    DESCRIPTION
           "The destination address used for sending link test
                   packets, formatted according to the value of the
                   corresponding instance of hpicfLinkTestType.  When
                   hpicfLinkTestType is equal to 'icmpEcho', this object
                   will be four octets long, and contain an IP address
                   in network byte order.  When hpicfLinkTestType is
                   equal to 'ieee8022Test', this object will be six
                   octets long, and contain an IEEE MAC address in
                   canonical order.  When hpicfLinkTestType is equal to
                   'ipxDiagnostic', this object will be ten octets long,
                   and will contain the IPX network number in network
                   byte order, followed by the IPX node number in
                   network byte order."
    ::= { hpicfLinkTestEntry  3 }

hpicfLinkTestIfIndex OBJECT-TYPE
    SYNTAX  INTEGER
    ACCESS  read-write
    STATUS  mandatory
    DESCRIPTION
           "The local interface to send the link test packets
                   on.  The value of this object must correspond to an
                   ifIndex value for an interface capable of supporting
                   the requested link test.  The value 0 is used to
                   indicate that the agent should determine the
                   interface using local routing information."
    DEFVAL  { 0 }
    ::= { hpicfLinkTestEntry  4 }

hpicfLinkTestTimeout OBJECT-TYPE
    SYNTAX  TimeInterval
    ACCESS  read-write
    STATUS  mandatory
    DESCRIPTION
           "The time interval over which a link test response
                   must be recieved, or the test is counted as failed."
    DEFVAL  { 100 }
    ::= { hpicfLinkTestEntry  5 }

hpicfLinkTestRepetitions OBJECT-TYPE
    SYNTAX  INTEGER (1..65535)
    ACCESS  read-write
    STATUS  mandatory
    DESCRIPTION
           "The total number of times that the agent should
                   send link test packets to the destination host."
    DEFVAL  { 1 }
    ::= { hpicfLinkTestEntry  6 }

hpicfLinkTestAttempts OBJECT-TYPE
    SYNTAX  INTEGER (0..65535)
    ACCESS  read-only
    STATUS  mandatory
    DESCRIPTION
           "The number of times we have sent link test packets
                   to the destination during the current test.  This
                   object will start at zero when the corresponding
                   instance of hpicfLinkTestStatus is set to 'active'.
                   It will increment at the completion of each iteration
                   of the test until either it reaches the value of
                   hpicfLinkTestRepetitions, or the corresponding
                   instance of hpicfLinkTestStatus is set to a value
                   other than 'active'.  Note that it is incremented
                   at the completion of each iteration, not when the
                   link test packet is sent, so that the number of
                   failures can be calculated accurately."
    ::= { hpicfLinkTestEntry  7 }

hpicfLinkTestSuccesses OBJECT-TYPE
    SYNTAX  INTEGER (0..65535)
    ACCESS  read-only
    STATUS  mandatory
    DESCRIPTION
           "The number of times that we have received a response
                   to a link test packet during the current test.  This
                   object will start at zero when the corresponding
                   instance of hpicfLinkTestStatus is set to 'active'.
                   It will increment each time the agent receives a
                   response from the destination of this test.  Note
                   that the number of failed attempts is given by
                   hpicfLinkTestAttempts - hpicfLinkTestSuccesses."
    ::= { hpicfLinkTestEntry  8 }

hpicfLinkTestMinRespTime OBJECT-TYPE
    SYNTAX  INTEGER
    ACCESS  read-only
    STATUS  mandatory
    DESCRIPTION
           "The shortest time (in milliseconds) between request
                   and response for all of the link tests that have been
                   attempted as part of this test."
    ::= { hpicfLinkTestEntry  9 }

hpicfLinkTestMaxRespTime OBJECT-TYPE
    SYNTAX  INTEGER
    ACCESS  read-only
    STATUS  mandatory
    DESCRIPTION
           "The longest time (in milliseconds) between request
                   and response for all of the link tests that have been
                   attempted as part of this test."
    ::= { hpicfLinkTestEntry  10 }

hpicfLinkTestTotalRespTime OBJECT-TYPE
    SYNTAX  INTEGER
    ACCESS  read-only
    STATUS  mandatory
    DESCRIPTION
           "The sum of all of the response times (in
                   milliseconds) for all of the link tests that have
                   been attempted as part of this test.  This value can
                   be used in conjunction with hpicfLinkTestSuccesses
                   to calculate the average response time."
    ::= { hpicfLinkTestEntry  11 }

hpicfLinkTestOwner OBJECT-TYPE
    SYNTAX  OwnerString
    ACCESS  read-write
    STATUS  mandatory
    DESCRIPTION
           "The entity that configured this test and is
                   therefore using the resources assigned to it."
    ::= { hpicfLinkTestEntry  12 }

hpicfLinkTestStatus OBJECT-TYPE
    SYNTAX  RowStatus
    ACCESS  read-write
    STATUS  mandatory
    DESCRIPTION
           "The status of this entry."
    ::= { hpicfLinkTestEntry  13 }

hpicfLinkTestDeleteMode OBJECT-TYPE
    SYNTAX  INTEGER {
                 keepWhenDone(1),
                 destroyWhenDone(2)
               }
    ACCESS  read-write
    STATUS  mandatory
    DESCRIPTION
           "When the value of this object is 'keepWhenDone',
                   the associated instance of the hpicfLinkTestStatus
                   object will be changed to 'notInService' upon
                   completion of the test.  It will then be timed out
                   by the agent after 5 minutes in the 'notInService'
                   state.

                   When the value of this object is 'destroyWhenDone',
                   the assocated instance of the hpicfLinkTestStatus
                   object will be changed to 'destroy' upon completion
                   of the test.  This will remove the row from the
                   table immediately after the test completes."
    DEFVAL  { keepWhenDone }
    ::= { hpicfLinkTestEntry  14 }

hpicfLinkTestConformance OBJECT IDENTIFIER ::= { hpicfLinkTestMib  1 }

hpicfLinkTestCompliances OBJECT IDENTIFIER ::= { hpicfLinkTestConformance  1 }

hpicfLinkTestGroups OBJECT IDENTIFIER ::= { hpicfLinkTestConformance  2 }

hpicfLinkTestCompliance OBJECT IDENTIFIER ::= { hpicfLinkTestCompliances  1 }

hpicfLinkTestCompliance2 OBJECT IDENTIFIER ::= { hpicfLinkTestCompliances  2 }

hpicfLinkTestGroup OBJECT IDENTIFIER ::= { hpicfLinkTestGroups  1 }

hpicfLinkTestGroup2 OBJECT IDENTIFIER ::= { hpicfLinkTestGroups  2 }

END
