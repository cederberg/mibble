-- automatically generated by mosy 7.1 #1 (hprnljf), do not edit!

HP-ICF-STACK DEFINITIONS ::= BEGIN


IMPORTS
	OBJECT-TYPE
		FROM RFC-1212
        DisplayString, TruthValue
		FROM SNMPv2-TC
	hpicfCommon, hpicfObjectModules
		FROM HP-ICF-OID
	entPhysicalIndex
		FROM ENTITY-MIB;
-- created from hpicfStackMib (9609062228Z)

hpicfStackMib OBJECT IDENTIFIER ::= { hpicfObjectModules  6 }

hpicfStack OBJECT IDENTIFIER ::= { hpicfCommon  5 }

hpicfStackBoxTable OBJECT-TYPE
    SYNTAX  SEQUENCE OF HpicfStackBoxEntry
    ACCESS  not-accessible
    STATUS  mandatory
    DESCRIPTION
           "This table contains a list of physical boxes
                   currently in the stack."
    ::= { hpicfStack  1 }

hpicfStackBoxEntry OBJECT-TYPE
    SYNTAX  HpicfStackBoxEntry
    ACCESS  not-accessible
    STATUS  mandatory
    DESCRIPTION
           "An entry containing information about a physical
                   box in the stack.  This table is indexed by
                   the value of entPhysicalIndex that corresponds to
                   the row in the entPhysicalTable for this box."
    INDEX   { entPhysicalIndex }
    ::= { hpicfStackBoxTable  1 }

HpicfStackBoxEntry ::=
    SEQUENCE {
    hpicfStackBoxId
        OCTET STRING,

    hpicfStackBoxName
        DisplayString
    }

hpicfStackBoxId OBJECT-TYPE
    SYNTAX  OCTET STRING (SIZE(5))
    ACCESS  read-only
    STATUS  mandatory
    DESCRIPTION
           "The box identifier that uniquely identifies this
                   physical box.  The value of this object is the serial
                   number of the box."
    ::= { hpicfStackBoxEntry  1 }

hpicfStackBoxName OBJECT-TYPE
    SYNTAX  DisplayString (SIZE(0..16))
    ACCESS  read-write
    STATUS  mandatory
    DESCRIPTION
           "A settable name for this box.  This name defaults
                   to an ASCII representation of the base MAC address
                   of the box, but may be set to a user-friendly
                   display string by a management application."
    ::= { hpicfStackBoxEntry  2 }

hpicfStackAgentTable OBJECT-TYPE
    SYNTAX  SEQUENCE OF HpicfStackAgentEntry
    ACCESS  not-accessible
    STATUS  mandatory
    DESCRIPTION
           "This table provides a list of SNMP agent cards in
                   the stack that are capable of managing the stack.
                   Note that this table is redundant, since this
                   information is available in the Entity MIB, but is
                   provided for the convenience of management
                   applications, so that they are not required to scan
                   the entire entPhysicalTable to determine what agent
                   cards are present."
    ::= { hpicfStack  2 }

hpicfStackAgentEntry OBJECT-TYPE
    SYNTAX  HpicfStackAgentEntry
    ACCESS  not-accessible
    STATUS  mandatory
    DESCRIPTION
           "An entry in the hpicfStackAgentTable representing
                   a single agent card.  This table is indexed by
                   the value of entPhysicalIndex that corresponds to
                   the row in the entPhysicalTable for this agent
                   card."
    INDEX   { entPhysicalIndex }
    ::= { hpicfStackAgentTable  1 }

HpicfStackAgentEntry ::=
    SEQUENCE {
    hpicfStackAgentBoxId
        OCTET STRING
    }

hpicfStackAgentBoxId OBJECT-TYPE
    SYNTAX  OCTET STRING (SIZE(5))
    ACCESS  read-only
    STATUS  mandatory
    DESCRIPTION
           "The value of hpicfStackBoxId for the box containing
                   this agent card.  Note that this object is redundant
                   since containment information is available in the
                   Entity MIB, but is provided for the convenience of
                   manament applications (and so that there would be at
                   least one accessible column in this table)."
    ::= { hpicfStackAgentEntry  1 }

hpicfStackActiveAgent OBJECT-TYPE
    SYNTAX  INTEGER (1..2147483647)
    ACCESS  read-write
    STATUS  mandatory
    DESCRIPTION
           "The value of entPhysicalIndex for the agent that is
                   currently managing this stack.  A set to this value
                   will also set hpicfStackAgentForced to 'true'.  Note
                   that setting this object to a value different from
                   the current value will cause this agent to reset.
                   After reset, the current agent will no longer be
                   active, because the new agent will take over."
    ::= { hpicfStack  3 }

hpicfStackAgentForced OBJECT-TYPE
    SYNTAX  TruthValue
    ACCESS  read-only
    STATUS  mandatory
    DESCRIPTION
           "A value of 'true' indicates that the current active
                   agent card has been chosen by a management action as
                   the active agent.  This management action may have
                   been performed through a console user interface
                   command, or by setting the hpicfStackActiveAgent
                   object.  The reason for this is to allow the network
                   administrator to prevent an added redundant agent
                   from taking over when there is a configured agent
                   card in the stack."
    ::= { hpicfStack  4 }

hpicfStackConformance OBJECT IDENTIFIER ::= { hpicfStackMib  1 }

hpicfStackCompliances OBJECT IDENTIFIER ::= { hpicfStackConformance  1 }

hpicfStackGroups OBJECT IDENTIFIER ::= { hpicfStackConformance  2 }

hpicfStackCompliance OBJECT IDENTIFIER ::= { hpicfStackCompliances  1 }

hpicfStackBasicGroup OBJECT IDENTIFIER ::= { hpicfStackGroups  1 }

hpicfStackMultiAgentGroup OBJECT IDENTIFIER ::= { hpicfStackGroups  2 }

END
