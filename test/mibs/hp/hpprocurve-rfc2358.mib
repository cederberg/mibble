-- automatically generated by mosy 7.1 #1 (hprnljf), do not edit!

EtherLike-MIB DEFINITIONS ::= BEGIN


IMPORTS
	Counter
		FROM RFC1155-SMI
        OBJECT-TYPE
		FROM RFC-1212
	InterfaceIndex, ifIndex
		FROM IF-MIB
	transmission, mib-2
		FROM SNMPv2-SMI;
-- created from etherMIB (9806032150Z)

etherMIB OBJECT IDENTIFIER ::= { mib-2  35 }

etherMIBObjects OBJECT IDENTIFIER ::= { etherMIB  1 }

dot3 OBJECT IDENTIFIER ::= { transmission  7 }

dot3StatsTable OBJECT-TYPE
    SYNTAX  SEQUENCE OF Dot3StatsEntry
    ACCESS  not-accessible
    STATUS  mandatory
    DESCRIPTION
           "Statistics for a collection of ethernet-like
                       interfaces attached to a particular system."
    ::= { dot3  2 }

dot3StatsEntry OBJECT-TYPE
    SYNTAX  Dot3StatsEntry
    ACCESS  not-accessible
    STATUS  mandatory
    DESCRIPTION
           "Statistics for a particular interface to an
                       ethernet-like medium."
    INDEX   { dot3StatsIndex }
    ::= { dot3StatsTable  1 }

Dot3StatsEntry ::=
    SEQUENCE {
    dot3StatsIndex
        InterfaceIndex,

    dot3StatsAlignmentErrors
        Counter,

    dot3StatsFCSErrors
        Counter,

    dot3StatsSingleCollisionFrames
        Counter,

    dot3StatsMultipleCollisionFrames
        Counter,

    dot3StatsSQETestErrors
        Counter,

    dot3StatsDeferredTransmissions
        Counter,

    dot3StatsLateCollisions
        Counter,

    dot3StatsExcessiveCollisions
        Counter,

    dot3StatsInternalMacTransmitErrors
        Counter,

    dot3StatsCarrierSenseErrors
        Counter,

    dot3StatsFrameTooLongs
        Counter,

    dot3StatsInternalMacReceiveErrors
        Counter,

    dot3StatsEtherChipSet
        OBJECT IDENTIFIER,

    dot3StatsSymbolErrors
        Counter
    }

dot3StatsIndex OBJECT-TYPE
    SYNTAX  InterfaceIndex
    ACCESS  read-only
    STATUS  mandatory
    DESCRIPTION
           "An index value that uniquely identifies an
                       interface to an ethernet-like medium.  The
                       interface identified by a particular value of
                       this index is the same interface as identified
                       by the same value of ifIndex."
    ::= { dot3StatsEntry  1 }

dot3StatsAlignmentErrors OBJECT-TYPE
    SYNTAX  Counter
    ACCESS  read-only
    STATUS  mandatory
    DESCRIPTION
           "A count of frames received on a particular
                       interface that are not an integral number of
                       octets in length and do not pass the FCS check.

                       The count represented by an instance of this
                       object is incremented when the alignmentError
                       status is returned by the MAC service to the
                       LLC (or other MAC user). Received frames for
                       which multiple error conditions obtain are,
                       according to the conventions of IEEE 802.3
                       Layer Management, counted exclusively according
                       to the error status presented to the LLC."
    REFERENCE
           "IEEE 802.3 Layer Management"
    ::= { dot3StatsEntry  2 }

dot3StatsFCSErrors OBJECT-TYPE
    SYNTAX  Counter
    ACCESS  read-only
    STATUS  mandatory
    DESCRIPTION
           "A count of frames received on a particular
                       interface that are an integral number of octets
                       in length but do not pass the FCS check.

                       The count represented by an instance of this
                       object is incremented when the frameCheckError
                       status is returned by the MAC service to the
                       LLC (or other MAC user). Received frames for
                       which multiple error conditions obtain are,
                       according to the conventions of IEEE 802.3
                       Layer Management, counted exclusively according
                       to the error status presented to the LLC."
    REFERENCE
           "IEEE 802.3 Layer Management"
    ::= { dot3StatsEntry  3 }

dot3StatsSingleCollisionFrames OBJECT-TYPE
    SYNTAX  Counter
    ACCESS  read-only
    STATUS  mandatory
    DESCRIPTION
           "A count of successfully transmitted frames on
                       a particular interface for which transmission
                       is inhibited by exactly one collision.

                       A frame that is counted by an instance of this
                       object is also counted by the corresponding
                       instance of either the ifOutUcastPkts,
                       ifOutMulticastPkts, or ifOutBroadcastPkts,
                       and is not counted by the corresponding
                       instance of the dot3StatsMultipleCollisionFrames
                       object."
    REFERENCE
           "IEEE 802.3 Layer Management"
    ::= { dot3StatsEntry  4 }

dot3StatsMultipleCollisionFrames OBJECT-TYPE
    SYNTAX  Counter
    ACCESS  read-only
    STATUS  mandatory
    DESCRIPTION
           "A count of successfully transmitted frames on
                       a particular interface for which transmission
                       is inhibited by more than one collision.

                       A frame that is counted by an instance of this
                       object is also counted by the corresponding
                       instance of either the ifOutUcastPkts,
                       ifOutMulticastPkts, or ifOutBroadcastPkts,
                       and is not counted by the corresponding
                       instance of the dot3StatsSingleCollisionFrames
                       object."
    REFERENCE
           "IEEE 802.3 Layer Management"
    ::= { dot3StatsEntry  5 }

dot3StatsSQETestErrors OBJECT-TYPE
    SYNTAX  Counter
    ACCESS  read-only
    STATUS  mandatory
    DESCRIPTION
           "A count of times that the SQE TEST ERROR
                       message is generated by the PLS sublayer for a
                       particular interface. The SQE TEST ERROR
                       message is defined in section 7.2.2.2.4 of
                       ANSI/IEEE 802.3-1985 and its generation is
                       described in section 7.2.4.6 of the same
                       document."
    REFERENCE
           "ANSI/IEEE Std 802.3-1985 Carrier Sense
                       Multiple Access with Collision Detection Access
                       Method and Physical Layer Specifications"
    ::= { dot3StatsEntry  6 }

dot3StatsDeferredTransmissions OBJECT-TYPE
    SYNTAX  Counter
    ACCESS  read-only
    STATUS  mandatory
    DESCRIPTION
           "A count of frames for which the first
                       transmission attempt on a particular interface
                       is delayed because the medium is busy.

                       The count represented by an instance of this
                       object does not include frames involved in
                       collisions."
    REFERENCE
           "IEEE 802.3 Layer Management"
    ::= { dot3StatsEntry  7 }

dot3StatsLateCollisions OBJECT-TYPE
    SYNTAX  Counter
    ACCESS  read-only
    STATUS  mandatory
    DESCRIPTION
           "The number of times that a collision is
                       detected on a particular interface later than
                       512 bit-times into the transmission of a
                       packet.

                       Five hundred and twelve bit-times corresponds
                       to 51.2 microseconds on a 10 Mbit/s system. A
                       (late) collision included in a count
                       represented by an instance of this object is
                       also considered as a (generic) collision for
                       purposes of other collision-related
                       statistics."
    REFERENCE
           "IEEE 802.3 Layer Management"
    ::= { dot3StatsEntry  8 }

dot3StatsExcessiveCollisions OBJECT-TYPE
    SYNTAX  Counter
    ACCESS  read-only
    STATUS  mandatory
    DESCRIPTION
           "A count of frames for which transmission on a
                       particular interface fails due to excessive
                       collisions."
    REFERENCE
           "IEEE 802.3 Layer Management"
    ::= { dot3StatsEntry  9 }

dot3StatsInternalMacTransmitErrors OBJECT-TYPE
    SYNTAX  Counter
    ACCESS  read-only
    STATUS  mandatory
    DESCRIPTION
           "A count of frames for which transmission on a
                       particular interface fails due to an internal
                       MAC sublayer transmit error. A frame is only
                       counted by an instance of this object if it is
                       not counted by the corresponding instance of
                       either the dot3StatsLateCollisions object, the
                       dot3StatsExcessiveCollisions object, or the
                       dot3StatsCarrierSenseErrors object.

                       The precise meaning of the count represented by
                       an instance of this object is implementation-
                       specific.  In particular, an instance of this
                       object may represent a count of transmission
                       errors on a particular interface that are not
                       otherwise counted."
    REFERENCE
           "IEEE 802.3 Layer Management"
    ::= { dot3StatsEntry  10 }

dot3StatsCarrierSenseErrors OBJECT-TYPE
    SYNTAX  Counter
    ACCESS  read-only
    STATUS  mandatory
    DESCRIPTION
           "The number of times that the carrier sense
                       condition was lost or never asserted when
                       attempting to transmit a frame on a particular
                       interface.

                       The count represented by an instance of this
                       object is incremented at most once per
                       transmission attempt, even if the carrier sense
                       condition fluctuates during a transmission
                       attempt."
    REFERENCE
           "IEEE 802.3 Layer Management"
    ::= { dot3StatsEntry  11 }

dot3StatsFrameTooLongs OBJECT-TYPE
    SYNTAX  Counter
    ACCESS  read-only
    STATUS  mandatory
    DESCRIPTION
           "A count of frames received on a particular
                       interface that exceed the maximum permitted
                       frame size.

                       The count represented by an instance of this
                       object is incremented when the frameTooLong
                       status is returned by the MAC service to the
                       LLC (or other MAC user). Received frames for
                       which multiple error conditions obtain are,
                       according to the conventions of IEEE 802.3
                       Layer Management, counted exclusively according
                       to the error status presented to the LLC."
    REFERENCE
           "IEEE 802.3 Layer Management"
    ::= { dot3StatsEntry  13 }

dot3StatsInternalMacReceiveErrors OBJECT-TYPE
    SYNTAX  Counter
    ACCESS  read-only
    STATUS  mandatory
    DESCRIPTION
           "A count of frames for which reception on a
                       particular interface fails due to an internal
                       MAC sublayer receive error. A frame is only
                       counted by an instance of this object if it is
                       not counted by the corresponding instance of
                       either the dot3StatsFrameTooLongs object, the
                       dot3StatsAlignmentErrors object, or the
                       dot3StatsFCSErrors object.
                       The precise meaning of the count represented by
                       an instance of this object is implementation-
                       specific.  In particular, an instance of this
                       object may represent a count of receive errors
                       on a particular interface that are not
                       otherwise counted."
    REFERENCE
           "IEEE 802.3 Layer Management"
    ::= { dot3StatsEntry  16 }

dot3StatsEtherChipSet OBJECT-TYPE
    SYNTAX  OBJECT IDENTIFIER
    ACCESS  read-only
    STATUS  mandatory
    DESCRIPTION
           "This object contains an OBJECT IDENTIFIER
                       which identifies the chipset used to
                       realize the interface. Ethernet-like
                       interfaces are typically built out of
                       several different chips. The MIB implementor
                       is presented with a decision of which chip
                       to identify via this object. The implementor
                       should identify the chip which is usually
                       called the Medium Access Control chip.
                       If no such chip is easily identifiable,
                       the implementor should identify the chip
                       which actually gathers the transmit
                       and receive statistics and error
                       indications. This would allow a
                       manager station to correlate the
                       statistics and the chip generating
                       them, giving it the ability to take
                       into account any known anomalies
                       in the chip."
    ::= { dot3StatsEntry  17 }

dot3StatsSymbolErrors OBJECT-TYPE
    SYNTAX  Counter
    ACCESS  read-only
    STATUS  mandatory
    DESCRIPTION
           "The number of times there was an invalid data
                       symbol when a valid carrier was present on a
                       particular interface.

                       The count represented by an instance of this
                       object is incremented at most once per carrier
                       event, even if multiple symbol errors occur
                       during the carrier event."
    REFERENCE
           "IEEE 802.3u-1995 10 & 100 Mb/s Management"
    ::= { dot3StatsEntry  18 }

dot3CollTable OBJECT-TYPE
    SYNTAX  SEQUENCE OF Dot3CollEntry
    ACCESS  not-accessible
    STATUS  mandatory
    DESCRIPTION
           "A collection of collision histograms for a
                       particular set of interfaces."
    ::= { dot3  5 }

dot3CollEntry OBJECT-TYPE
    SYNTAX  Dot3CollEntry
    ACCESS  not-accessible
    STATUS  mandatory
    DESCRIPTION
           "A cell in the histogram of per-frame
                       collisions for a particular interface.  An
                       instance of this object represents the
                       frequency of individual MAC frames for which
                       the transmission (successful or otherwise) on a
                       particular interface is accompanied by a
                       particular number of media collisions."
    INDEX   { ifIndex,  dot3CollCount }
    ::= { dot3CollTable  1 }

Dot3CollEntry ::=
    SEQUENCE {
    dot3CollCount
        INTEGER,

    dot3CollFrequencies
        Counter
    }

dot3CollCount OBJECT-TYPE
    SYNTAX  INTEGER (1..16)
    ACCESS  not-accessible
    STATUS  mandatory
    DESCRIPTION
           "The number of per-frame media collisions for
                       which a particular collision histogram cell
                       represents the frequency on a particular
                       interface."
    ::= { dot3CollEntry  2 }

dot3CollFrequencies OBJECT-TYPE
    SYNTAX  Counter
    ACCESS  read-only
    STATUS  mandatory
    DESCRIPTION
           "A count of individual MAC frames for which the
                       transmission (successful or otherwise) on a
                       particular interface occurs after the
                       frame has experienced exactly the number
                       of collisions in the associated
                       dot3CollCount object.

                       For example, a frame which is transmitted
                       on interface 77 after experiencing
                       exactly 4 collisions would be indicated
                       by incrementing only dot3CollFrequencies.77.4.
                       No other instance of dot3CollFrequencies would
                       be incremented in this example."
    ::= { dot3CollEntry  3 }

dot3Tests OBJECT IDENTIFIER ::= { dot3  6 }

dot3Errors OBJECT IDENTIFIER ::= { dot3  7 }

dot3TestTdr OBJECT IDENTIFIER ::= { dot3Tests  1 }

dot3TestLoopBack OBJECT IDENTIFIER ::= { dot3Tests  2 }

dot3ErrorInitError OBJECT IDENTIFIER ::= { dot3Errors  1 }

dot3ErrorLoopbackError OBJECT IDENTIFIER ::= { dot3Errors  2 }

dot3ChipSets OBJECT IDENTIFIER ::= { dot3  8 }

dot3ChipSetAMD OBJECT IDENTIFIER ::= { dot3ChipSets  1 }

dot3ChipSetAMD7990 OBJECT IDENTIFIER ::= { dot3ChipSetAMD  1 }

dot3ChipSetAMD79900 OBJECT IDENTIFIER ::= { dot3ChipSetAMD  2 }

dot3ChipSetAMD79C940 OBJECT IDENTIFIER ::= { dot3ChipSetAMD  3 }

dot3ChipSetAMD79C90 OBJECT IDENTIFIER ::= { dot3ChipSetAMD  4 }

dot3ChipSetAMD79C960 OBJECT IDENTIFIER ::= { dot3ChipSetAMD  5 }

dot3ChipSetAMD79C961 OBJECT IDENTIFIER ::= { dot3ChipSetAMD  6 }

dot3ChipSetAMD79C961A OBJECT IDENTIFIER ::= { dot3ChipSetAMD  7 }

dot3ChipSetAMD79C965 OBJECT IDENTIFIER ::= { dot3ChipSetAMD  8 }

dot3ChipSetAMD79C970 OBJECT IDENTIFIER ::= { dot3ChipSetAMD  9 }

dot3ChipSetAMD79C970A OBJECT IDENTIFIER ::= { dot3ChipSetAMD  10 }

dot3ChipSetAMD79C971 OBJECT IDENTIFIER ::= { dot3ChipSetAMD  11 }

dot3ChipSetAMD79C972 OBJECT IDENTIFIER ::= { dot3ChipSetAMD  12 }

dot3ChipSetIntel OBJECT IDENTIFIER ::= { dot3ChipSets  2 }

dot3ChipSetIntel82586 OBJECT IDENTIFIER ::= { dot3ChipSetIntel  1 }

dot3ChipSetIntel82596 OBJECT IDENTIFIER ::= { dot3ChipSetIntel  2 }

dot3ChipSetIntel82595 OBJECT IDENTIFIER ::= { dot3ChipSetIntel  3 }

dot3ChipSetIntel82557 OBJECT IDENTIFIER ::= { dot3ChipSetIntel  4 }

dot3ChipSetIntel82558 OBJECT IDENTIFIER ::= { dot3ChipSetIntel  5 }

dot3ChipSetSeeq OBJECT IDENTIFIER ::= { dot3ChipSets  3 }

dot3ChipSetSeeq8003 OBJECT IDENTIFIER ::= { dot3ChipSetSeeq  1 }

dot3ChipSetSeeq80C03 OBJECT IDENTIFIER ::= { dot3ChipSetSeeq  2 }

dot3ChipSetSeeq84C30 OBJECT IDENTIFIER ::= { dot3ChipSetSeeq  3 }

dot3ChipSetSeeq8431 OBJECT IDENTIFIER ::= { dot3ChipSetSeeq  4 }

dot3ChipSetSeeq80C300 OBJECT IDENTIFIER ::= { dot3ChipSetSeeq  5 }

dot3ChipSetSeeq84C300 OBJECT IDENTIFIER ::= { dot3ChipSetSeeq  6 }

dot3ChipSetSeeq84301 OBJECT IDENTIFIER ::= { dot3ChipSetSeeq  7 }

dot3ChipSetSeeq84302 OBJECT IDENTIFIER ::= { dot3ChipSetSeeq  8 }

dot3ChipSetSeeq8100 OBJECT IDENTIFIER ::= { dot3ChipSetSeeq  9 }

dot3ChipSetNational OBJECT IDENTIFIER ::= { dot3ChipSets  4 }

dot3ChipSetNational8390 OBJECT IDENTIFIER ::= { dot3ChipSetNational  1 }

dot3ChipSetNationalSonic OBJECT IDENTIFIER ::= { dot3ChipSetNational  2 }

dot3ChipSetNational83901 OBJECT IDENTIFIER ::= { dot3ChipSetNational  3 }

dot3ChipSetNational83902 OBJECT IDENTIFIER ::= { dot3ChipSetNational  4 }

dot3ChipSetNational83905 OBJECT IDENTIFIER ::= { dot3ChipSetNational  5 }

dot3ChipSetNational83907 OBJECT IDENTIFIER ::= { dot3ChipSetNational  6 }

dot3ChipSetNational83916 OBJECT IDENTIFIER ::= { dot3ChipSetNational  7 }

dot3ChipSetNational83934 OBJECT IDENTIFIER ::= { dot3ChipSetNational  8 }

dot3ChipSetNational83936 OBJECT IDENTIFIER ::= { dot3ChipSetNational  9 }

dot3ChipSetFujitsu OBJECT IDENTIFIER ::= { dot3ChipSets  5 }

dot3ChipSetFujitsu86950 OBJECT IDENTIFIER ::= { dot3ChipSetFujitsu  1 }

dot3ChipSetFujitsu86960 OBJECT IDENTIFIER ::= { dot3ChipSetFujitsu  2 }

dot3ChipSetFujitsu86964 OBJECT IDENTIFIER ::= { dot3ChipSetFujitsu  3 }

dot3ChipSetFujitsu86965A OBJECT IDENTIFIER ::= { dot3ChipSetFujitsu  4 }

dot3ChipSetFujitsu86965B OBJECT IDENTIFIER ::= { dot3ChipSetFujitsu  5 }

dot3ChipSetDigital OBJECT IDENTIFIER ::= { dot3ChipSets  6 }

dot3ChipSetDigitalDC21040 OBJECT IDENTIFIER ::= { dot3ChipSetDigital  1 }

dot3ChipSetDigital21041 OBJECT IDENTIFIER ::= { dot3ChipSetDigital  2 }

dot3ChipSetDigital21140 OBJECT IDENTIFIER ::= { dot3ChipSetDigital  3 }

dot3ChipSetDigital21143 OBJECT IDENTIFIER ::= { dot3ChipSetDigital  4 }

dot3ChipSetDigital21340 OBJECT IDENTIFIER ::= { dot3ChipSetDigital  5 }

dot3ChipSetDigital21440 OBJECT IDENTIFIER ::= { dot3ChipSetDigital  6 }

dot3ChipSetDigital21540 OBJECT IDENTIFIER ::= { dot3ChipSetDigital  7 }

dot3ChipSetTI OBJECT IDENTIFIER ::= { dot3ChipSets  7 }

dot3ChipSetTIE100 OBJECT IDENTIFIER ::= { dot3ChipSetTI  1 }

dot3ChipSetTIE110 OBJECT IDENTIFIER ::= { dot3ChipSetTI  2 }

dot3ChipSetTIX3100 OBJECT IDENTIFIER ::= { dot3ChipSetTI  3 }

dot3ChipSetTIX3150 OBJECT IDENTIFIER ::= { dot3ChipSetTI  4 }

dot3ChipSetTIX3270 OBJECT IDENTIFIER ::= { dot3ChipSetTI  5 }

dot3ChipSetToshiba OBJECT IDENTIFIER ::= { dot3ChipSets  8 }

dot3ChipSetToshibaTC35815F OBJECT IDENTIFIER ::= { dot3ChipSetToshiba  1 }

dot3ChipSetLucent OBJECT IDENTIFIER ::= { dot3ChipSets  9 }

dot3ChipSetLucentATT1MX10 OBJECT IDENTIFIER ::= { dot3ChipSetLucent  1 }

dot3ChipSetLucentLUC3M08 OBJECT IDENTIFIER ::= { dot3ChipSetLucent  2 }

dot3ChipSetGalileo OBJECT IDENTIFIER ::= { dot3ChipSets  10 }

dot3ChipSetGalileoGT48001 OBJECT IDENTIFIER ::= { dot3ChipSetGalileo  1 }

dot3ChipSetGalileoGT48002 OBJECT IDENTIFIER ::= { dot3ChipSetGalileo  2 }

dot3ChipSetGalileoGT48004 OBJECT IDENTIFIER ::= { dot3ChipSetGalileo  3 }

dot3ChipSetGalileoGT48207 OBJECT IDENTIFIER ::= { dot3ChipSetGalileo  4 }

dot3ChipSetGalileoGT48208 OBJECT IDENTIFIER ::= { dot3ChipSetGalileo  5 }

dot3ChipSetGalileoGT48212 OBJECT IDENTIFIER ::= { dot3ChipSetGalileo  6 }

dot3ChipSetJato OBJECT IDENTIFIER ::= { dot3ChipSets  11 }

dot3ChipSetJatoJT1001 OBJECT IDENTIFIER ::= { dot3ChipSetJato  1 }

dot3ChipSetXaQti OBJECT IDENTIFIER ::= { dot3ChipSets  12 }

dot3ChipSetXaQtiXQ11800FP OBJECT IDENTIFIER ::= { dot3ChipSetXaQti  1 }

dot3ChipSetXaQtiXQ18110FP OBJECT IDENTIFIER ::= { dot3ChipSetXaQti  2 }

etherConformance OBJECT IDENTIFIER ::= { etherMIB  2 }

etherGroups OBJECT IDENTIFIER ::= { etherConformance  1 }

etherCompliances OBJECT IDENTIFIER ::= { etherConformance  2 }

etherCompliance OBJECT IDENTIFIER ::= { etherCompliances  1 }

ether100MbsCompliance OBJECT IDENTIFIER ::= { etherCompliances  2 }

etherStatsGroup OBJECT IDENTIFIER ::= { etherGroups  1 }

etherCollisionTableGroup OBJECT IDENTIFIER ::= { etherGroups  2 }

etherStats100MbsGroup OBJECT IDENTIFIER ::= { etherGroups  3 }

END
