-- automatically generated by mosy 7.1 #1 (hprnljf), do not edit!

SNMPv2-TC DEFINITIONS ::= BEGIN

    IMPORTS
	TimeTicks FROM RFC1155-SMI;

DisplayString ::=
    OCTET STRING (SIZE (0..255))

PhysAddress ::=
    OCTET STRING

MacAddress ::=
    OCTET STRING (SIZE (6))

TruthValue ::=
    INTEGER {
 true(1),
 false(2)
 }

TestAndIncr ::=
    INTEGER (0..2147483647)

AutonomousType ::=
    OBJECT IDENTIFIER

InstancePointer ::=
    OBJECT IDENTIFIER

VariablePointer ::=
    OBJECT IDENTIFIER

RowPointer ::=
    OBJECT IDENTIFIER

RowStatus ::=
    INTEGER {
 active(1),
 notInService(2),
 notReady(3),
 createAndGo(4),
 createAndWait(5),
 destroy(6)
 }

TimeStamp ::=
    TimeTicks

TimeInterval ::=
    INTEGER (0..2147483647)

DateAndTime ::=
    OCTET STRING (SIZE (8 | 11))

StorageType ::=
    INTEGER {
 other(1),
 volatile(2),
 nonVolatile(3),
 permanent(4),
 readOnly(5)
 }

TDomain ::=
    OBJECT IDENTIFIER

TAddress ::=
    OCTET STRING (SIZE (1..255))

END
