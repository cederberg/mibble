-- automatically generated by mosy 7.1 #1 (hprnljf), do not edit!

UDP-MIB DEFINITIONS ::= BEGIN


IMPORTS
	Counter, IpAddress
		FROM RFC1155-SMI
        OBJECT-TYPE
		FROM RFC-1212
	mib-2
		FROM RFC1213-MIB;
-- created from udpMIB (9411010000Z)

udpMIB OBJECT IDENTIFIER ::= { mib-2  50 }

udp OBJECT IDENTIFIER ::= { mib-2  7 }

udpInDatagrams OBJECT-TYPE
    SYNTAX  Counter
    ACCESS  read-only
    STATUS  mandatory
    DESCRIPTION
           "The total number of UDP datagrams delivered to UDP users."
    ::= { udp  1 }

udpNoPorts OBJECT-TYPE
    SYNTAX  Counter
    ACCESS  read-only
    STATUS  mandatory
    DESCRIPTION
           "The total number of received UDP datagrams for which there
            was no application at the destination port."
    ::= { udp  2 }

udpInErrors OBJECT-TYPE
    SYNTAX  Counter
    ACCESS  read-only
    STATUS  mandatory
    DESCRIPTION
           "The number of received UDP datagrams that could not be
            delivered for reasons other than the lack of an application
            at the destination port."
    ::= { udp  3 }

udpOutDatagrams OBJECT-TYPE
    SYNTAX  Counter
    ACCESS  read-only
    STATUS  mandatory
    DESCRIPTION
           "The total number of UDP datagrams sent from this entity."
    ::= { udp  4 }

udpTable OBJECT-TYPE
    SYNTAX  SEQUENCE OF UdpEntry
    ACCESS  not-accessible
    STATUS  mandatory
    DESCRIPTION
           "A table containing UDP listener information."
    ::= { udp  5 }

udpEntry OBJECT-TYPE
    SYNTAX  UdpEntry
    ACCESS  not-accessible
    STATUS  mandatory
    DESCRIPTION
           "Information about a particular current UDP listener."
    INDEX   { udpLocalAddress,  udpLocalPort }
    ::= { udpTable  1 }

UdpEntry ::=
    SEQUENCE {
    udpLocalAddress
        IpAddress,

    udpLocalPort
        INTEGER
    }

udpLocalAddress OBJECT-TYPE
    SYNTAX  IpAddress
    ACCESS  read-only
    STATUS  mandatory
    DESCRIPTION
           "The local IP address for this UDP listener.  In the case of
            a UDP listener which is willing to accept datagrams for any
            IP interface associated with the node, the value 0.0.0.0 is
            used."
    ::= { udpEntry  1 }

udpLocalPort OBJECT-TYPE
    SYNTAX  INTEGER (0..65535)
    ACCESS  read-only
    STATUS  mandatory
    DESCRIPTION
           "The local port number for this UDP listener."
    ::= { udpEntry  2 }

udpMIBConformance OBJECT IDENTIFIER ::= { udpMIB  2 }

udpMIBCompliances OBJECT IDENTIFIER ::= { udpMIBConformance  1 }

udpMIBGroups OBJECT IDENTIFIER ::= { udpMIBConformance  2 }

udpMIBCompliance OBJECT IDENTIFIER ::= { udpMIBCompliances  1 }

udpGroup OBJECT IDENTIFIER ::= { udpMIBGroups  1 }

END
