-- automatically generated by mosy 7.1 #1 (hprnljf), do not edit!

HP-ICF-OID DEFINITIONS ::= BEGIN

-- created from icf (9809240004Z)

    IMPORTS
	enterprises
	    FROM RFC1155-SMI;

hp OBJECT IDENTIFIER ::= { enterprises  11 }

nm OBJECT IDENTIFIER ::= { hp  2 }

icf OBJECT IDENTIFIER ::= { nm  14 }

icfCommon OBJECT IDENTIFIER ::= { icf  1 }

icfHub OBJECT IDENTIFIER ::= { icf  2 }

icfBridge OBJECT IDENTIFIER ::= { icf  3 }

icfSecurity OBJECT IDENTIFIER ::= { icf  4 }

icfConfig OBJECT IDENTIFIER ::= { icf  5 }

icfEsSwitch OBJECT IDENTIFIER ::= { icf  6 }

hpEs OBJECT IDENTIFIER ::= { icfEsSwitch  1 }

hpEs2 OBJECT IDENTIFIER ::= { icfEsSwitch  2 }

hpNetSwitch OBJECT IDENTIFIER ::= { icfEsSwitch  3 }

icfRouter OBJECT IDENTIFIER ::= { icf  7 }

icfDot12Draft OBJECT IDENTIFIER ::= { icf  8 }

icfVgRepeater OBJECT IDENTIFIER ::= { icfDot12Draft  1 }

icfVgInterface OBJECT IDENTIFIER ::= { icfDot12Draft  2 }

hpicfAdmin OBJECT IDENTIFIER ::= { icf  10 }

hpicfObjects OBJECT IDENTIFIER ::= { icf  11 }

hpicfNotifications OBJECT IDENTIFIER ::= { icf  12 }

hpicfOEMs OBJECT IDENTIFIER ::= { icf  13 }

hpicfFEHub OBJECT IDENTIFIER ::= { hpicfOEMs  1 }

hpicfDomains OBJECT IDENTIFIER ::= { hpicfAdmin  1 }

hpicfLLCDomain OBJECT IDENTIFIER ::= { hpicfDomains  1 }

hpicfObjectModules OBJECT IDENTIFIER ::= { hpicfAdmin  2 }

hpicfAgentModules OBJECT IDENTIFIER ::= { hpicfAdmin  3 }

hpicfCommon OBJECT IDENTIFIER ::= { hpicfObjects  1 }

hpicfRepeater OBJECT IDENTIFIER ::= { hpicfObjects  2 }

hpicfVg OBJECT IDENTIFIER ::= { hpicfObjects  3 }

hpicfGenericRepeater OBJECT IDENTIFIER ::= { hpicfObjects  4 }

hpicfCommonTraps OBJECT IDENTIFIER ::= { hpicfNotifications  1 }

-- hpicfCommonTrapsPrefix OBJECT IDENTIFIER ::= { hpicfCommonTraps  0 }

hpicf8023RptrTraps OBJECT IDENTIFIER ::= { hpicfNotifications  2 }

-- hpicf8023RptrTrapsPrefix OBJECT IDENTIFIER ::= { hpicf8023RptrTraps  0 }

hpicfVgRptrTraps OBJECT IDENTIFIER ::= { hpicfNotifications  3 }

-- hpicfVgRptrTrapsPrefix OBJECT IDENTIFIER ::= { hpicfVgRptrTraps  0 }

hpicfGenRptrTraps OBJECT IDENTIFIER ::= { hpicfNotifications  4 }

-- hpicfGenRptrTrapsPrefix OBJECT IDENTIFIER ::= { hpicfGenRptrTraps  0 }

system OBJECT IDENTIFIER ::= { nm  3 }

netElement OBJECT IDENTIFIER ::= { system  7 }

bridge OBJECT IDENTIFIER ::= { netElement  1 }

bridge1010 OBJECT IDENTIFIER ::= { bridge  1 }

bridgeRemote OBJECT IDENTIFIER ::= { bridge  2 }

eswitch OBJECT IDENTIFIER ::= { bridge  3 }

eswitch2 OBJECT IDENTIFIER ::= { bridge  8 }

netSwitch100 OBJECT IDENTIFIER ::= { bridge  9 }

netSwitch200 OBJECT IDENTIFIER ::= { bridge  10 }

router OBJECT IDENTIFIER ::= { netElement  2 }

icfRouterER OBJECT IDENTIFIER ::= { router  1 }

icfRouterTR OBJECT IDENTIFIER ::= { router  2 }

icfRouterSR OBJECT IDENTIFIER ::= { router  3 }

icfRouterFR OBJECT IDENTIFIER ::= { router  4 }

icfRouterLR OBJECT IDENTIFIER ::= { router  5 }

icfRouterBR OBJECT IDENTIFIER ::= { router  6 }

icfRouterPR OBJECT IDENTIFIER ::= { router  7 }

icfRouter650 OBJECT IDENTIFIER ::= { router  8 }

icfRouter230 OBJECT IDENTIFIER ::= { router  9 }

icfRouter250 OBJECT IDENTIFIER ::= { router  10 }

icfRouter255 OBJECT IDENTIFIER ::= { router  11 }

icfRouter210 OBJECT IDENTIFIER ::= { router  12 }

icfRouter650Engine OBJECT IDENTIFIER ::= { icfRouter650  2 }

icfRouter650Port4E OBJECT IDENTIFIER ::= { icfRouter650  3 }

icfRouter650Port4S OBJECT IDENTIFIER ::= { icfRouter650  4 }

icfRouter650Port4T OBJECT IDENTIFIER ::= { icfRouter650  5 }

icfRouter650PortFDDI OBJECT IDENTIFIER ::= { icfRouter650  6 }

icfRouter650Port100VG OBJECT IDENTIFIER ::= { icfRouter650  7 }

hub OBJECT IDENTIFIER ::= { netElement  5 }

etherTwist12 OBJECT IDENTIFIER ::= { hub  1 }

fiberOptic OBJECT IDENTIFIER ::= { hub  3 }

etherTwist48 OBJECT IDENTIFIER ::= { hub  4 }

thinLAN OBJECT IDENTIFIER ::= { hub  5 }

etherTwist24S OBJECT IDENTIFIER ::= { hub  6 }

advStack12 OBJECT IDENTIFIER ::= { hub  7 }

advStack24 OBJECT IDENTIFIER ::= { hub  8 }

advStack48 OBJECT IDENTIFIER ::= { hub  9 }

advStackVg15 OBJECT IDENTIFIER ::= { hub  10 }

advStackU8 OBJECT IDENTIFIER ::= { hub  11 }

advStackU16 OBJECT IDENTIFIER ::= { hub  12 }

advStackVg6 OBJECT IDENTIFIER ::= { hub  13 }

advStackVg12 OBJECT IDENTIFIER ::= { hub  14 }

hpAdvStkEnetSH12R OBJECT IDENTIFIER ::= { hub  15 }

hpAdvStkEnetSH24R OBJECT IDENTIFIER ::= { hub  16 }

hpAdvStkEnetSH24T OBJECT IDENTIFIER ::= { hub  17 }

hpAdvStk100Tx12TM OBJECT IDENTIFIER ::= { hub  18 }

hp10THub16M OBJECT IDENTIFIER ::= { hub  19 }

hp10BaseTHub12M OBJECT IDENTIFIER ::= { hub  20 }

hp10BaseTHub24M OBJECT IDENTIFIER ::= { hub  21 }

hpProCurve10T100THub12M OBJECT IDENTIFIER ::= { hub  22 }

hpProCurve10T100THub24M OBJECT IDENTIFIER ::= { hub  23 }

chassis OBJECT IDENTIFIER ::= { netElement  8 }

repeaterAgent OBJECT IDENTIFIER ::= { chassis  1 }

chassisAgents OBJECT IDENTIFIER ::= { chassis  2 }

icfVgAgent OBJECT IDENTIFIER ::= { chassisAgents  1 }

icfVgAgent2 OBJECT IDENTIFIER ::= { chassisAgents  3 }

hpicfEnetSMM OBJECT IDENTIFIER ::= { chassisAgents  4 }

hpAdvStkEnetSHAgent OBJECT IDENTIFIER ::= { chassisAgents  5 }

hpAdvStkSwStackTopMgmt OBJECT IDENTIFIER ::= { chassisAgents  6 }

hpSwitch8000CpuCard OBJECT IDENTIFIER ::= { chassisAgents  7 }

icfSensors OBJECT IDENTIFIER ::= { chassis  3 }

icfPowerSupplySensor OBJECT IDENTIFIER ::= { icfSensors  1 }

icfFanSensor OBJECT IDENTIFIER ::= { icfSensors  2 }

icfTemperatureSensor OBJECT IDENTIFIER ::= { icfSensors  3 }

icfFutureSlotSensor OBJECT IDENTIFIER ::= { icfSensors  4 }

icfCards OBJECT IDENTIFIER ::= { chassis  4 }

icfUnidentifiedCard OBJECT IDENTIFIER ::= { icfCards  1 }

hpAdvStkEnetSHSwitch OBJECT IDENTIFIER ::= { icfCards  2 }

hpAdvStkSwStackExpander OBJECT IDENTIFIER ::= { icfCards  3 }

hpicfStacks OBJECT IDENTIFIER ::= { chassis  5 }

hpAdvStkEnetSHStack OBJECT IDENTIFIER ::= { hpicfStacks  1 }

hpicfBackplanes OBJECT IDENTIFIER ::= { chassis  6 }

hpAdvStkEnetSHExtSeg OBJECT IDENTIFIER ::= { hpicfBackplanes  1 }

hpAdvStkEnetSHIntSeg OBJECT IDENTIFIER ::= { hpicfBackplanes  2 }

hp10BaseTHubSeg OBJECT IDENTIFIER ::= { hpicfBackplanes  3 }

hpSwitchBackplane OBJECT IDENTIFIER ::= { hpicfBackplanes  4 }

hp100BaseTHubSeg OBJECT IDENTIFIER ::= { hpicfBackplanes  5 }

hpicfSlots OBJECT IDENTIFIER ::= { chassis  7 }

hpAdvStkEnetSHAgentSlot OBJECT IDENTIFIER ::= { hpicfSlots  1 }

hpAdvStkEnetSHIOSlot OBJECT IDENTIFIER ::= { hpicfSlots  2 }

hpAdvStkSwStackMgmtSlot OBJECT IDENTIFIER ::= { hpicfSlots  3 }

hpAdvStkSwStackExpSlot OBJECT IDENTIFIER ::= { hpicfSlots  4 }

hpSwitch8000PowerSupplyBay OBJECT IDENTIFIER ::= { hpicfSlots  5 }

hpSwitch8000CpuSlot OBJECT IDENTIFIER ::= { hpicfSlots  6 }

hpSwitch8000PortSlot OBJECT IDENTIFIER ::= { hpicfSlots  7 }

hpicfHubPorts OBJECT IDENTIFIER ::= { chassis  8 }

hpAdvStkEnetSHExtPort OBJECT IDENTIFIER ::= { hpicfHubPorts  1 }

hpAdvStkEnetSHIntPort OBJECT IDENTIFIER ::= { hpicfHubPorts  2 }

hpAdvStkEnetSHAgentPort OBJECT IDENTIFIER ::= { hpicfHubPorts  3 }

hp10BaseTHubPort OBJECT IDENTIFIER ::= { hpicfHubPorts  4 }

hp10BaseTHubAgentPort OBJECT IDENTIFIER ::= { hpicfHubPorts  5 }

hp10T100THubPort OBJECT IDENTIFIER ::= { hpicfHubPorts  6 }

hp100BaseTHubAgentPort OBJECT IDENTIFIER ::= { hpicfHubPorts  7 }

hpicfEnetChipSets OBJECT IDENTIFIER ::= { chassis  9 }

hpicfEnetChipSetHydra OBJECT IDENTIFIER ::= { hpicfEnetChipSets  1 }

hpicfEnetChipSetGT48001 OBJECT IDENTIFIER ::= { hpicfEnetChipSets  2 }

hpicfEnetChipSetPentagon OBJECT IDENTIFIER ::= { hpicfEnetChipSets  3 }

hpicfSwitchPorts OBJECT IDENTIFIER ::= { chassis  10 }

hpicfSwitchPort10T100TX OBJECT IDENTIFIER ::= { hpicfSwitchPorts  1 }

hpicfSwitchPort100FX OBJECT IDENTIFIER ::= { hpicfSwitchPorts  2 }

hpicfSwitchPort10FL OBJECT IDENTIFIER ::= { hpicfSwitchPorts  3 }

hpicfSwitchPort1000SX OBJECT IDENTIFIER ::= { hpicfSwitchPorts  4 }

hpicfSwitchPort10T OBJECT IDENTIFIER ::= { hpicfSwitchPorts  5 }

hpicfSwitchPort1000LX OBJECT IDENTIFIER ::= { hpicfSwitchPorts  6 }

hpicfSwitchPort1000T OBJECT IDENTIFIER ::= { hpicfSwitchPorts  7 }

hpicfMAUTypes OBJECT IDENTIFIER ::= { chassis  11 }

hpicfMauType1000BaseSXHD OBJECT IDENTIFIER ::= { hpicfMAUTypes  1 }

hpicfMauType1000BaseSXFD OBJECT IDENTIFIER ::= { hpicfMAUTypes  2 }

hpicfMauType1000BaseLXHD OBJECT IDENTIFIER ::= { hpicfMAUTypes  3 }

hpicfMauType1000BaseLXFD OBJECT IDENTIFIER ::= { hpicfMAUTypes  4 }

hpicfMauType1000BaseTHD OBJECT IDENTIFIER ::= { hpicfMAUTypes  5 }

hpicfMauType1000BaseTFD OBJECT IDENTIFIER ::= { hpicfMAUTypes  6 }

hpEtherSwitch OBJECT IDENTIFIER ::= { netElement  11 }

hpAdvSwitch2000 OBJECT IDENTIFIER ::= { hpEtherSwitch  1 }

hpAdvSwitch2000B OBJECT IDENTIFIER ::= { hpEtherSwitch  2 }

hpAdvSwitch800T OBJECT IDENTIFIER ::= { hpEtherSwitch  3 }

hpAdvSwitch200 OBJECT IDENTIFIER ::= { hpEtherSwitch  4 }

hpSwitch212M OBJECT IDENTIFIER ::= { hpEtherSwitch  5 }

hpSwitch224M OBJECT IDENTIFIER ::= { hpEtherSwitch  6 }

hpSwitch8000 OBJECT IDENTIFIER ::= { hpEtherSwitch  7 }

hpSwitch1600 OBJECT IDENTIFIER ::= { hpEtherSwitch  8 }

hpSwitch4000 OBJECT IDENTIFIER ::= { hpEtherSwitch  9 }

hpSwitch2400 OBJECT IDENTIFIER ::= { hpEtherSwitch  10 }

hpSwitch2424 OBJECT IDENTIFIER ::= { hpEtherSwitch  11 }

hpSwitchPortModuleET4 OBJECT IDENTIFIER ::= { hpAdvSwitch2000  1 }

hpSwitchPortModuleVG2 OBJECT IDENTIFIER ::= { hpAdvSwitch2000  2 }

hpSwitchPortModule10FL OBJECT IDENTIFIER ::= { hpAdvSwitch2000  3 }

hpSwitchPortModuleFDDI OBJECT IDENTIFIER ::= { hpAdvSwitch2000  4 }

hpSwitchPortModuleTX2 OBJECT IDENTIFIER ::= { hpAdvSwitch2000  5 }

hpSwitchPortModuleATM OBJECT IDENTIFIER ::= { hpAdvSwitch2000  6 }

hpSwitchPortModule100TX8 OBJECT IDENTIFIER ::= { hpSwitch8000  1 }

hpSwitchPortModule100FX4 OBJECT IDENTIFIER ::= { hpSwitch8000  2 }

hpSwitchPortModule10FL4 OBJECT IDENTIFIER ::= { hpSwitch8000  3 }

hpSwitchPortModuleGigSX OBJECT IDENTIFIER ::= { hpSwitch8000  4 }

hpSwitchPortModuleGigLX OBJECT IDENTIFIER ::= { hpSwitch8000  5 }

hpSwitchPortModule2Gig OBJECT IDENTIFIER ::= { hpSwitch8000  6 }

END
