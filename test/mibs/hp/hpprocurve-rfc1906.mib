-- automatically generated by mosy 7.1 #1 (hprnljf), do not edit!

SNMPv2-TM DEFINITIONS ::= BEGIN


IMPORTS
	snmpProxys, snmpDomains
		FROM SNMPv2-SMI;
snmpUDPDomain OBJECT IDENTIFIER ::= { snmpDomains  1 }

SnmpUDPAddress ::=
    OCTET STRING (SIZE (6))

snmpCLNSDomain OBJECT IDENTIFIER ::= { snmpDomains  2 }

snmpCONSDomain OBJECT IDENTIFIER ::= { snmpDomains  3 }

SnmpOSIAddress ::=
    OCTET STRING (SIZE (1 | 4..85))

snmpDDPDomain OBJECT IDENTIFIER ::= { snmpDomains  4 }

SnmpNBPAddress ::=
    OCTET STRING (SIZE (3..99))

snmpIPXDomain OBJECT IDENTIFIER ::= { snmpDomains  5 }

SnmpIPXAddress ::=
    OCTET STRING (SIZE (12))

rfc1157Proxy OBJECT IDENTIFIER ::= { snmpProxys  1 }

rfc1157Domain OBJECT IDENTIFIER ::= { rfc1157Proxy  1 }

END
