-- automatically generated by mosy 7.1 #1 (hprnljf), do not edit!

TOKENRING-STATION-SR-MIB DEFINITIONS ::= BEGIN


IMPORTS
	OBJECT-TYPE
		FROM RFC-1212
	ifIndex, mib-2
		FROM RFC1213-MIB
	RowStatus, MacAddress
		FROM SNMPv2-TC;
-- created from dot5SrMIB (9412161000Z)

dot5SrMIB OBJECT IDENTIFIER ::= { mib-2  42 }

dot5SrMIBObjects OBJECT IDENTIFIER ::= { dot5SrMIB  1 }

SourceRoute ::=
    OCTET STRING (SIZE(0..30))

dot5SrRouteTable OBJECT-TYPE
    SYNTAX  SEQUENCE OF Dot5SrRouteEntry
    ACCESS  not-accessible
    STATUS  mandatory
    DESCRIPTION
           "The table of source-routing routes.
               This represents the 802.5 RIF database."
    ::= { dot5SrMIBObjects  1 }

dot5SrRouteEntry OBJECT-TYPE
    SYNTAX  Dot5SrRouteEntry
    ACCESS  not-accessible
    STATUS  mandatory
    DESCRIPTION
           "Information on a specific route.

                An entry is created whenever a 'Single Path
                Explorer' or an 'All Paths Explorer' discovers
                a route to a neighbor not currently in the table,
                or whenever an 'All Paths Explorer' discovers a
                better (e.g., shorter) route than the route currently
                stored in the table.  This is done on behalf of
                any network layer client.

                The ifIndex value in the INDEX clause refers to
                the value of MIB-II's ifIndex object for the
                interface on which the route is in effect."
    INDEX   { ifIndex,  dot5SrRouteDestination }
    ::= { dot5SrRouteTable  1 }

Dot5SrRouteEntry ::=
    SEQUENCE {
    dot5SrRouteDestination
        MacAddress,

    dot5SrRouteControl
        OCTET STRING,

    dot5SrRouteDescr
        SourceRoute,

    dot5SrRouteStatus
        RowStatus
    }

dot5SrRouteDestination OBJECT-TYPE
    SYNTAX  MacAddress
    ACCESS  not-accessible
    STATUS  mandatory
    DESCRIPTION
           "The destination of this route."
    ::= { dot5SrRouteEntry  2 }

dot5SrRouteControl OBJECT-TYPE
    SYNTAX  OCTET STRING (SIZE(2))
    ACCESS  read-write
    STATUS  mandatory
    DESCRIPTION
           "The value of Routing Control field for this
               route."
    REFERENCE
           "Annex C of ISO/IEC 10038: 1993,
               [ANSI/IEEE Std 802.1D, 1993]"
    ::= { dot5SrRouteEntry  3 }

dot5SrRouteDescr OBJECT-TYPE
    SYNTAX  SourceRoute
    ACCESS  read-write
    STATUS  mandatory
    DESCRIPTION
           "The embedded sequence of bridge and ring ID's
               for this route.  For destinations on the
               local ring, the value of this object is
               the zero-length string."
    REFERENCE
           "Annex C of ISO/IEC 10038: 1993,
               [ANSI/IEEE Std 802.1D, 1993]"
    ::= { dot5SrRouteEntry  4 }

dot5SrRouteStatus OBJECT-TYPE
    SYNTAX  RowStatus
    ACCESS  read-write
    STATUS  mandatory
    DESCRIPTION
           "The status of this row.  Values of the instances
             of dot5SrRouteControl and dot5SrRouteDescr can be
             modified while the row's status is 'active."
    ::= { dot5SrRouteEntry  5 }

dot5SrConformance OBJECT IDENTIFIER ::= { dot5SrMIB  2 }

dot5SrGroups OBJECT IDENTIFIER ::= { dot5SrConformance  1 }

dot5SrCompliances OBJECT IDENTIFIER ::= { dot5SrConformance  2 }

dot5SrCompliance OBJECT IDENTIFIER ::= { dot5SrCompliances  1 }

dot5SrRouteGroup OBJECT IDENTIFIER ::= { dot5SrGroups  1 }

END
