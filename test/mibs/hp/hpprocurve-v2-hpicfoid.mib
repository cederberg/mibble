HP-ICF-OID DEFINITIONS ::= BEGIN

       IMPORTS
           enterprises, MODULE-IDENTITY, OBJECT-IDENTITY
               FROM SNMPv2-SMI;

       hp                OBJECT IDENTIFIER ::= { enterprises 11 }
       nm                OBJECT IDENTIFIER ::= { hp 2 }

       icf MODULE-IDENTITY
            LAST-UPDATED "9809240004Z"
            ORGANIZATION "Hewlett Packard Company,
                          Workgroup Networks Division"
            CONTACT-INFO "Hewlett Packard Company
                          8000 Foothills Blvd.
                          Roseville, CA 95747"
            DESCRIPTION  "This MIB module describes devices in the HP 
                         Integrated Communication Facility product 
                         line."

            REVISION     "9809240004Z"
            DESCRIPTION  "Added definitions for 100Mbit and 10/100
                         hub products, and definitions for the
                         ProCurve switch products."

            REVISION     "9710210242Z"
            DESCRIPTION  "Added definitions for new hub products
                         (10Base-T Hub-12M, 10Base-T Hub-24M, and
                         10Base-T Hub-16M) and Switch 2000 ATM module.
                         Added branch for the Fault Finder MIB."

            REVISION     "9703060342Z"
            DESCRIPTION  "Added definitions for new switch products
                         (208/224), 100T hub (J3233A).  Added missing
                         include of OBJECT-IDENTITY."

            REVISION     "9609132303Z"
            DESCRIPTION  "Initial revision.  Split from the former
                         monolithic hpicf MIB."
            ::= { nm 14 }


       -- Branches under the icf node.  Most of these
       -- branches are defined in other modules.

       icfCommon         OBJECT IDENTIFIER ::= { icf 1 }
       icfHub            OBJECT IDENTIFIER ::= { icf 2 }
       icfBridge         OBJECT IDENTIFIER ::= { icf 3 }

       icfSecurity       OBJECT IDENTIFIER ::= { icf 4 }
       icfConfig         OBJECT IDENTIFIER ::= { icf 5 }

       icfEsSwitch       OBJECT IDENTIFIER ::= { icf 6 }
       hpEs              OBJECT IDENTIFIER ::= { icfEsSwitch 1 }
       hpEs2             OBJECT IDENTIFIER ::= { icfEsSwitch 2 }
       hpNetSwitch       OBJECT IDENTIFIER ::= { icfEsSwitch 3 }

       icfRouter         OBJECT IDENTIFIER ::= { icf 7 }

       icfDot12Draft     OBJECT IDENTIFIER ::= { icf 8 }
       icfVgRepeater     OBJECT IDENTIFIER ::= { icfDot12Draft 1 }
       icfVgInterface    OBJECT IDENTIFIER ::= { icfDot12Draft 2 }

    -- hpEntityMIB       OBJECT IDENTIFIER ::= { icf 9 }

       hpicfAdmin        OBJECT IDENTIFIER ::= { icf 10 }
       hpicfObjects      OBJECT IDENTIFIER ::= { icf 11 }
       hpicfNotifications
                         OBJECT IDENTIFIER ::= { icf 12 }

       hpicfOEMs         OBJECT IDENTIFIER ::= { icf 13 }
       hpicfFEHub        OBJECT IDENTIFIER ::= { hpicfOEMs 1 }


       -- HP defined transport domains

       hpicfDomains      OBJECT IDENTIFIER ::= { hpicfAdmin 1 }

       hpicfLLCDomain OBJECT-IDENTITY
           STATUS      current
           DESCRIPTION "The SNMP over 802.2 transport domain."
           ::= { hpicfDomains 1 }


       -- Placeholder for registering object modules.  Note that the
       -- MODULE-IDENTITY, MODULE-COMPLIANCE, and OBJECT-GROUP
       -- definitions for each module are declared beneath these
       -- branches.

       hpicfObjectModules OBJECT IDENTIFIER ::= { hpicfAdmin 2 }

    -- icfSecurityMib    OBJECT IDENTIFIER ::= { hpicfObjectModules 1 }
    -- hpicfChainMib     OBJECT IDENTIFIER ::= { hpicfObjectModules 2 }
    -- hpicfChassisMib   OBJECT IDENTIFIER ::= { hpicfObjectModules 3 }
    -- hpicfDownloadMib  OBJECT IDENTIFIER ::= { hpicfObjectModules 4 }
    -- hpicfBasicMib     OBJECT IDENTIFIER ::= { hpicfObjectModules 5 }
    -- hpicfStackMib     OBJECT IDENTIFIER ::= { hpicfObjectModules 6 }
    -- hpicfLinkTestMib  OBJECT IDENTIFIER ::= { hpicfObjectModules 7 }
    -- hpicfGenRptrMib   OBJECT IDENTIFIER ::= { hpicfObjectModules 8 }
    -- hpicf8023RptrMib  OBJECT IDENTIFIER ::= { hpicfObjectModules 9 }
    -- icfVgRepeaterMib  OBJECT IDENTIFIER ::= { hpicfObjectModules 10 }
    -- hpicfVgRptrMib    OBJECT IDENTIFIER ::= { hpicfObjectModules 11 }
    -- hpicfFaultFinderMib
    --                   OBJECT IDENTIFIER ::= { hpicfObjectModules 12 }


       -- Placeholder for registering agent capabilities modules

       hpicfAgentModules OBJECT IDENTIFIER ::= { hpicfAdmin 3 }


       -- Placeholders for branches allocated to agent capabilities
       -- modules

    -- hpicfETwistHubAgentsMib
    --                   OBJECT IDENTIFIER ::= { hpicfAgentModules 1 }
    -- hpicfETwistBridgeAgentsMib
    --                   OBJECT IDENTIFIER ::= { hpicfAgentModules 2 }
    -- hpicfAdvStk8023AgentsMib
    --                   OBJECT IDENTIFIER ::= { hpicfAgentModules 3 }
    -- hpicfAdvStkVGAgentsMib
    --                   OBJECT IDENTIFIER ::= { hpicfAgentModules 4 }


       -- Placeholders for branches allocated to other MIB modules
       -- under the hpicfObjects node

       hpicfCommon       OBJECT IDENTIFIER ::= { hpicfObjects 1 }
       hpicfRepeater     OBJECT IDENTIFIER ::= { hpicfObjects 2 }
       hpicfVg           OBJECT IDENTIFIER ::= { hpicfObjects 3 }
       hpicfGenericRepeater  
                         OBJECT IDENTIFIER ::= { hpicfObjects 4 }
    -- hpicfSwitch       OBJECT IDENTIFIER ::= { hpicfObjects 5 }



       -- Branches for registering HP ICF notifications

       hpicfCommonTraps  OBJECT IDENTIFIER ::= { hpicfNotifications 1 }
       hpicfCommonTrapsPrefix
                         OBJECT IDENTIFIER ::= { hpicfCommonTraps 0 }

       hpicf8023RptrTraps
                         OBJECT IDENTIFIER ::= { hpicfNotifications 2 }
       hpicf8023RptrTrapsPrefix
                         OBJECT IDENTIFIER ::= { hpicf8023RptrTraps 0 }

       hpicfVgRptrTraps  OBJECT IDENTIFIER ::= { hpicfNotifications 3 }
       hpicfVgRptrTrapsPrefix
                         OBJECT IDENTIFIER ::= { hpicfVgRptrTraps 0 }

       hpicfGenRptrTraps OBJECT IDENTIFIER ::= { hpicfNotifications 4 }
       hpicfGenRptrTrapsPrefix
                         OBJECT IDENTIFIER ::= { hpicfGenRptrTraps 0 }



       -- HP ICF Device Identifiers

       system            OBJECT IDENTIFIER ::= { nm 3 }
       netElement        OBJECT IDENTIFIER ::= { system 7 }


       bridge            OBJECT IDENTIFIER ::= { netElement 1 }

       bridge1010 OBJECT-IDENTITY
           STATUS      current
           DESCRIPTION "The authoritative identifier for the 
                       HP 28673A 10:10 LAN Bridge."
           ::= { bridge 1 }

       bridgeRemote OBJECT-IDENTITY
           STATUS      current
           DESCRIPTION "The authoritative identifier for the
                       HP 28674A/B Remote Bridge."
           ::= { bridge 2 }

       eswitch OBJECT-IDENTITY
           STATUS      current
           DESCRIPTION "The authoritative identifier for the
                       HP J2418A EtherTwist LAN Switch."
           ::= { bridge 3 }

       eswitch2 OBJECT-IDENTITY
           STATUS      current
           DESCRIPTION "The authoritative identifier for the
                       HP J2980A AdvanceStack LAN Switch-16."
           ::= { bridge 8 }

       netSwitch100 OBJECT-IDENTITY
           STATUS      current
           DESCRIPTION "The authoritative identifier for the
                       HP J3126A AdvanceStack Switch 100."
           ::= { bridge 9 }

       netSwitch200 OBJECT-IDENTITY
           STATUS      current
           DESCRIPTION "The authoritative identifier for the
                       HP J3125A AdvanceStack Switch 200."
           ::= { bridge 10 }


       router            OBJECT IDENTIFIER ::= { netElement 2 }

       icfRouterER OBJECT-IDENTITY
           STATUS      current
           DESCRIPTION "The authoritative identifier for the
                       HP 27285A Router ER."
           ::= { router 1 }

       icfRouterTR OBJECT-IDENTITY
           STATUS      current
           DESCRIPTION "The authoritative identifier for the
                       HP 27286A Router TR."
           ::= { router 2 }

       icfRouterSR OBJECT-IDENTITY
           STATUS      current
           DESCRIPTION "The authoritative identifier for the
                       HP 27288A Router SR."
           ::= { router 3 }

       icfRouterFR OBJECT-IDENTITY
           STATUS      current
           DESCRIPTION "The authoritative identifier for the
                       HP 27289A Router FR."
           ::= { router 4 }

       icfRouterLR OBJECT-IDENTITY
           STATUS      current
           DESCRIPTION "The authoritative identifier for the
                       HP Router LR."
           ::= { router 5 }

       icfRouterBR OBJECT-IDENTITY
           STATUS      current
           DESCRIPTION "The authoritative identifier for the
                       HP 27290A Router BR."
           ::= { router 6 }

       icfRouterPR OBJECT-IDENTITY
           STATUS      current
           DESCRIPTION "The authoritative identifier for the
                       HP J2540A Router PR."
           ::= { router 7 }

       icfRouter650 OBJECT-IDENTITY
           STATUS      current
           DESCRIPTION "The authoritative identifier for the
                       HP J2430A AdvanceStack Router 650."
           ::= { router 8 }

       icfRouter230 OBJECT-IDENTITY
           STATUS      current
           DESCRIPTION "The authoritative identifier for the
                       HP J2540B Router 230."
           ::= { router 9 }

       icfRouter250 OBJECT-IDENTITY
           STATUS      current
           DESCRIPTION "The authoritative identifier for the
                       HP 27289B Router 250."
           ::= { router 10 }

       icfRouter255 OBJECT-IDENTITY
           STATUS      current
           DESCRIPTION "The authoritative identifier for the
                       HP J2543A Router 255."
           ::= { router 11 }

       icfRouter210 OBJECT-IDENTITY
           STATUS      current
           DESCRIPTION "The authoritative identifier for the
                       HP J2628A AdvanceStack Router 210."
           ::= { router 12 }

       icfRouter650Engine OBJECT-IDENTITY
           STATUS      current
           DESCRIPTION "The authoritative identifier for the routing
                       engine card for the HP J2430A AdvanceStack
                       Router 650."
           ::= { icfRouter650 2 }

       icfRouter650Port4E OBJECT-IDENTITY
           STATUS      current
           DESCRIPTION "The authoritative identifier for the
                       HP J2435A AdvanceStack Router 4E Port Module."
           ::= { icfRouter650 3 }

       icfRouter650Port4S OBJECT-IDENTITY
           STATUS      current
           DESCRIPTION "The authoritative identifier for the
                       HP J2434A AdvanceStack Router 4S Port Module."
           ::= { icfRouter650 4 }

       icfRouter650Port4T OBJECT-IDENTITY
           STATUS      current
           DESCRIPTION "The authoritative identifier for the
                       HP J2437A AdvanceStack Router 4T Port Module."
           ::= { icfRouter650 5 }

       icfRouter650PortFDDI OBJECT-IDENTITY
           STATUS      current
           DESCRIPTION "The authoritative identifier for the
                       HP J2436A AdvanceStack Router FDDI Port Module."
           ::= { icfRouter650 6 }

       icfRouter650Port100VG OBJECT-IDENTITY
           STATUS      current
           DESCRIPTION "The authoritative identifier for the
                       HP J2438A AdvanceStack Router 100VG Port
                       Module."
           ::= { icfRouter650 7 }


       hub               OBJECT IDENTIFIER ::= { netElement 5 }

       etherTwist12 OBJECT-IDENTITY
           STATUS      current
           DESCRIPTION "The authoritative identifier for the
                       HP 27288A/B EtherTwist Hub PLUS."
           ::= { hub 1 }

       fiberOptic OBJECT-IDENTITY
           STATUS      current
           DESCRIPTION "The authoritative identifier for the
                       HP 28682A Fiber-Optic Hub PLUS."
           ::= { hub 3 }

       etherTwist48 OBJECT-IDENTITY
           STATUS      current
           DESCRIPTION "The authoritative identifier for the
                       HP 28699A EtherTwist Hub PLUS/48."
           ::= { hub 4 }

       thinLAN OBJECT-IDENTITY
           STATUS      current
           DESCRIPTION "The authoritative identifier for the
                       HP 28692A ThinLAN Hub PLUS."
           ::= { hub 5 }

       etherTwist24S OBJECT-IDENTITY
           STATUS      current
           DESCRIPTION "The authoritative identifier for the
                       HP J2355A EtherTwist Secure Hub PLUS/24S"
           ::= { hub 6 }

       advStack12 OBJECT-IDENTITY
           STATUS      current
           DESCRIPTION "The authoritative identifier for the
                       HP J2600A AdvanceStack 10Base-T Hub-12"
           ::= { hub 7 }

       advStack24 OBJECT-IDENTITY
           STATUS      current
           DESCRIPTION "The authoritative identifier for the
                       HP J2601A/B AdvanceStack 10Base-T Hub-24."
           ::= { hub 8 }

       advStack48 OBJECT-IDENTITY
           STATUS      current
           DESCRIPTION "The authoritative identifier for the
                       HP J2602A/B AdvanceStack 10Base-T Hub-48."
           ::= { hub 9 }

       advStackVg15 OBJECT-IDENTITY
           STATUS      current
           DESCRIPTION "The authoritative identifier for the
                       HP J2410A AdvanceStack 100VG Hub-15."
           ::= { hub 10 }

       advStackU8 OBJECT-IDENTITY
           STATUS      current
           DESCRIPTION "The authoritative identifier for the
                       HP J2610A AdvanceStack 10Base-T Hub-8U."
           ::= { hub 11 }

       advStackU16 OBJECT-IDENTITY
           STATUS      current
           DESCRIPTION "The authoritative identifier for the
                       HP J2611A AdvanceStack 10Base-T Hub-16U."
           ::= { hub 12 }

       advStackVg6 OBJECT-IDENTITY
           STATUS      current
           DESCRIPTION "The authoritative identifier for the
                       HP J2413A AdvanceStack 100VG Hub-7M."
           ::= { hub 13 }

       advStackVg12 OBJECT-IDENTITY
           STATUS      current
           DESCRIPTION "The authoritative identifier for the
                       HP J2415A AdvanceStack 100VG Hub-14."
           ::= { hub 14 }

       hpAdvStkEnetSH12R OBJECT-IDENTITY
           STATUS      current
           DESCRIPTION "The authoritative identifier for the
                       HP J3200A AdvanceStack 10BT Switching Hub-12R."
           ::= { hub 15 }

       hpAdvStkEnetSH24R OBJECT-IDENTITY
           STATUS      current
           DESCRIPTION "The authoritative identifier for the
                       HP J3202A AdvanceStack 10BT Switching Hub-24R."
           ::= { hub 16 }

       hpAdvStkEnetSH24T OBJECT-IDENTITY
           STATUS      current
           DESCRIPTION "The authoritative identifier for the
                       HP J3204A AdvanceStack 10BT Switching Hub-24T."
           ::= { hub 17 }

       hpAdvStk100Tx12TM OBJECT-IDENTITY
           STATUS      current
           DESCRIPTION "The authoritative identifier for the
                       HP J3233A AdvanceStack 100B-TX Hub-12TM w/MGMT."
           ::= { hub 18 }

       hp10THub16M OBJECT-IDENTITY
           STATUS      current
           DESCRIPTION "The authoritative identifier for the
                       HP J3188A 10Base-T Hub-16M."
           ::= { hub 19}

       hp10BaseTHub12M OBJECT-IDENTITY
           STATUS      current
           DESCRIPTION "The authoritative identifier for the
                       HP J3301A 10Base-T Hub-12M"
           ::= { hub 20 }

       hp10BaseTHub24M OBJECT-IDENTITY
           STATUS      current
           DESCRIPTION "The authoritative identifier for the
                       HP J3303A 10Base-T Hub-24M"
           ::= { hub 21 }

       hpProCurve10T100THub12M OBJECT-IDENTITY
           STATUS      current
           DESCRIPTION "The authoritative identifier for the
                       HP J3288A ProCurve 100Base-T Hub 12M"
           ::= { hub 22 }

       hpProCurve10T100THub24M OBJECT-IDENTITY
           STATUS      current
           DESCRIPTION "The authoritative identifier for the
                       HP J3289A ProCurve 100Base-T Hub 24M"
           ::= { hub 23 }


       chassis           OBJECT IDENTIFIER ::= { netElement 8 }

       repeaterAgent OBJECT-IDENTITY
           STATUS      current
           DESCRIPTION "The authoritative identifier for the
                       HP J2603A/B AdvanceStack Ethernet SNMP module."
           ::= { chassis 1 }


       chassisAgents     OBJECT IDENTIFIER ::= { chassis 2 }

       icfVgAgent OBJECT-IDENTITY
           STATUS      current
           DESCRIPTION "The authoritative identifier for the
                       HP J2414A AdvanceStack 100VG/ET SNMP/Bridge
                       Module."
           ::= { chassisAgents 1 }

       icfVgAgent2 OBJECT-IDENTITY
           STATUS      current
           DESCRIPTION "The authoritative identifier for the
                       HP J2414B AdvanceStack 100VG/ET SNMP/Bridge
                       Module."
           ::= { chassisAgents 3 }

       hpicfEnetSMM OBJECT-IDENTITY
           STATUS      current
           DESCRIPTION "The authoritative identifier for the
                       HPJ3133A AdvanceStack 8U/16U SNMP Module."
           ::= { chassisAgents 4 }

       hpAdvStkEnetSHAgent OBJECT-IDENTITY
           STATUS      current
           DESCRIPTION "The authoritative identifier for the
                       HPJ3210A AdvanceStack 10BT Switching Hub
                       Management Module."
           ::= { chassisAgents 5 }

       hpAdvStkSwStackTopMgmt OBJECT-IDENTITY
           STATUS      current
           DESCRIPTION "The authoritative identifier for the
                       HPJ3179A AdvanceStack Switch StackTop Management
                       Module."
           ::= { chassisAgents 6 }

       hpSwitch8000CpuCard OBJECT-IDENTITY
           STATUS      current
           DESCRIPTION "The authoritative identifier for the
                       HP J4110A Switch 8000M and HP J4121A Switch
                       4000M CPU card."
           ::= { chassisAgents 7 }


       icfSensors        OBJECT IDENTIFIER ::= { chassis 3 }

       icfPowerSupplySensor OBJECT-IDENTITY
           STATUS      current
           DESCRIPTION "Identifier for a power supply sensor type."
           ::= { icfSensors 1 }

       icfFanSensor OBJECT-IDENTITY
           STATUS      current
           DESCRIPTION "Identifier for a fan sensor type."
           ::= { icfSensors 2 }

       icfTemperatureSensor OBJECT-IDENTITY
           STATUS      current
           DESCRIPTION "Identifier for a temperature sensor type."
           ::= { icfSensors 3 }

       icfFutureSlotSensor OBJECT-IDENTITY
           STATUS      current
           DESCRIPTION "Identifier for a FutureSlot sensor type."
           ::= { icfSensors 4 }


       icfCards          OBJECT IDENTIFIER ::= { chassis 4 }

       icfUnidentifiedCard OBJECT-IDENTITY
           STATUS      current
           DESCRIPTION "Used to indicate that a module is installed in
                       a slot in a chassis, but the agent is unable to
                       identify it."
           ::= { icfCards 1 }

       hpAdvStkEnetSHSwitch OBJECT-IDENTITY
           STATUS      current
           DESCRIPTION "The authoritative identifier for the
                       HP J3212A AdvanceStack 10BT Switching Hub Switch
                       Module."
           ::= { icfCards 2 }

       hpAdvStkSwStackExpander OBJECT-IDENTITY
           STATUS      current
           DESCRIPTION "The authoritative identifier for the
                       HPJ3180A AdvanceStack Switch Stack Expander
                       Module."
           ::= { icfCards 3 }

       hpicfStacks       OBJECT IDENTIFIER ::= { chassis 5 }

       hpAdvStkEnetSHStack OBJECT-IDENTITY
           STATUS      current
           DESCRIPTION "The authoritative identifier for a stack of
                       HP AdvanceStack 10Base-T Switching Hubs."
           ::= { hpicfStacks 1 }


       hpicfBackplanes   OBJECT IDENTIFIER ::= { chassis 6 }

       hpAdvStkEnetSHExtSeg OBJECT-IDENTITY
           STATUS      current
           DESCRIPTION "The authoritative identifier for an inter-box
                       repeater segment in a stack of HP AdvanceStack
                       10Base-T Switching Hubs."
           ::= { hpicfBackplanes 1 }

       hpAdvStkEnetSHIntSeg OBJECT-IDENTITY
           STATUS      current
           DESCRIPTION "The authoritative identifier for a repeater
                       segment that is internal to a single box in
                       a stack of HP AdvanceStack 10Base-T Switching
                       Hubs."
           ::= { hpicfBackplanes 2 }

       hp10BaseTHubSeg OBJECT-IDENTITY
           STATUS      current
           DESCRIPTION "The authoritative identifier for a repeater
                       segment in an HP 10Base-T Hub-12M or HP
                       10Base-T Hub-24M."
           ::= { hpicfBackplanes 3 }

       hpSwitchBackplane OBJECT-IDENTITY
           STATUS      current
           DESCRIPTION "The authoritative identifier for an HP Switch
                       backplane."
           ::= { hpicfBackplanes 4 }

       hp100BaseTHubSeg OBJECT-IDENTITY
           STATUS      current
           DESCRIPTION "The authoritative identifier for a repeater
                       segment in an HP ProCurve 100Base-T Hub 12M
                       or HP ProCurve 100Base-T Hub 24M."
           ::= { hpicfBackplanes 5 }



       hpicfSlots        OBJECT IDENTIFIER ::= { chassis 7 }

       hpAdvStkEnetSHAgentSlot OBJECT-IDENTITY
           STATUS      current
           DESCRIPTION "The authoritative identifier for the Management
                       Slot in an HP AdvanceStack 10Base-T Switching
                       Hub."
           ::= { hpicfSlots 1 }

       hpAdvStkEnetSHIOSlot OBJECT-IDENTITY
           STATUS      current
           DESCRIPTION "The authoritative identifier for the Expansion
                       Slot in an HP AdvanceStack 10Base-T Switching
                       Hub."
           ::= { hpicfSlots 2 }

       hpAdvStkSwStackMgmtSlot OBJECT-IDENTITY
           STATUS      current
           DESCRIPTION "The authoritative identifier for the
                       Management/Stacking Slot in an HP AdvanceStack
                       Switch 208 or Switch 224."
           ::= { hpicfSlots 3 }

       hpAdvStkSwStackExpSlot OBJECT-IDENTITY
           STATUS      current
           DESCRIPTION "The authoritative identifier for the
                       Expansion Slot in an HP AdvanceStack Switch 208
                       or Switch 224."
           ::= { hpicfSlots 4 }

       hpSwitch8000PowerSupplyBay OBJECT-IDENTITY
           STATUS      current
           DESCRIPTION "The authoritative identifier for a
                       power supply bay in an HP Switch 8000 or
                       HP Switch 4000."
           ::= { hpicfSlots 5 }

       hpSwitch8000CpuSlot OBJECT-IDENTITY
           STATUS      current
           DESCRIPTION "The authoritative identifier for the CPU
                       slot in an HP Switch 8000 or HP Switch 4000."
           ::= { hpicfSlots 6 }

       hpSwitch8000PortSlot OBJECT-IDENTITY
           STATUS      current
           DESCRIPTION "The authoritative identifier for a port
                       module slot in an HP Switch 8000, HP Switch
                       4000, HP Switch 1600, HP Switch 2400 or HP
                       Switch 2424."
           ::= { hpicfSlots 7 }


       hpicfHubPorts     OBJECT IDENTIFIER ::= { chassis 8 }

       hpAdvStkEnetSHExtPort OBJECT-IDENTITY
           STATUS      current
           DESCRIPTION "The authoritative identifier for a repeater
                        port which has an external connector on an HP
                       AdvanceStack 10Base-T Switching Hub."
           ::= { hpicfHubPorts 1 }

       hpAdvStkEnetSHIntPort OBJECT-IDENTITY
           STATUS      current
           DESCRIPTION "The authoritative identifier for a repeater
                       port which does not have an external connector
                       on an HP AdvanceStack 10Base-T Switching Hub.
                       This port may be used to connect to an interface
                       on an expansion module."
           ::= { hpicfHubPorts 2 }

       hpAdvStkEnetSHAgentPort OBJECT-IDENTITY
           STATUS      current
           DESCRIPTION "The authoritative identifier for an internal
                       repeater port used to connect to an interface on
                       a management module in an HP AdvanceStack
                       10Base-T Switching Hub."
           ::= { hpicfHubPorts 3 }

       hp10BaseTHubPort OBJECT-IDENTITY
           STATUS      current
           DESCRIPTION "The authoritative identifier for a repeater
                       port which has an external connector on an HP
                       10Base-T Hub-12M or an HP 10Base-T Hub-24M."
           ::= { hpicfHubPorts 4 }

       hp10BaseTHubAgentPort OBJECT-IDENTITY
           STATUS      current
           DESCRIPTION "The authoritative identifier for an internal
                       repeater port used to connect to an agent
                       interface in an HP 10Base-T Hub-12M or an HP
                       10Base-T Hub-24M."
           ::= { hpicfHubPorts 5 }

       hp10T100THubPort OBJECT-IDENTITY
           STATUS      current
           DESCRIPTION "The authoritative identifier for a 10/100
                       repeater port that has an external connector
                       on an HP ProCurve 100Base-T Hub."
           ::= { hpicfHubPorts 6 }

       hp100BaseTHubAgentPort OBJECT-IDENTITY
           STATUS      current
           DESCRIPTION "The authoritative identifier for an internal
                       100Mbit repeater port used to connect to an
                       agent interface in an HP ProCurve 100Base-T
                       Hub."
           ::= { hpicfHubPorts 7 }


       hpicfEnetChipSets OBJECT IDENTIFIER ::= { chassis 9 }

       hpicfEnetChipSetHydra OBJECT-IDENTITY
           STATUS      current
           DESCRIPTION "The authoritative identifier for the
                       HP Hydra 4-interface Ethernet LAN controller."
           ::= { hpicfEnetChipSets 1 }

       hpicfEnetChipSetGT48001 OBJECT-IDENTITY
           STATUS      current
           DESCRIPTION "The authoritative identifier for the
                       GT48001 8-interface switch chip."
           ::= { hpicfEnetChipSets 2 }

       hpicfEnetChipSetPentagon OBJECT-IDENTITY
           STATUS      current
           DESCRIPTION "The authoritative identifier for the
                       HP Pentagon ASIC."
           ::= { hpicfEnetChipSets 3 }


       hpicfSwitchPorts  OBJECT IDENTIFIER ::= { chassis 10 }

       hpicfSwitchPort10T100TX OBJECT-IDENTITY
           STATUS      current
           DESCRIPTION "The authoritative identifier for an IEEE
                       802.3 10BASE-T/100BASE-TX autonegotiating port
                       on an HP switch."
           ::= { hpicfSwitchPorts 1 }

       hpicfSwitchPort100FX  OBJECT-IDENTITY
           STATUS      current
           DESCRIPTION "The authoritative identifier for an IEEE
                       802.3 100BASE-FX port on an HP switch."
           ::= { hpicfSwitchPorts 2 }

       hpicfSwitchPort10FL OBJECT-IDENTITY
           STATUS      current
           DESCRIPTION "The authoritative identifier for an IEEE
                       802.3 10BASE-FL port on an HP switch."
           ::= { hpicfSwitchPorts 3 }

       hpicfSwitchPort1000SX OBJECT-IDENTITY
           STATUS      current
           DESCRIPTION "The authoritative identifier for an IEEE
                       802.3 1000BASE-SX port on an HP switch."
           ::= { hpicfSwitchPorts 4 }

       hpicfSwitchPort10T OBJECT-IDENTITY
           STATUS      current
           DESCRIPTION "The authoritative identifier for an IEEE
                       802.3 10BASE-T port on an HP switch."
           ::= { hpicfSwitchPorts 5 }

       hpicfSwitchPort1000LX OBJECT-IDENTITY
           STATUS      current
           DESCRIPTION "The authoritative identifier for an IEEE
                       802.3 1000BASE-LX port on an HP switch."
           ::= { hpicfSwitchPorts 6 }

       hpicfSwitchPort1000T OBJECT-IDENTITY
           STATUS      current
           DESCRIPTION "The authoritative identifier for an IEEE
                       802.3 1000BASE-T port on an HP switch."
           ::= { hpicfSwitchPorts 7 }

       hpicfMAUTypes     OBJECT IDENTIFIER ::= { chassis 11 }

       hpicfMauType1000BaseSXHD OBJECT-IDENTITY
           STATUS      current
           DESCRIPTION "IEEE 802.3 X fiber over short-wavelength
                       laser PMD (clause 38), half-duplex."
           ::= { hpicfMAUTypes 1 }

       hpicfMauType1000BaseSXFD OBJECT-IDENTITY
           STATUS      current
           DESCRIPTION "IEEE 802.3 X fiber over short-wavelength
                       laser PMD (clause 38), full-duplex."
           ::= { hpicfMAUTypes 2 }

       hpicfMauType1000BaseLXHD OBJECT-IDENTITY
           STATUS      current
           DESCRIPTION "IEEE 802.3 X fiber over long-wavelength
                       laser PMD (clause 38), half-duplex."
           ::= { hpicfMAUTypes 3 }

       hpicfMauType1000BaseLXFD OBJECT-IDENTITY
           STATUS      current
           DESCRIPTION "IEEE 802.3 X fiber over long-wavelength
                       laser PMD (clause 38), full-duplex."
           ::= { hpicfMAUTypes 4 }

       hpicfMauType1000BaseTHD OBJECT-IDENTITY
           STATUS      current
           DESCRIPTION "IEEE 802.3 four-pair Category 5 UTP
                       PHY (clause 40), half-duplex."
           ::= { hpicfMAUTypes 5 }

       hpicfMauType1000BaseTFD OBJECT-IDENTITY
           STATUS      current
           DESCRIPTION "IEEE 802.3 four-pair Category 5 UTP
                       PHY (clause 40), full-duplex."
           ::= { hpicfMAUTypes 6 }


       hpEtherSwitch     OBJECT IDENTIFIER ::= { netElement 11 }

       hpAdvSwitch2000 OBJECT-IDENTITY
           STATUS      current
           DESCRIPTION "The authoritative identifier for the
                       HP J3100A AdvanceStack Switch 2000."
           ::= { hpEtherSwitch 1 }

       hpAdvSwitch2000B OBJECT-IDENTITY
           STATUS      current
           DESCRIPTION "The authoritative identifier for the
                       HP J3100B AdvanceStack Switch 2000B."
           ::= { hpEtherSwitch 2 }

       hpAdvSwitch800T OBJECT-IDENTITY
           STATUS      current
           DESCRIPTION "The authoritative identifier for the
                       HP J3245A AdvanceStack Switch 800T."
           ::= { hpEtherSwitch 3 }

       hpAdvSwitch200   OBJECT-IDENTITY
           STATUS      current
           DESCRIPTION "The authoritative identifier for the
                       HP J3175A AdvanceStack Switch 208T and
                       HP J3177A AdvanceStack Switch 224T."
           ::= { hpEtherSwitch  4 }

       hpSwitch212M OBJECT-IDENTITY
           STATUS      current
           DESCRIPTION "The authoritative identifier for the
                       HP J3298A Switch 212M."
           ::= { hpEtherSwitch 5 }

       hpSwitch224M OBJECT-IDENTITY
           STATUS      current
           DESCRIPTION "The authoritative identifier for the
                       HP J3299A Switch 224M."
           ::= { hpEtherSwitch 6 }

       hpSwitch8000 OBJECT-IDENTITY
           STATUS      current
           DESCRIPTION "The authoritative identifier for the
                       HP J4110A Switch 8000M."
           ::= { hpEtherSwitch 7 }

       hpSwitch1600 OBJECT-IDENTITY
           STATUS      current
           DESCRIPTION "The authoritative identifier for the
                       HP J4120A Switch 1600M."
           ::= { hpEtherSwitch 8 }

       hpSwitch4000 OBJECT-IDENTITY
           STATUS      current
           DESCRIPTION "The authoritative identifier for the
                       HP J4121A Switch 4000M."
           ::= { hpEtherSwitch 9 }

       hpSwitch2400 OBJECT-IDENTITY
           STATUS      current
           DESCRIPTION "The authoritative identifier for the
                       HP J4122A Switch 2400M."
           ::= { hpEtherSwitch 10 }

       hpSwitch2424 OBJECT-IDENTITY
           STATUS      current
           DESCRIPTION "The authoritative identifier for the
                       HP J4122B Switch 2424M."
           ::= { hpEtherSwitch 11 }


       -- different cards for Switch 2000

       hpSwitchPortModuleET4 OBJECT-IDENTITY
           STATUS      current
           DESCRIPTION "The authoritative identifier for the
                       HP J3102A AdvanceStack Switch Ethernet Port
                       Module."
           ::= { hpAdvSwitch2000 1 }

       hpSwitchPortModuleVG2 OBJECT-IDENTITY
           STATUS      current
           DESCRIPTION "The authoritative identifier for the
                       HP J3103A AdvanceStack Switch 100VG Port
                       Module."
           ::= { hpAdvSwitch2000 2 }

       hpSwitchPortModule10FL OBJECT-IDENTITY
           STATUS      current
           DESCRIPTION "The authoritative identifier for the
                       HP AdvanceStack Switch 10BaseFL Port Module."
           ::= { hpAdvSwitch2000 3 }

       hpSwitchPortModuleFDDI OBJECT-IDENTITY
           STATUS      current
           DESCRIPTION "The authoritative identifier for the
                       HP AdvanceStack Switch FDDI Port Module."
           ::= { hpAdvSwitch2000 4 }

       hpSwitchPortModuleTX2 OBJECT-IDENTITY
           STATUS      current
           DESCRIPTION "The authoritative identifier for the
                       HP AdvanceStack Switch 100BaseT Port Module."
           ::= { hpAdvSwitch2000 5 }

       hpSwitchPortModuleATM OBJECT-IDENTITY
           STATUS      current
           DESCRIPTION "The authoritative identifier for the
                       HP AdvanceStack Switch ATM Port Module."
           ::= { hpAdvSwitch2000 6 }

       -- different cards for Switch 8000/4000/1600/2400/2424 family

       hpSwitchPortModule100TX8 OBJECT-IDENTITY
           STATUS      current
           DESCRIPTION "The authoritative identifier for the
                       HP J4111A 8-port 10/100Base-TX module."
           ::= { hpSwitch8000 1 }

       hpSwitchPortModule100FX4 OBJECT-IDENTITY
           STATUS      current
           DESCRIPTION "The authoritative identifier for the
                       HP J4112A 4-port 100Base-FX module."
           ::= { hpSwitch8000 2 }

       hpSwitchPortModule10FL4 OBJECT-IDENTITY
           STATUS      current
           DESCRIPTION "The authoritative identifier for the
                       HP J4118A 4-port 10Base-FL module."
           ::= { hpSwitch8000 3 }

       hpSwitchPortModuleGigSX OBJECT-IDENTITY
           STATUS      current
           DESCRIPTION "The authoritative identifier for the
                       HP J4113A 1-port Gigabit SX module."
           ::= { hpSwitch8000 4 }

       hpSwitchPortModuleGigLX OBJECT-IDENTITY
           STATUS      current
           DESCRIPTION "The authoritative identifier for the
                       HP J4114A 1-port Gigabit LX module."
           ::= { hpSwitch8000 5 }

       hpSwitchPortModule2Gig OBJECT-IDENTITY
           STATUS      current
           DESCRIPTION "The authoritative identifier for the
                       HP J4130A 2-port Gigabit module."
           ::= { hpSwitch8000 6 }


       END
