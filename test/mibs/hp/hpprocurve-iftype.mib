-- automatically generated by mosy 7.1 #1 (hprnljf), do not edit!

IANAifType-MIB DEFINITIONS ::= BEGIN


IMPORTS
	mib-2
		FROM SNMPv2-SMI;
-- created from ianaifType (97101011123Z)

ianaifType OBJECT IDENTIFIER ::= { mib-2  30 }

IANAifType ::=
    INTEGER {
 other(1),
 regular1822(2),
 hdh1822(3),
 ddnX25(4),
 rfc877x25(5),
 ethernetCsmacd(6),
 iso88023Csmacd(7),
 iso88024TokenBus(8),
 iso88025TokenRing(9),
 iso88026Man(10),
 starLan(11),
 proteon10Mbit(12),
 proteon80Mbit(13),
 hyperchannel(14),
 fddi(15),
 lapb(16),
 sdlc(17),
 ds1(18),
 e1(19),
 basicISDN(20),
 primaryISDN(21),
 propPointToPointSerial(22),
 ppp(23),
 softwareLoopback(24),
 eon(25),
 ethernet3Mbit(26),
 nsip(27),
 slip(28),
 ultra(29),
 ds3(30),
 sip(31),
 frameRelay(32),
 rs232(33),
 para(34),
 arcnet(35),
 arcnetPlus(36),
 atm(37),
 miox25(38),
 sonet(39),
 x25ple(40),
 iso88022llc(41),
 localTalk(42),
 smdsDxi(43),
 frameRelayService(44),
 v35(45),
 hssi(46),
 hippi(47),
 modem(48),
 aal5(49),
 sonetPath(50),
 sonetVT(51),
 smdsIcip(52),
 propVirtual(53),
 propMultiplexor(54),
 ieee80212(55),
 fibreChannel(56),
 hippiInterface(57),
 frameRelayInterconnect(58),
 aflane8023(59),
 aflane8025(60),
 cctEmul(61),
 fastEther(62),
 isdn(63),
 v11(64),
 v36(65),
 g703at64k(66),
 g703at2mb(67),
 qllc(68),
 fastEtherFX(69),
 channel(70),
 ieee80211(71),
 ibm370parChan(72),
 escon(73),
 dlsw(74),
 isdns(75),
 isdnu(76),
 lapd(77),
 ipSwitch(78),
 rsrb(79),
 atmLogical(80),
 ds0(81),
 ds0Bundle(82),
 bsc(83),
 async(84),
 cnr(85),
 iso88025Dtr(86),
 eplrs(87),
 arap(88),
 propCnls(89),
 hostPad(90),
 termPad(91),
 frameRelayMPI(92),
 x213(93),
 adsl(94),
 radsl(95),
 sdsl(96),
 vdsl(97),
 iso88025CRFPInt(98),
 myrinet(99),
 voiceEM(100),
 voiceFXO(101),
 voiceFXS(102),
 voiceEncap(103),
 voiceOverIp(104),
 atmDxi(105),
 atmFuni(106),
 atmIma(107),
 pppMultilinkBundle(108),
 ipOverCdlc(109),
 ipOverClaw(110),
 stackToStack(111),
 virtualIpAddress(112),
 mpc(113),
 ipOverAtm(114),
 iso88025Fiber(115),
 tdlc(116),
 gigabitEthernet(117),
 hdlc(118),
 lapf(119),
 v37(120),
 x25mlp(121),
 x25huntGroup(122),
 trasnpHdlc(123),
 interleave(124),
 fast(125),
 ip(126),
 docsCableMaclayer(127),
 docsCableDownstream(128),
 docsCableUpstream(129),
 a12MppSwitch(130),
 tunnel(131),
 coffee(132),
 ces(133),
 atmSubInterface(134),
 l2vlan(135),
 l3ipvlan(136),
 l3ipxvlan(137)
 }

END
