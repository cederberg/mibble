-- automatically generated by mosy 7.1 #1 (hprnljf), do not edit!

HP-VLAN DEFINITIONS ::= BEGIN


IMPORTS
	enterprises
		FROM RFC1155-SMI
        OBJECT-TYPE
		FROM RFC-1212
	InterfaceIndex
		FROM IF-MIB
	RowStatus, DisplayString, PhysAddress
		FROM SNMPv2-TC;
hp OBJECT IDENTIFIER ::= { enterprises  11 }

nm OBJECT IDENTIFIER ::= { hp  2 }

icf OBJECT IDENTIFIER ::= { nm  14 }

hpicfObjects OBJECT IDENTIFIER ::= { icf  11 }

hpicfSwitch OBJECT IDENTIFIER ::= { hpicfObjects  5 }

hpSwitch OBJECT IDENTIFIER ::= { hpicfSwitch  1 }

hpVLAN OBJECT IDENTIFIER ::= { hpSwitch  3 }

-- created from hpVlanLevelOne (9510200000Z)

hpVlanLevelOne OBJECT IDENTIFIER ::= { hpVLAN  1 }

hpVlanObjects OBJECT IDENTIFIER ::= { hpVlanLevelOne  1 }

hpVlanTraps OBJECT IDENTIFIER ::= { hpVlanLevelOne  2 }

hpVlanConformance OBJECT IDENTIFIER ::= { hpVlanLevelOne  3 }

VlanID ::=
    INTEGER (1..65535)

ConfigStatus ::=
    INTEGER {
 active(1),
 notInService(2),
 notReady(3)
 }

hpVlanNumber OBJECT-TYPE
    SYNTAX  INTEGER
    ACCESS  read-only
    STATUS  mandatory
    DESCRIPTION
           "The number of currently defined VLANs in
                      the device. Though VLANs should be created
                      using contiguous VLAN IDs, this is not
                      mandatory. Gaps in the VLAN ID sequence may
                      also result from the deletion of existing
                      VLANs. Therefore, this value represents the
                      total number of VLANs in the device and should
                      not be used to indicate the highest VLAN ID
                      value currently in use."
    ::= { hpVlanObjects  1 }

hpVlanIdentTable OBJECT-TYPE
    SYNTAX  SEQUENCE OF HpVlanIdentEntry
    ACCESS  not-accessible
    STATUS  mandatory
    DESCRIPTION
           "A table describing the various VLANs that 
                      are currently defined for this device."
    ::= { hpVlanObjects  4 }

hpVlanIdentEntry OBJECT-TYPE
    SYNTAX  HpVlanIdentEntry
    ACCESS  not-accessible
    STATUS  mandatory
    DESCRIPTION
           "The row in the hpVlanIdentTable containing 
                      the general VLAN information."
    INDEX   { hpVlanIdentIndex }
    ::= { hpVlanIdentTable  1 }

HpVlanIdentEntry ::=
    SEQUENCE {
    hpVlanIdentIndex
        VlanID,

    hpVlanIdentName
        DisplayString,

    hpVlanIdentMode
        INTEGER,

    hpVlanIdentStatus
        RowStatus,

    hpVlanDot1QID
        INTEGER,

    hpVlanIdentState
        INTEGER
    }

hpVlanIdentIndex OBJECT-TYPE
    SYNTAX  VlanID
    ACCESS  not-accessible
    STATUS  mandatory
    DESCRIPTION
           "The VLAN ID which uniquely identifies a row  
                      in this table."
    ::= { hpVlanIdentEntry  1 }

hpVlanIdentName OBJECT-TYPE
    SYNTAX  DisplayString
    ACCESS  read-write
    STATUS  mandatory
    DESCRIPTION
           "The user defined textual name that is
                      associated with this VLAN."
    ::= { hpVlanIdentEntry  2 }

hpVlanIdentMode OBJECT-TYPE
    SYNTAX  INTEGER {
                 port(1),
                 mac(2)
               }
    ACCESS  read-only
    STATUS  mandatory
    DESCRIPTION
           "The mode of this VLAN. A VLAN can be either
                      port-based or MAC address-based. A port-based
                      VLAN supports a multiple addresses per VLAN 
                      port.
                      A MAC address-
                      based VLAN supports multiple MAC addresses 
                      per port such that VLAN address tables must be
                      consulted to determine the number of VLAN
                      clients."
    ::= { hpVlanIdentEntry  3 }

hpVlanIdentStatus OBJECT-TYPE
    SYNTAX  RowStatus
    ACCESS  read-write
    STATUS  mandatory
    DESCRIPTION
           "The status of a VLAN information entry."
    ::= { hpVlanIdentEntry  4 }

hpVlanDot1QID OBJECT-TYPE
    SYNTAX  INTEGER (1..4095)
    ACCESS  read-write
    STATUS  mandatory
    DESCRIPTION
           "The VLAN tag ID.  802.1Q"
    ::= { hpVlanIdentEntry  5 }

hpVlanIdentState OBJECT-TYPE
    SYNTAX  INTEGER {
                 up(1),
                 down(2)
               }
    ACCESS  read-only
    STATUS  mandatory
    DESCRIPTION
           "Current state of the VLAN.  If one port in the
		       VLAN is up, then that VLAN is up, otherwise it
		       is down."
    ::= { hpVlanIdentEntry  6 }

hpVlanMemberTable OBJECT-TYPE
    SYNTAX  SEQUENCE OF HpVlanMemberEntry
    ACCESS  not-accessible
    STATUS  mandatory
    DESCRIPTION
           "A table describing the members of the various  
                      VLANs that are currently defined for this device.
                      Interfaces can be associated with a pre-defined
                      VLAN (i.e., VLANs can be created by grouping
                      existing interfaces) by adding rows to this table.
                      Likewise, deleting rows from this table removes
                      the specified interface from the VLAN. 

                      Note that certain entries in this table will
                      automatically be created when a VLAN is created,
                      such as the entry associating a VLAN with its
                      propVirtual interface to the management and/or
                      forwarding entity on the device. These entries
                      are read-only and can not be manipulated via
                      the MIB."
    ::= { hpVlanObjects  5 }

hpVlanMemberEntry OBJECT-TYPE
    SYNTAX  HpVlanMemberEntry
    ACCESS  not-accessible
    STATUS  mandatory
    DESCRIPTION
           "The row in the hpVlanMemberTable containing the 
                      VLAN ID to Interface Group ifIndex mappings."
    INDEX   { hpVlanMemberIfIndex }
    ::= { hpVlanMemberTable  1 }

HpVlanMemberEntry ::=
    SEQUENCE {
    hpVlanMemberIfIndex
        InterfaceIndex,

    hpVlanMemberIndex
        VlanID
    }

hpVlanMemberIfIndex OBJECT-TYPE
    SYNTAX  InterfaceIndex
    ACCESS  not-accessible
    STATUS  mandatory
    DESCRIPTION
           "The ifIndex value which uniquely identifies
                      a row in the Interfaces Table. The corresponding
                      row in the Interfaces Table must exist prior 
                      to the index being used in this table."
    ::= { hpVlanMemberEntry  1 }

hpVlanMemberIndex OBJECT-TYPE
    SYNTAX  VlanID
    ACCESS  read-write
    STATUS  mandatory
    DESCRIPTION
           "The VLAN ID identifies the VLAN the interface
                       is in.
                       The corresponding 
                      row in the VLAN Ident Table must exist prior 
                      to the index being used in this table."
    ::= { hpVlanMemberEntry  2 }

hpVlanAddrTable OBJECT-TYPE
    SYNTAX  SEQUENCE OF HpVlanAddrEntry
    ACCESS  not-accessible
    STATUS  mandatory
    DESCRIPTION
           "A table describing the MAC addresses that
                      are currently associated with a specific
                      VLAN. Entries are added to and deleted
                      from this read-only table automatically
                      as they are learned from the network."
    ::= { hpVlanObjects  6 }

hpVlanAddrEntry OBJECT-TYPE
    SYNTAX  HpVlanAddrEntry
    ACCESS  not-accessible
    STATUS  mandatory
    DESCRIPTION
           "The row in the hpVlanAddrTable containing 
                      the VLAN ID to MAC address mappings."
    INDEX   { hpVlanAddrIndex }
    ::= { hpVlanAddrTable  1 }

HpVlanAddrEntry ::=
    SEQUENCE {
    hpVlanAddrIndex
        VlanID,

    hpVlanAddrPhysAddress
        PhysAddress
    }

hpVlanAddrIndex OBJECT-TYPE
    SYNTAX  VlanID
    ACCESS  not-accessible
    STATUS  mandatory
    DESCRIPTION
           "The VLAN ID which uniquely identifies a row  
                      in the VLAN Ident Table. The corresponding 
                      row in the VLAN Ident Table must exist prior 
                      to the index being present in this table."
    ::= { hpVlanAddrEntry  1 }

hpVlanAddrPhysAddress OBJECT-TYPE
    SYNTAX  PhysAddress
    ACCESS  read-only
    STATUS  mandatory
    DESCRIPTION
           "The MAC address of a node that is associated 
                      with a specific VLAN as identified by the
                      object hpVlanAddrIndex."
    ::= { hpVlanAddrEntry  2 }

hpVlanIdentConfigStatus OBJECT-TYPE
    SYNTAX  ConfigStatus
    ACCESS  read-only
    STATUS  deprecated
    DESCRIPTION
           "The status of a VLAN information table. If one or more
                      variables in this group were reconfigurated since last 
                      reboot and required reboot to take effect, the value of
                      this variable will be set to notInService."
    ::= { hpVlanObjects  7 }

hpVlanMemberTable2 OBJECT-TYPE
    SYNTAX  SEQUENCE OF HpVlanMemberEntry2
    ACCESS  not-accessible
    STATUS  mandatory
    DESCRIPTION
           "A table describing the VLANs on each particular port
		      along with tagging information."
    ::= { hpVlanObjects  8 }

hpVlanMemberEntry2 OBJECT-TYPE
    SYNTAX  HpVlanMemberEntry2
    ACCESS  not-accessible
    STATUS  mandatory
    DESCRIPTION
           "The row in the hpVlanMemberTable2 containing the
		      VLAN ID to interface group ifIndex mappings as well
		      the VLAN tagging information."
    INDEX   { hpVlanIdentIndex,  hpVlanMemberIfIndex }
    ::= { hpVlanMemberTable2  1 }

HpVlanMemberEntry2 ::=
    SEQUENCE {
    hpVlanMemberTagged2
        INTEGER
    }

hpVlanMemberTagged2 OBJECT-TYPE
    SYNTAX  INTEGER {
                 tagged(1),
                 untagged(2),
                 no(3)
               }
    ACCESS  read-write
    STATUS  mandatory
    DESCRIPTION
           "Identifies whether the particular VLan on this
		      port is tagged or not. 'no' denotes not a member
		      of that vlan."
    ::= { hpVlanMemberEntry2  1 }

hpVlanGroups OBJECT IDENTIFIER ::= { hpVlanConformance  1 }

hpVlanCompliances OBJECT IDENTIFIER ::= { hpVlanConformance  2 }

hpVlanCompliance OBJECT IDENTIFIER ::= { hpVlanCompliances  1 }

hpVlanGeneralGroup OBJECT IDENTIFIER ::= { hpVlanGroups  1 }

hpVlanAddressGroup OBJECT IDENTIFIER ::= { hpVlanGroups  2 }

END
