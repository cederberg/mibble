Windows-System-Mib DEFINITIONS ::= BEGIN

IMPORTS
    Counter
        FROM RFC1155-SMI
    Integer32
        FROM SNMPv2-SMI
    DisplayString
        FROM SNMPv2-TC;

-- TEXTUAL-CONVENTIONS --
org	OBJECT IDENTIFIER  ::=  {  iso  3  }

dod	OBJECT IDENTIFIER  ::=  {  org  6  }

internet	OBJECT IDENTIFIER  ::=  {  dod  1  }

directory	OBJECT IDENTIFIER  ::=  {  internet  1  }

mgmt	OBJECT IDENTIFIER  ::=  {  internet  2  }

experimental	OBJECT IDENTIFIER  ::=  {  internet  3  }

private	OBJECT IDENTIFIER  ::=  {  internet  4  }

snmpV2	OBJECT IDENTIFIER  ::=  {  internet  6  }

mib-2	OBJECT IDENTIFIER  ::=  {  mgmt  1  }

enterprises	OBJECT IDENTIFIER  ::=  {  private  1  }

snmpDomains	OBJECT IDENTIFIER  ::=  {  snmpV2  1  }

snmpProxys	OBJECT IDENTIFIER  ::=  {  snmpV2  2  }

snmpModules	OBJECT IDENTIFIER  ::=  {  snmpV2  3  }

adventnet       OBJECT IDENTIFIER  ::=  {  enterprises  2162  }

system1	OBJECT IDENTIFIER  ::=  {  adventnet  1  }

disk	OBJECT IDENTIFIER  ::=  {  adventnet  2  }

memory	OBJECT IDENTIFIER  ::=  {  adventnet  3  }

network	OBJECT IDENTIFIER  ::=  {  adventnet  4  }

userName	OBJECT-TYPE 
	SYNTAX	DisplayString 
	ACCESS	read-write 
	STATUS	mandatory
 
	
	DESCRIPTION
		""
	
	REFERENCE
		""
	
--	AGENTCLAUSE
--		 "
--		 CLASS-COMMAND: 
--		 CLASS-NAME: WinSystem
--		 INSTANTIATE: at-start
--		 PARAMETERS: param string"
--	 END AGENTCLAUSE
	::=  {  system1  1  }

computerName	OBJECT-TYPE 
	SYNTAX	DisplayString 
	ACCESS	read-write 
	STATUS	mandatory
 
	
	DESCRIPTION
		"This gives the Computer description"
	
	REFERENCE
		""
--	AGENTCLAUSE
--		 "
--		 CLASS-COMMAND: 
--		 CLASS-NAME: WinSystem
--		 INSTANTIATE: at-start
--		 PARAMETERS: param string"
--	 END AGENTCLAUSE
	
	::=  {  system1  2  }

numOfProcessors	OBJECT-TYPE 
	SYNTAX	Integer32 
	ACCESS	read-only 
	STATUS	mandatory
 
	
	DESCRIPTION
		""
	
	REFERENCE
		"Number of Processors"

--	AGENTCLAUSE
--		 "
--		 CLASS-COMMAND: 
--		 CLASS-NAME: WinSystem
--		 INSTANTIATE: at-start
--		 PARAMETERS: param string"
--	 END AGENTCLAUSE
	
	::=  {  system1  3  }

processorType	OBJECT-TYPE 
	SYNTAX	DisplayString 
	ACCESS	read-only 
	STATUS	mandatory
 
	
	DESCRIPTION
		"Returns the Processor Type"
	
	REFERENCE
		""
--	AGENTCLAUSE
--		 "
--		 CLASS-COMMAND: 
--		 CLASS-NAME: WinSystem
--		 INSTANTIATE: at-start
--		 PARAMETERS: param string"
--	 END AGENTCLAUSE
	
	::=  {  system1  4  }

oS	OBJECT-TYPE 
	SYNTAX	DisplayString 
	ACCESS	read-only 
	STATUS	mandatory
 
	
	DESCRIPTION
		"Returns the Operating System"
	
	REFERENCE
		""
--	AGENTCLAUSE
--		 "
--		 CLASS-COMMAND: 
--		 CLASS-NAME: WinSystem
--		 INSTANTIATE: at-start
--		 PARAMETERS: param string"
--	 END AGENTCLAUSE
	
	::=  {  system1  5  }

variableReferce	OBJECT-TYPE 
	SYNTAX	DisplayString 
	ACCESS	read-write 
	STATUS	mandatory
 
	
	DESCRIPTION
		"Return values for environmental  variable like 'PATH'"
	
	REFERENCE
		""
--	AGENTCLAUSE
--		 "
--		 CLASS-COMMAND: 
--		 CLASS-NAME: WinSystem
--		 INSTANTIATE: at-start
--		 PARAMETERS: param string"
--	 END AGENTCLAUSE
	
	::=  {  system1  6  }

sysDate	OBJECT-TYPE 
	SYNTAX	DisplayString 
	ACCESS	read-write 
	STATUS	mandatory
 
	
	DESCRIPTION
		"Retrives the current date with the format mm-dd-yyyy 
Use the same for set command also. "
	
	REFERENCE
		""
--	AGENTCLAUSE
--		 "
--		 CLASS-COMMAND: 
--		 CLASS-NAME: WinSystem
--		 INSTANTIATE: at-start
--		 PARAMETERS: param string"
--	 END AGENTCLAUSE
	
	::=  {  system1  7  }

sysTime	OBJECT-TYPE 
	SYNTAX	DisplayString 
	ACCESS	read-write 
	STATUS	mandatory
 
	
	DESCRIPTION
		"Retrives the current time  with the format hh:mm:ss
Use the same for set command also. "
	
	REFERENCE
		""
--	AGENTCLAUSE
--		 "
--		 CLASS-COMMAND: 
--		 CLASS-NAME: WinSystem
--		 INSTANTIATE: at-start
--		 PARAMETERS: param string"
--	 END AGENTCLAUSE
	
	::=  {  system1  8  }


diskTable	OBJECT-TYPE
	SYNTAX	SEQUENCE  OF  DiskEntry
	ACCESS	not-accessible
STATUS	mandatory
 	::=  { disk  1 }

diskEntry	OBJECT-TYPE
	SYNTAX	DiskEntry
	ACCESS	not-accessible
STATUS	mandatory
 	INDEX	{  diskName  }
	::=  { diskTable 1 }

DiskEntry  ::=  SEQUENCE {
	diskName  DisplayString,
	diskType  DisplayString,
	sectorPerCluster  INTEGER,
	bytesPerSector  INTEGER,
	totalSpaceinBytes  INTEGER,
	freeSpaceinBytes  INTEGER
	}
diskName	OBJECT-TYPE 
	SYNTAX	DisplayString 
	ACCESS	read-only 
	STATUS	mandatory
 
	
	DESCRIPTION
		"Disk Name "
	
	REFERENCE
		""
--	AGENTCLAUSE
--		 "
--		 CLASS-COMMAND: 
--		 CLASS-NAME: WinDisk
--		 INSTANTIATE: at-start
--		 PARAMETERS: param string"
--	 END AGENTCLAUSE

	::=  {  diskEntry  1  }

diskType	OBJECT-TYPE 
	SYNTAX	DisplayString 
	ACCESS	read-only 
	STATUS	mandatory
 
	
	DESCRIPTION
		"Disk Type : like Removable Disk;CD ROM drive etc ..."
	
	REFERENCE
		""
--	AGENTCLAUSE
--		 "
--		 CLASS-COMMAND: 
--		 CLASS-NAME: WinDisk
--		 INSTANTIATE: at-start
--		 PARAMETERS: param string"
--	 END AGENTCLAUSE
	
	
	::=  {  diskEntry  2  }

sectorPerCluster	OBJECT-TYPE 
	SYNTAX	INTEGER 
	ACCESS	read-only 
	STATUS	mandatory
 
	
	DESCRIPTION
		"No of Sectors per Cluster"
	
	REFERENCE
		""
--	AGENTCLAUSE
--		 "
--		 CLASS-COMMAND: 
--		 CLASS-NAME: WinDisk
--		 INSTANTIATE: at-start
--		 PARAMETERS: param string"
--	 END AGENTCLAUSE
	
	::=  {  diskEntry  3  }

bytesPerSector	OBJECT-TYPE 
	SYNTAX	INTEGER 
	ACCESS	read-only 
	STATUS	mandatory
 
	
	DESCRIPTION
		"No of  bytes per Sector "
	
	REFERENCE
		""
--	AGENTCLAUSE
--		 "
--		 CLASS-COMMAND: 
--		 CLASS-NAME: WinDisk
--		 INSTANTIATE: at-start
--		 PARAMETERS: param string"
--	 END AGENTCLAUSE
	
	::=  {  diskEntry  4  }

totalSpaceinBytes	OBJECT-TYPE 
	SYNTAX	INTEGER 
	ACCESS	read-only 
	STATUS	mandatory
 
	
	DESCRIPTION
		"total space in bytes of the specified drive"
	
	REFERENCE
		""
--	AGENTCLAUSE
--		 "
--		 CLASS-COMMAND: 
--		 CLASS-NAME: WinDisk
--		 INSTANTIATE: at-start
--		 PARAMETERS: param string"
--	 END AGENTCLAUSE
	
	::=  {  diskEntry  5  }

freeSpaceinBytes	OBJECT-TYPE 
	SYNTAX	INTEGER 
	ACCESS	read-only 
	STATUS	mandatory
 
	
	DESCRIPTION
		"free space in bytes of the specified drive "
	
	REFERENCE
		""
--	AGENTCLAUSE
--		 "
--		 CLASS-COMMAND: 
--		 CLASS-NAME: WinDisk
--		 INSTANTIATE: at-start
--		 PARAMETERS: param string"
--	 END AGENTCLAUSE
	
	::=  {  diskEntry  6  }

totalFreeSpaceInBytes	OBJECT-TYPE 
	SYNTAX	Counter 
	ACCESS	read-only 
	STATUS	mandatory
 
	
	DESCRIPTION
		"Return Total Free Space in the machine ( Calculated from the Hard Disk attached )"
	
	REFERENCE
		""
--	AGENTCLAUSE
--		 "
--		 CLASS-COMMAND: 
--		 CLASS-NAME: WinDiskInfo
--		 INSTANTIATE: at-start
--		 PARAMETERS: param string"
--	 END AGENTCLAUSE
	
	::=  {  disk  2  }

totalSpaceInBytes	OBJECT-TYPE 
	SYNTAX	Counter 
	ACCESS	read-only 
	STATUS	mandatory
 
	
	DESCRIPTION
		"Total Space in the machine (calculated from the Hard Disk attached )"
	
	REFERENCE
		""
--	AGENTCLAUSE
--		 "
--		 CLASS-COMMAND: 
--		 CLASS-NAME: WinDiskInfo
--		 INSTANTIATE: at-start
--		 PARAMETERS: param string"
--	 END AGENTCLAUSE
	
	
	::=  {  disk  3  }

totalOccupiedSpaceInBytes	OBJECT-TYPE 
	SYNTAX	Counter 
	ACCESS	read-only 
	STATUS	mandatory
 
	
	DESCRIPTION
		"Total Occupied space in the machine  (calculated from the Hard Disk attached )"
	
	REFERENCE
		""
--	AGENTCLAUSE
--		 "
--		 CLASS-COMMAND: 
--		 CLASS-NAME: WinDiskInfo
--		 INSTANTIATE: at-start
--		 PARAMETERS: param string"
--	 END AGENTCLAUSE
	
	
	::=  {  disk  4  }


processTable	OBJECT-TYPE
	SYNTAX	SEQUENCE  OF  ProcessEntry
	ACCESS	not-accessible
STATUS	mandatory
 	DESCRIPTION
		"Process entry attributes stored"
	::=  { memory  1 }

processEntry	OBJECT-TYPE
	SYNTAX	ProcessEntry
	ACCESS	not-accessible
STATUS	mandatory
 	INDEX	{  processID  }
	::=  { processTable 1 }

ProcessEntry  ::=  SEQUENCE {
	processID  INTEGER,
	processModuleName  DisplayString,
	processPriority  INTEGER,
	processBasePriority  INTEGER,
	processNumOfThreads  INTEGER,
	processAppType  DisplayString,
	processFullPath  DisplayString,
	processKill  INTEGER
	}
processID	OBJECT-TYPE 
	SYNTAX	INTEGER 
	ACCESS	read-only 
	STATUS	mandatory
 
	
	DESCRIPTION
		"Process Identifier of the Selected process. This will be unique for processes"

--	AGENTCLAUSE
--		 "
--		 CLASS-COMMAND: 
--		 CLASS-NAME: WinProcess
--		 INSTANTIATE: at-start
--		 PARAMETERS: param string"
--	 END AGENTCLAUSE
	
	::=  {  processEntry  1  }

processModuleName	OBJECT-TYPE 
	SYNTAX	DisplayString 
	ACCESS	read-only 
	STATUS	mandatory
 
	
	DESCRIPTION
		"Name of the  application "
	
	REFERENCE
		""
--	AGENTCLAUSE
--		 "
--		 CLASS-COMMAND: 
--		 CLASS-NAME: WinProcess
--		 INSTANTIATE: at-start
--		 PARAMETERS: param string"
--	 END AGENTCLAUSE
	
	
	::=  {  processEntry  2  }

processPriority	OBJECT-TYPE 
	SYNTAX	INTEGER 
	ACCESS	read-only 
	STATUS	mandatory
 
	
	DESCRIPTION
		"Refers the Process Priority"
--	AGENTCLAUSE
--		 "
--		 CLASS-COMMAND: 
--		 CLASS-NAME: WinProcess
--		 INSTANTIATE: at-start
--		 PARAMETERS: param string"
--	 END AGENTCLAUSE
	
	
	::=  {  processEntry  3  }

processBasePriority	OBJECT-TYPE 
	SYNTAX	INTEGER 
	ACCESS	read-only 
	STATUS	mandatory
 
	
	DESCRIPTION
		"Base process priority"
--	AGENTCLAUSE
--		 "
--		 CLASS-COMMAND: 
--		 CLASS-NAME: WinProcess
--		 INSTANTIATE: at-start
--		 PARAMETERS: param string"
--	 END AGENTCLAUSE
	
	
	::=  {  processEntry  4  }

processNumOfThreads	OBJECT-TYPE 
	SYNTAX	INTEGER 
	ACCESS	read-only 
	STATUS	mandatory
 
	
	DESCRIPTION
		"Number of threads of the given process"
	
--	AGENTCLAUSE
--		 "
--		 CLASS-COMMAND: 
--		 CLASS-NAME: WinProcess
--		 INSTANTIATE: at-start
--		 PARAMETERS: param string"
--	 END AGENTCLAUSE
	
	::=  {  processEntry  5  }

processAppType	OBJECT-TYPE 
	SYNTAX	DisplayString 
	ACCESS	read-only 
	STATUS	mandatory
 
	
	DESCRIPTION
		"Refer whether the application is a 16 Bit or 32 Bit application."
	
--	AGENTCLAUSE
--		 "
--		 CLASS-COMMAND: 
--		 CLASS-NAME: WinProcess
--		 INSTANTIATE: at-start
--		 PARAMETERS: param string"
--	 END AGENTCLAUSE
	
	::=  {  processEntry  6  }

processFullPath	OBJECT-TYPE 
	SYNTAX	DisplayString 
	ACCESS	read-only 
	STATUS	mandatory
 
	
	DESCRIPTION
		"Refers the full path of Application"
	
--	AGENTCLAUSE
--		 "
--		 CLASS-COMMAND: 
--		 CLASS-NAME: WinProcess
--		 INSTANTIATE: at-start
--		 PARAMETERS: param string"
--	 END AGENTCLAUSE
	
	::=  {  processEntry  7  }

processKill	OBJECT-TYPE 
	SYNTAX	INTEGER 
	ACCESS	read-write 
	STATUS	mandatory
 
	
	DESCRIPTION
		"Used to kill the given process "
	
	REFERENCE
		""
	
--	AGENTCLAUSE
--		 "
--		 CLASS-COMMAND: 
--		 CLASS-NAME: WinProcess
--		 INSTANTIATE: at-start
--		 PARAMETERS: param string"
--	 END AGENTCLAUSE
	
	::=  {  processEntry  8  }

noOfProcess	OBJECT-TYPE 
	SYNTAX	Counter 
	ACCESS	read-only 
	STATUS	mandatory
 
	
	DESCRIPTION
		"This return no of Processes that are running in the machine"
	
	REFERENCE
		""
	
--	AGENTCLAUSE
--		 "
--		 CLASS-COMMAND: 
--		 CLASS-NAME: WinNoProcess
--		 INSTANTIATE: at-start
--		 PARAMETERS: param string"
--	 END AGENTCLAUSE
	
	::=  {  memory  2  }

noOfThreads	OBJECT-TYPE 
	SYNTAX	Counter 
	ACCESS	read-only 
	STATUS	mandatory
 
	
	DESCRIPTION
		"Return No of Threads running in the machine"
	
	REFERENCE
		""
	
--	AGENTCLAUSE
--		 "
--		 CLASS-COMMAND: 
--		 CLASS-NAME: WinNoProcess
--		 INSTANTIATE: at-start
--		 PARAMETERS: param string"
--	 END AGENTCLAUSE
	
	::=  {  memory  3  }












netWorkTrap	TRAP-TYPE
	ENTERPRISE	adventnet
	DESCRIPTION
		"When Windows Network Drive is deleted/added this trap will be generated."
	REFERENCE
		""
	::=  1





END
