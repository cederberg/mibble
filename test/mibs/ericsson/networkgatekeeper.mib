NETWORKGATEKEEPER DEFINITIONS ::= BEGIN

-- 
--								SNMPv1
-- 
-- NAME:		NETWORK GATEKEEPER LONG DISTANCE
-- 
-- REVISION HISTORY:-
--
-- REV  DATE    NAME                	DESCRIPTION
-- PA1  970926  ETXDESW/ETXHAIM     	First try
-- PA2  971007  ETXDESW/ETXHAIM     	minor changes
-- PA3  971028  ETXPODI             	Alarm changes
-- A	980421  QTXJOAL             	Removed ngkTimeSyncHost
--                                  	Added ngkProgramTraceOnAlarm
-- PB1	980622	QTXJOAL			Added traps.
-- B	980629	QTXJOAL			Rev B.
-- PC1	980716	QTXSCHU			OID for version information
-- C	981010	ETXHAIM			Rev C.
-- PD1  980208  QTXKAJ			Added functionality for software upgrades
-- 
-- DESCRIPTION
-- LATER
-- 
--
-- Ericsson Long Distance MIB for NetworkGateKeeper
--
IMPORTS
	enterprises
		FROM RFC1155-SMI
	OBJECT-TYPE
		FROM RFC-1212
	DisplayString
-- FIX:		FROM RFC-1213;
                FROM RFC1213-MIB;
		
		
	ericsson			OBJECT IDENTIFIER ::= { enterprises 193 }
	phonedoubler			OBJECT IDENTIFIER ::= { ericsson 26 } 
	networkGateKeeperMIB		OBJECT IDENTIFIER ::= { phonedoubler 6 }
	networkGateKeeperMIBObjects	OBJECT IDENTIFIER ::= { networkGateKeeperMIB 1 }
	
-- Define of a truth value
	TruthValue ::= INTEGER { true(1), false(2) }
--
--=======================================================================================
-- networkGateKeeper MIB
--
--=======================================================================================

-- GENERAL DESCRIPTION
-- ===================

	ngkMACAddress OBJECT-TYPE
		SYNTAX DisplayString
		ACCESS	read-only
		STATUS	mandatory
		DESCRIPTION	"This is the address of the network card."
		::= { networkGateKeeperMIBObjects 2 }
--
--=======================================================================================

-- CONTROL
-- =============
	ngkServiceState OBJECT-TYPE
		    SYNTAX INTEGER {
				stop(1),
				startpending(2),
				stoppending(3),
				run(4),
				continuepending(5),
				pausepending(6),
				pause(7)
			}
			ACCESS read-write
			STATUS mandatory
			DESCRIPTION
				"This function controls or returns the state of the 
				 GateKeeper service."
		::= { networkGateKeeperMIBObjects 3}

	ngkMachineReboot OBJECT-TYPE
			SYNTAX INTEGER
			ACCESS write-only
			STATUS mandatory
			DESCRIPTION
				"This function reboots the machine."
		::= { networkGateKeeperMIBObjects 4}
--
--=======================================================================================

-- ALARMS
-- ======
	ngkAlarmState OBJECT-TYPE
		SYNTAX INTEGER {
				noAlarm(0),
				sendMailAlarm(2),
				definedSiteNotRegistered(4),
				unknownSiteRejected(8),
				serviceNotRunning(16),
				definedABNotRegistered(32),
				unknownABRejected(64),
				definedACCNotRegistered(128),
				unknownACCRejected(256),
				definedBSSNotRegistered(512),
				unknownBSSRejected(1024)
				}

		ACCESS read-only
		STATUS mandatory
		DESCRIPTION
			"The current alarm state which can take a combination of the
			following values
				0     No alarm
				2     Failed to send alarm mail
				4     Defined site not registered
				8     Unknown site rejected
				16    Service not running
				32    Defined access broker not registered
				64    Unknown access broker rejected
				128   Defined accounting server not registered
				256   Unknown accounting server rejected
				512   Defined billing server not registered
				1024  Unknown billing server rejected"
		::= { networkGateKeeperMIBObjects 5 }

	ngkMailUsingSmtp OBJECT-TYPE
		SYNTAX TruthValue   
		ACCESS read-write
		STATUS mandatory
		DESCRIPTION
				"This indicates, if true, that the alarms are sent via
				SMTP."
		::= { networkGateKeeperMIBObjects 6 }

	ngkMailServer OBJECT-TYPE
		SYNTAX DisplayString
		ACCESS read-write
		STATUS mandatory
		DESCRIPTION
				"Mail server for alarms."
		::= { networkGateKeeperMIBObjects 7}

	ngkOriginMailAddress OBJECT-TYPE
		SYNTAX DisplayString
		ACCESS read-write
		STATUS mandatory
		DESCRIPTION
				"Origin mail address in alarm
				 mails."
		::= { networkGateKeeperMIBObjects 8}

	ngkDestMailAddress OBJECT-TYPE
		SYNTAX DisplayString
		ACCESS read-write
		STATUS mandatory
		DESCRIPTION
				"Destination mail address in alarm
				 mails."
		::= { networkGateKeeperMIBObjects 9}

	ngkMailSubjectText OBJECT-TYPE
		SYNTAX DisplayString
		ACCESS read-write
		STATUS mandatory
		DESCRIPTION
				"Subject text in alarm mails."
		::= { networkGateKeeperMIBObjects 10}

	ngkMailHeaderText OBJECT-TYPE
		SYNTAX DisplayString
		ACCESS read-write
		STATUS mandatory
		DESCRIPTION
				"Mail header text in alarm mails."
		::= { networkGateKeeperMIBObjects 11}
--
--=======================================================================================

-- TRACING
-- =======

	ngkProgramTraceOnErrors OBJECT-TYPE
		SYNTAX TruthValue   
		ACCESS read-write
		STATUS mandatory
		DESCRIPTION
				"This indicates that errors are traced if set to true."
		::= { networkGateKeeperMIBObjects 12}

	ngkProgramTraceOnWarn OBJECT-TYPE
		SYNTAX TruthValue   
		ACCESS read-write
		STATUS mandatory
		DESCRIPTION
				"This indicates that warnings are traced if set to true."
		::= { networkGateKeeperMIBObjects 13}

	ngkProgramTraceOnInfo OBJECT-TYPE
		SYNTAX TruthValue   
		ACCESS read-write
		STATUS mandatory
		DESCRIPTION
				"This indicates that information is logged if set to true."
		::= { networkGateKeeperMIBObjects 14}

	ngkProgramTraceOnAlarm OBJECT-TYPE
		SYNTAX TruthValue   
		ACCESS read-write
		STATUS mandatory
		DESCRIPTION
				"This indicates that alarms are logged if set to true."
		::= { networkGateKeeperMIBObjects 15}

	ngkVersionInfo OBJECT-TYPE
		SYNTAX DisplayString   
		ACCESS read-only
		STATUS mandatory
		DESCRIPTION
				"This is the version information for the installed
					network gatekeeper service.."
		::= { networkGateKeeperMIBObjects 16}

	ngkHCVGSoftwarePath OBJECT-TYPE
		SYNTAX DisplayString   
		ACCESS read-only
		STATUS mandatory
		DESCRIPTION
				"Gives path from webserver root to HCVG files"
		::= { networkGateKeeperMIBObjects 18}

	ngkHCVGSoftwareList OBJECT-TYPE
		SYNTAX DisplayString   
		ACCESS read-only
		STATUS mandatory
		DESCRIPTION
				"Returns hcvg images found in ngkHCVGSoftwarePath.
					Each file entry contains:
					Filename \t Size \t Prodname \n
					The string is ended with \n\n"
		::= { networkGateKeeperMIBObjects 19}

	ngkGetngkServerIP OBJECT-TYPE
		SYNTAX DisplayString   
		ACCESS read-only
		STATUS mandatory
		DESCRIPTION
				"Returns the IP-address to the webserver which
				holds (software)images"
		::= { networkGateKeeperMIBObjects 20}

	ngkSS7SoftwarePath OBJECT-TYPE
		SYNTAX DisplayString   
		ACCESS read-only
		STATUS mandatory
		DESCRIPTION
				"Gives path from webserver root to SS7 files"
		::= { networkGateKeeperMIBObjects 21}

	ngkSS7SoftwareList OBJECT-TYPE
		SYNTAX DisplayString   
		ACCESS read-only
		STATUS mandatory
		DESCRIPTION
				"Returns ss7 images found in ngkSS7SoftwarePath.
					Each file entry contains:
					filename \t Size \t Prodname \n
					The string is ended with \n\n"
		::= { networkGateKeeperMIBObjects 22}

	serviceStateChange TRAP-TYPE
		ENTERPRISE networkGateKeeperMIB
		VARIABLES { ngkServiceState }
		DESCRIPTION
		"Trap is sent when the state of the network GateKeeper service is changed."
		::= 1

	alarm TRAP-TYPE
		ENTERPRISE networkGateKeeperMIB
		VARIABLES { ngkAlarmState }
		DESCRIPTION
		"Trap is sent when an alarm occurs."
		::= 2

	alarmCeasing TRAP-TYPE
		ENTERPRISE networkGateKeeperMIB
		VARIABLES { ngkAlarmState }
		DESCRIPTION
		"Trap is sent when an alarm disappears."
		::= 3

--
--=======================================================================================
END
