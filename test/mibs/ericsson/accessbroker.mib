ACCESSBROKER DEFINITIONS ::= BEGIN

-- 
--								SNMPv1
-- 
-- NAME:		Access Broker Seamac MIB
-- 
-- REVISION HISTORY:-
--
-- REV	DATE		NAME		DESCRIPTION
-- PA1	980211		ETXHAIM		First try
-- PA2  980227		ETXHAIM		New parameters
-- PA3	980319		ETXHAIM		Minor changes
-- A    980422          QTXJOAL         Minor changes
-- PB1	980622		QTXJOAL		Added traps
-- B    980629          QTXJOAL         B-rev
--
-- DESCRIPTION
-- LATER
-- 



-- Ericsson Long Distance MIB for LocalGateKeeper

IMPORTS
	enterprises
		FROM RFC1155-SMI
	OBJECT-TYPE
		FROM RFC-1212   
	DisplayString
-- FIX:		FROM RFC-1213;
                FROM RFC1213-MIB;
		
		
	ericsson		  OBJECT IDENTIFIER ::= { enterprises 193 }
	phonedoubler		  OBJECT IDENTIFIER ::= { ericsson 26 } 
	accessbrokerMIB 	  OBJECT IDENTIFIER ::= { phonedoubler 7 }
	accessbrokerMIBObjects    OBJECT IDENTIFIER ::= { accessbrokerMIB 1 }
	
-- Define of a truth value
	TruthValue ::= INTEGER { true(1), false(2) }

-- =======================================================================================
-- AccessBroker MIB

-- =======================================================================================
-- GENERAL ATTRIBUTES
-- ==================

	abMACAddress OBJECT-TYPE
		SYNTAX	DisplayString
		ACCESS	read-only
		STATUS	mandatory
		DESCRIPTION "This is the address of the network card."
		::= { accessbrokerMIBObjects 1}

	netKeeperIpAddress OBJECT-TYPE
		SYNTAX DisplayString  -- This is a string of 0 to 255 in length
		ACCESS read-write
		STATUS mandatory
		DESCRIPTION
				"This is the IP address of the Network
				Gatekeeper used by this access broker. 
				The address takes the form X.X.X.X where
				X is an integer between 0 and 255."
		DEFVAL { "" }
		::= { accessbrokerMIBObjects 2}

	abRadiusServer1 OBJECT-TYPE
		SYNTAX DisplayString  -- This is a string of 0 to 255 in length
		ACCESS read-write
		STATUS mandatory
		DESCRIPTION
				"This is the IP address of the billing
				server 1 used by this access broker. 
				The address takes the form X.X.X.X where
				X is an integer between 0 and 255."
		DEFVAL { "" }
		::= { accessbrokerMIBObjects 3}

	abRadiusServer2 OBJECT-TYPE
		SYNTAX DisplayString  -- This is a string of 0 to 255 in length
		ACCESS read-write
		STATUS mandatory
		DESCRIPTION
				"This is the IP address of the billing
				server 2 used by this access broker. 
				The address takes the form X.X.X.X where
				X is an integer between 0 and 255."
		DEFVAL { "" }
		::= { accessbrokerMIBObjects 4}

	commonRadiusServerSecret OBJECT-TYPE
		SYNTAX DisplayString  -- This is a string
		ACCESS write-only
		STATUS mandatory
		DESCRIPTION
				"This is the common secret for the radius
				servers used by this access broker." 
				
		DEFVAL { "" }
		::= { accessbrokerMIBObjects 5 }

    abURLhelp OBJECT-TYPE
		SYNTAX DisplayString
		ACCESS read-write
		STATUS mandatory
		DESCRIPTION
				"This is the URL address to help the client."
		::= { accessbrokerMIBObjects 6 }

	abMachineReboot OBJECT-TYPE
			SYNTAX INTEGER
			ACCESS write-only
			STATUS mandatory
			DESCRIPTION
				"This function reboots the machine."
		::= { accessbrokerMIBObjects 7 }

	abAlarmState OBJECT-TYPE
		SYNTAX INTEGER {
				noAlarm(0),
				pBillingServerAlarm(1),
				sBillingServerAlarm(2),
				maxNumberOfAuthReq(4),
				noContactWithSitekeeper(16),
				noContactWithNetkeeper(32),
				serviceNotRunning(64)
				}

		ACCESS read-only
		STATUS mandatory
		DESCRIPTION
			"The current alarm state which can take a combination of the
			following values:
				 0   No alarm
				 1   No contact with primary billing server 
				 2   No contact with secondary billing server
				 4   Maximum number of pending authentication requests exceeded
				16   No contact with sitekeeper
				32   No contact with netkeeper
				64   Service not running"
		::= { accessbrokerMIBObjects 8 }

	abProgramTraceOnErrors OBJECT-TYPE
		SYNTAX TruthValue   
		ACCESS read-write
		STATUS mandatory
		DESCRIPTION
				"This indicates that errors are traced if set to true."
		DEFVAL { false }
		::= { accessbrokerMIBObjects 9 }

    abProgramTraceOnWarn OBJECT-TYPE
		SYNTAX TruthValue   
		ACCESS read-write
		STATUS mandatory
		DESCRIPTION
				"This indicates that warnings are traced if set to true."
		DEFVAL { false }
		::= { accessbrokerMIBObjects 10 }

	abProgramTraceOnInfo OBJECT-TYPE
		SYNTAX TruthValue   
		ACCESS read-write
		STATUS mandatory
		DESCRIPTION
				"This indicates that information is logged if set to true."
		DEFVAL { false }
		::= { accessbrokerMIBObjects 11 }

	abServiceState OBJECT-TYPE
		    SYNTAX INTEGER {
				stop(1),
				startpending(2),
				stoppending(3),
				run(4),
				continuepending(5),
				pausepending(6),
				pause(7)
			}
			ACCESS read-write
			STATUS mandatory
			DESCRIPTION
				"This function controls or returns the state of the 
				 Access Broker service."
		::= { accessbrokerMIBObjects 12 }

	abAlarmTrace OBJECT-TYPE
		SYNTAX TruthValue   
		ACCESS read-write
		STATUS mandatory
		DESCRIPTION
				"This indicates that alarms are traced if set to true."
		DEFVAL { false }
		::= { accessbrokerMIBObjects 13 }

   	abServiceProvider OBJECT-TYPE
		SYNTAX DisplayString
		ACCESS read-write
		STATUS mandatory
		DESCRIPTION
				"This is the name of the service provider."
		::= { accessbrokerMIBObjects 14 }

   	abBitMapUrl OBJECT-TYPE
		SYNTAX DisplayString
		ACCESS read-write
		STATUS mandatory
		DESCRIPTION
				"This is the URL address to help the client."
		::= { accessbrokerMIBObjects 15 }

	abNrAut	OBJECT-TYPE
			SYNTAX INTEGER
			ACCESS read-only
			STATUS mandatory
			DESCRIPTION
				"This is the number of subscribers trying to use 
                                 the service at this moment."
		::= { accessbrokerMIBObjects 16 }

	serviceStateChange TRAP-TYPE
		ENTERPRISE accessbrokerMIB
		VARIABLES { abServiceState }
		DESCRIPTION
		"Trap is sent when the state of the ABSVC is changed."
		::= 1

	alarm TRAP-TYPE
		ENTERPRISE accessbrokerMIB
		VARIABLES { abAlarmState }
		DESCRIPTION
		"Trap is sent when an alarm occurs."
		::= 2

	alarmCeasing TRAP-TYPE
		ENTERPRISE accessbrokerMIB
		VARIABLES { abAlarmState }
		DESCRIPTION
		"Trap is sent when an alarm disappears."
		::= 3

--=======================================================================================
END
