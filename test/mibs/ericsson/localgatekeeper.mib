LOCALGATEKEEPER DEFINITIONS ::= BEGIN

-- 
--								SNMPv1
-- 
-- NAME:		LocalGateKeeper Long Distance MIB
-- 
-- REVISION HISTORY:-
--
-- REV	DATE		NAME		DESCRIPTION
-- PA1	970926		ETXHAIM		First try
-- PA2	971007		ETXHAIM		Minor changes
-- PA3	971009		ETXHAIM		Minor changes after compilation
-- PA4	971014		ETXDESW		Added lgkNetworkGK attribute
-- PA5	971022		ETXPODI		Updating Alarms
-- PA6	980318		ETXHAIM		Major changes
-- A	980422		QTXJOAL		Updated with same values as the dll.
-- PB1	980622		QTXJOAL		Added traps.
-- B	980629		QTXJOAL		Revision B.
-- PC1	980716		QTXSCHU		Changes for Öland  (new OIDs)
-- PC2	981001		ETXHAIM		Changes for Öland  (new OIDs)
-- C	981010		ETXHAIM		Revision C.
--
-- DESCRIPTION
-- LATER
-- 



-- Ericsson Long Distance MIB for LocalGateKeeper

IMPORTS
	enterprises
		FROM RFC1155-SMI
	OBJECT-TYPE
		FROM RFC-1212   
	DisplayString
-- FIX:		FROM RFC-1213;
                FROM RFC1213-MIB;
		
		
	ericsson		  OBJECT IDENTIFIER ::= { enterprises 193 }
	phonedoubler		  OBJECT IDENTIFIER ::= { ericsson 26 } 
	localGateKeeperMIB	  OBJECT IDENTIFIER ::= { phonedoubler 5 }
	localGateKeeperMIBObjects OBJECT IDENTIFIER ::= { localGateKeeperMIB 1 }
	
-- Define of a truth value
	TruthValue ::= INTEGER { true(1), false(2) }

-- =======================================================================================
-- LocalGateKeeper MIB

-- =======================================================================================
-- GENERAL ATTRIBUTES
-- ==================

	lgkMACAddress OBJECT-TYPE
		SYNTAX	DisplayString
		ACCESS	read-only
		STATUS	mandatory
		DESCRIPTION "This is the address of the network card."
		::= { localGateKeeperMIBObjects 1}

	lgkNetworkGK OBJECT-TYPE
		SYNTAX DisplayString  -- This is a string of 0 to 255 in length
		ACCESS read-write
		STATUS mandatory
		DESCRIPTION
				"This is the IP address of the Network
				Gatekeeper used by this Local Gatekeeper. 
				The address takes the form X.X.X.X where
				X is an integer between 0 and 255."
		DEFVAL { "" }
		::= { localGateKeeperMIBObjects 2}

-- =======================================================================================
-- CONTROL
-- =============

	lgkServiceState OBJECT-TYPE
		    SYNTAX INTEGER {
				stop(1),
				startpending(2),
				stoppending(3),
				run(4),
				continuepending(5),
				pausepending(6),
				pause(7)
			}
			ACCESS read-write
			STATUS mandatory
			DESCRIPTION
				"This function controls or returns the state of the 
				 Local Gatekeeper service."
		::= { localGateKeeperMIBObjects 3}

	lgkMachineReboot OBJECT-TYPE
			SYNTAX INTEGER
			ACCESS write-only
			STATUS mandatory
			DESCRIPTION
				"This function reboots the machine."
		::= { localGateKeeperMIBObjects 4}


-- =======================================================================================
-- ALARMS
-- ======

	lgkAlarmState OBJECT-TYPE
		SYNTAX INTEGER {
				noAlarm(0),
				noNetKeeper(1),
				noAccountServer(4),
				timeSyncError(8),
				definedEndpointNotRegistr(32),
				unknownEndpointRejected(64),
				callLogWriteFailure(128),
				failedLoadingConfigFiles(256),
				serviceNotRunning(512),
				noContactWithPrimaryBilling(1024),
				noContactWithSecondaryBilling(2048)
				}

		ACCESS read-only
		STATUS mandatory
		DESCRIPTION
			"The current alarm state which can be a combination of the
			following values:
				 0  No alarm
				 1  No contact with netkeeper
				 4  No contact with accounting server
				 8  Failed to synchronize time
				32  Defined endpoint not registered
				64  Unknown endpoint rejected
			   128  Failed to write to call log
			   256  Failed to load configuration files
			   512  Service not running
			  1024  No contact with primary billing server
			  2048  No contact with secondary billing server"
		::= { localGateKeeperMIBObjects 5}

-- =======================================================================================
-- TRACING
-- ======
       	lgkProgramTraceOnErrors OBJECT-TYPE
		SYNTAX TruthValue   
		ACCESS read-write
		STATUS mandatory
		DESCRIPTION
				"This indicates that errors are traced if set to true."
		::= { localGateKeeperMIBObjects 6}

	lgkProgramTraceOnWarn OBJECT-TYPE
		SYNTAX TruthValue   
		ACCESS read-write
		STATUS mandatory
		DESCRIPTION
				"This indicates that warnings are traced if set to true."
		::= { localGateKeeperMIBObjects 7}

	lgkProgramTraceOnInfo OBJECT-TYPE
		SYNTAX TruthValue   
		ACCESS read-write
		STATUS mandatory
		DESCRIPTION
				"This indicates that information is logged if set to true."
		::= { localGateKeeperMIBObjects 8}
	
--=======================================================================================	
-- General
-- =======
	networkPressure OBJECT-TYPE
		SYNTAX	INTEGER
		ACCESS	read-write
		STATUS	mandatory
		DESCRIPTION "This is the network pressure (0 to 10)."
		::= { localGateKeeperMIBObjects 9}

	limitOfRegisteredClients OBJECT-TYPE
		SYNTAX	INTEGER
		ACCESS	read-write
		STATUS	mandatory
		DESCRIPTION "This is the limit of registered clients."
		::= { localGateKeeperMIBObjects 10}

	numberOfRegisteredClients OBJECT-TYPE
		SYNTAX	INTEGER
		ACCESS	read-only
		STATUS	mandatory
		DESCRIPTION "This is the number of registered clients."
		::= { localGateKeeperMIBObjects 11}

	limitOfCallingClients OBJECT-TYPE
		SYNTAX	INTEGER
		ACCESS	read-write
		STATUS	mandatory
		DESCRIPTION "This is the calling clients limit."
		::= { localGateKeeperMIBObjects 12}

	numberOfCallingClients OBJECT-TYPE
		SYNTAX	INTEGER
		ACCESS	read-only
		STATUS	mandatory
		DESCRIPTION "This is the number of calling clients."
		::= { localGateKeeperMIBObjects 13}

	numberOfChannels OBJECT-TYPE
		SYNTAX	INTEGER
		ACCESS	read-only
		STATUS	mandatory
		DESCRIPTION "This is the number of channels."
		::= { localGateKeeperMIBObjects 14}

	numberOfUsedChannels OBJECT-TYPE
		SYNTAX	INTEGER
		ACCESS	read-only
		STATUS	mandatory
		DESCRIPTION "This is the number of used channels."
		::= { localGateKeeperMIBObjects 15}

-- FIX:	limitOfRegisteredClients OBJECT-TYPE
	limitOfRegisteredClients2 OBJECT-TYPE
		SYNTAX	INTEGER
		ACCESS	read-only
		STATUS	mandatory
		DESCRIPTION "This is the limit of registered clients."
		::= { localGateKeeperMIBObjects 16}

	numberOfAuthenticatedClients OBJECT-TYPE
		SYNTAX	INTEGER
		ACCESS	read-write
		STATUS	mandatory
		DESCRIPTION "This is the number of authenticated clients."
		::= { localGateKeeperMIBObjects 17}

	lgkProgramTraceOnAlarm OBJECT-TYPE
		SYNTAX TruthValue   
		ACCESS read-write
		STATUS mandatory
		DESCRIPTION
				"This indicates that alarms are logged if set to true."
		::= { localGateKeeperMIBObjects 18}

	
	nrOfConnections OBJECT-TYPE
		SYNTAX INTEGER   
		ACCESS read-write
		STATUS mandatory
		DESCRIPTION
				"This is the number of subscribers trying to use 
					the service at the moment."
		::= { localGateKeeperMIBObjects 19}

	serviceProvider OBJECT-TYPE
		SYNTAX DisplayString   
		ACCESS read-write
		STATUS mandatory
		DESCRIPTION
				"This is the name of the service provider."
		::= { localGateKeeperMIBObjects 20}

	bitMapUrl OBJECT-TYPE
		SYNTAX DisplayString
		ACCESS read-write
		STATUS mandatory
		DESCRIPTION
				"This is the URL address to help the client."
		::= { localGateKeeperMIBObjects 21}

	urlHelp OBJECT-TYPE
		SYNTAX DisplayString
		ACCESS read-write
		STATUS mandatory
		DESCRIPTION
				"This is the URL address to help the client."
		::= { localGateKeeperMIBObjects 22}

	lgkVersionInfo OBJECT-TYPE
		SYNTAX DisplayString
		ACCESS read-only
		STATUS mandatory
		DESCRIPTION
				"This is the version information of the installed
					local gatekeeper service."
		::= { localGateKeeperMIBObjects 23}

	limitOfAuthenticatedClients OBJECT-TYPE
		SYNTAX	INTEGER
		ACCESS	read-only
		STATUS	mandatory
		DESCRIPTION "This is the limit of authenticated clients."
		::= { localGateKeeperMIBObjects 24}

	serviceStateChange TRAP-TYPE
		ENTERPRISE localGateKeeperMIB
		VARIABLES { lgkServiceState }
		DESCRIPTION
		"Trap is sent when the state of the Local Gatekeeper service is changed."
		::= 1

	alarm TRAP-TYPE
		ENTERPRISE localGateKeeperMIB
		VARIABLES { lgkAlarmState }
		DESCRIPTION
		"Trap is sent when an alarm occurs."
		::= 2

	alarmCeasing TRAP-TYPE
		ENTERPRISE localGateKeeperMIB
		VARIABLES { lgkAlarmState }
		DESCRIPTION
		"Trap is sent when an alarm disappears."
		::= 3

END
