BILLINGSERVER DEFINITIONS ::= BEGIN

-- 
--								SNMPv1
-- 
-- NAME:		Billing Server Seamac MIB
-- 
-- REVISION HISTORY:-
--
-- REV	DATE		NAME		DESCRIPTION
-- PA1	980423		ETXHAIM		First try
-- A			ETXHAIN		-
-- PB1	980623		QTXJOAL		Added service state + traps.
-- B	980629		QTXJOAL		Rev. B.
-- PC1	980716		QTXSCHU		Replaced some oids and added some new (Öland)
-- C	981010		ETXHAIM		Rev C.
--
--
--
--
-- DESCRIPTION
-- This document describe the configuration parameters for the billing server.
-- 

-- Ericsson Long Distance MIB for billing server

IMPORTS
	enterprises
		FROM RFC1155-SMI
	OBJECT-TYPE
		FROM RFC-1212   
	DisplayString
-- FIX:		FROM RFC-1213;
                FROM RFC1213-MIB;
		
	ericsson		  OBJECT IDENTIFIER ::= { enterprises 193 }
	phonedoubler		  OBJECT IDENTIFIER ::= { ericsson 26 } 
	billingserverMIB 	  OBJECT IDENTIFIER ::= { phonedoubler 9 }
	billingserverMIBObjects   OBJECT IDENTIFIER ::= { billingserverMIB 1 }
	
-- Define of a truth value
	TruthValue ::= INTEGER { true(1), false(2) }

-- =======================================================================================
-- BillingServer MIB

-- =======================================================================================
-- GENERAL ATTRIBUTES
-- ==================

	macAddress OBJECT-TYPE
		SYNTAX	DisplayString
		ACCESS	read-only
		STATUS	mandatory
		DESCRIPTION "This is the address of the network card."
		::= { billingserverMIBObjects 1}

	machineReboot OBJECT-TYPE
		SYNTAX INTEGER
		ACCESS write-only
		STATUS mandatory
		DESCRIPTION
				"This function reboots the machine."
		::= { billingserverMIBObjects 2}

	netkeeperAddress OBJECT-TYPE
		SYNTAX DisplayString
		ACCESS read-write
		STATUS mandatory
		DESCRIPTION
				"This is the IP address of the Network
				Gatekeeper used by this Billing Server. 
				The address takes the form X.X.X.X where
				X is an integer between 0 and 255."
		::= { billingserverMIBObjects 3}

	secret OBJECT-TYPE
		SYNTAX DisplayString  -- This is a string
		ACCESS write-only
		STATUS mandatory
		DESCRIPTION
				"This is the shared secret between the billing
				servers, access broker and the Sitekeeper." 
				
		DEFVAL { "" }
		::= { billingserverMIBObjects 4 }

	maxUsers OBJECT-TYPE
		SYNTAX INTEGER
		ACCESS read-write
		STATUS mandatory
		DESCRIPTION
				"This is the licensed maximum number of enabled 
                                 users in the User Table."
		DEFVAL { "" }
		::= { billingserverMIBObjects 5 }

	maxUsersThreshold OBJECT-TYPE
		SYNTAX INTEGER
		ACCESS read-write
		STATUS mandatory
		DESCRIPTION
				"This is the limit at which percentage of MaxUsers
                                 the NUMBER_USERS_WARNING alarm is issued. 
                                 Default: 70 (70 %)."
		DEFVAL { "" }
		::= { billingserverMIBObjects 6 }

	usersLicenseKey OBJECT-TYPE  -- (PFV)
		SYNTAX DisplayString  -- This is a string of 0 to 255 in length
		ACCESS read-write
		STATUS mandatory
		DESCRIPTION
				"This is the key provided by Ericsson which enable
				the licensed number of users."
		DEFVAL { "" }
		::= { billingserverMIBObjects 7 }

	accountingPort OBJECT-TYPE
		SYNTAX INTEGER
		ACCESS read-write
		STATUS mandatory
		DESCRIPTION
				"This is the port or accounting requests.
                                 Recommended value: 1646." 
		DEFVAL { 1646 }
		::= { billingserverMIBObjects 8 }

	authenticationPort OBJECT-TYPE
		SYNTAX INTEGER
		ACCESS read-write
		STATUS mandatory
		DESCRIPTION
				"This is the port or authentication requests.
                                 Recommended value: 1645." 
		DEFVAL { 1645 }
		::= { billingserverMIBObjects 9 }

	pendingAuthentications OBJECT-TYPE
		SYNTAX INTEGER
		ACCESS read-write
		STATUS mandatory
		DESCRIPTION
				"This is the maximum number of pending
                                 authentication request. 
                                 Recommended value: 10."
		DEFVAL { 10 }
		::= { billingserverMIBObjects 10 }

	pendingAccountings OBJECT-TYPE
		SYNTAX INTEGER
		ACCESS read-write
		STATUS mandatory
		DESCRIPTION
				"This is the maximum number of pending
                                 accounting request. 
                                 Recommended value: 10."
		DEFVAL { 10 }
		::= { billingserverMIBObjects 11 }

	dbmsServer OBJECT-TYPE
		SYNTAX DisplayString  -- This is a string of 0 to 255 in length
		ACCESS read-write
		STATUS mandatory
		DESCRIPTION
				"This is the IP address of the DBMS
				machine. 
				The address takes the form X.X.X.X where
				X is an integer between 0 and 255."
		DEFVAL { "" }
		::= { billingserverMIBObjects 12 }

	dbmsName OBJECT-TYPE
		SYNTAX DisplayString  -- This is a string
		ACCESS read-write
		STATUS mandatory
		DESCRIPTION
				"This is the name of the database." 
				
		DEFVAL { "" }
		::= { billingserverMIBObjects 13 }

	dbmsUserName OBJECT-TYPE
		SYNTAX DisplayString  -- This is a string
		ACCESS read-write
		STATUS mandatory
		DESCRIPTION
				"This is the user name to use on the DBMS." 
				
		DEFVAL { "" }
		::= { billingserverMIBObjects 14 }

	dbmsPassword OBJECT-TYPE
		SYNTAX DisplayString  -- This is a string
		ACCESS write-only
		STATUS mandatory
		DESCRIPTION
				"This is the user password to use on the DBMS." 
		DEFVAL { "" }
		::= { billingserverMIBObjects 15 }

	cacheRates OBJECT-TYPE
		SYNTAX INTEGER
		ACCESS read-write
		STATUS mandatory
		DESCRIPTION
				"1: Cache rate lookups to improve performance
			     0: Do not cache." 
		DEFVAL { "" }
		::= { billingserverMIBObjects 16 }

	flushRatesCacheMinutes OBJECT-TYPE
		SYNTAX INTEGER
		ACCESS read-write
		STATUS mandatory
		DESCRIPTION
				"This is the value at which interval in minutes the 
			         cache of rates should be slushed." 
		DEFVAL { "" }
		::= { billingserverMIBObjects 17 }

	alarmState OBJECT-TYPE
		SYNTAX INTEGER {
				noAlarm(0),
				unknownServerRejected(1),
				failedToAuthenticateServer(2),
				parameterServersNotSet(4),
				parameterPcSitekeepersNotSet(8),
				noContactWithSQLserver(16),
				numberOfUsersWarning(32),
				numberOfUsersAlarm(64),
				numberOfAllowedSelectiveCallsAlarm(128),
				numberOfAllowedSelectiveCallsWarning(256),
				netkeeperError(512)
				}

		ACCESS read-only
		STATUS mandatory
		DESCRIPTION
			"The current alarm state which can take a combination of the
			following values:
				 0   No alarm
				 1   Unknown server rejected 
				 2   Failed to authenticate server
				 4   Parameter servers not set
				 8   Parameter PcSitekeepers not set
				16   No contact with SQL server
				32   Number of users warning
				64   Number of users alarm
			   128   Number of allowed selective calls exceeded, alarm
			   256   Number of allowed selective calls exceeded, warning
			   512   No contact with Netkeeper"

		::= { billingserverMIBObjects 18 }

	traceLogDirectory OBJECT-TYPE
		SYNTAX DisplayString
		ACCESS read-write
		STATUS mandatory
		DESCRIPTION
				"This is where to write trace files.
                Recommended value: C:\Seamac\Traces"
		DEFVAL { "" }
		::= { billingserverMIBObjects 19 }

	programTraceOnWarn OBJECT-TYPE
		SYNTAX TruthValue   
		ACCESS read-write
		STATUS mandatory
		DESCRIPTION
				"This indicates that warnings are traced if set to true."
		DEFVAL { false }
		::= { billingserverMIBObjects 20 }

	programTraceOnInfo OBJECT-TYPE
		SYNTAX TruthValue   
		ACCESS read-write
		STATUS mandatory
		DESCRIPTION
				"This indicates that information is logged if set to true."
		DEFVAL { false }
		::= { billingserverMIBObjects 21 }

	programTraceOnAlarm OBJECT-TYPE
		SYNTAX TruthValue   
		ACCESS read-write
		STATUS mandatory
		DESCRIPTION
				"This indicates that alarms are traced if set to true."
		DEFVAL { false }
		::= { billingserverMIBObjects 22 }

	programTraceOnErrors OBJECT-TYPE
		SYNTAX TruthValue   
		ACCESS read-write
		STATUS mandatory
		DESCRIPTION
				"This indicates that errors are traced if set to true."
		DEFVAL { false }
		::= { billingserverMIBObjects 23 }

	serviceState OBJECT-TYPE
		    SYNTAX INTEGER {
				stop(1),
				startpending(2),
				stoppending(3),
				run(4),
				continuepending(5),
				pausepending(6),
				pause(7)
			}
			ACCESS read-write
			STATUS mandatory
			DESCRIPTION
				"This function controls or returns the state of the 
				 billing service."
		::= { billingserverMIBObjects 24 }

	bsVersionInfo OBJECT-TYPE
		    SYNTAX DisplayString
			ACCESS read-only
			STATUS mandatory
			DESCRIPTION
				"This is the version information of the installed
					billing server service."
		::= { billingserverMIBObjects 25 }

	noOfSelectiveCalls OBJECT-TYPE
		    SYNTAX INTEGER
			ACCESS read-write
			STATUS mandatory
			DESCRIPTION
				"This value specifies the number of free (800) calls."
		::= { billingserverMIBObjects 26 }


	serviceStateChange TRAP-TYPE
		ENTERPRISE billingserverMIB
		VARIABLES { serviceState }
		DESCRIPTION
		"Trap is sent when the state of the billing service is changed."
		::= 1

	alarm TRAP-TYPE
		ENTERPRISE billingserverMIB
		VARIABLES { alarmState }
		DESCRIPTION
		"Trap is sent when an alarm occurs."
		::= 2

	alarmCeasing TRAP-TYPE
		ENTERPRISE billingserverMIB
		VARIABLES { alarmState }
		DESCRIPTION
		"Trap is sent when an alarm disappears."
		::= 3

--=======================================================================================
END
