TEST1 DEFINITIONS ::= BEGIN

  -- PRODUCT-SHORT-NAME MPLS

  IMPORTS
      MODULE-IDENTITY, OBJECT-TYPE,Integer32, Unsigned32      FROM SNMPv2-SMI
      MODULE-COMPLIANCE, OBJECT-GROUP                         FROM SNMPv2-CONF
      TEXTUAL-CONVENTION, RowStatus, TruthValue               FROM SNMPv2-TC
      DcLmgrIndex, PartnerStatus                              FROM TEST-INC-MIB
      notFound                                                FROM NO-GOOD-MIB;

notFoundOid OBJECT IDENTIFIER ::= { notFound 1 }

  test1 MODULE-IDENTITY
      LAST-UPDATED "200211260000Z" -- Tue Nov 26 00:00:00 GMT 2002
      ORGANIZATION "dk"
      CONTACT-INFO "dk"
      DESCRIPTION  "Test module"

  ::= { iso member-body(2) gb(826) national (0) 1
        dataConnectionLtd (1578918) adg (5) lmgr (32) 17 }

  dcTeMibEntityObjects OBJECT IDENTIFIER ::= { test1 1 } -- tables

-- Textual conventions

  DcTeMibEntityIndex ::= TEXTUAL-CONVENTION
      STATUS      current
      DESCRIPTION "The index value identifying a TE-MIB entity."
      SYNTAX      Unsigned32

-- End of textual conventions

-- TE-MIB entity table

  teMibEntityTable OBJECT-TYPE
  -- FAMILY-SHORT-NAME temib
      SYNTAX      SEQUENCE OF DcMplsTeMibEntityEntry
      MAX-ACCESS  not-accessible
      STATUS      current
      DESCRIPTION
          "The table of TE-MIB entities."
      ::= { dcTeMibEntityObjects 1 }

  dcMplsTeMibEntityEntry OBJECT-TYPE
      SYNTAX      DcMplsTeMibEntityEntry
      MAX-ACCESS  not-accessible
      STATUS      current
      DESCRIPTION
          "Each entry represents a TE-MIB entity."
      INDEX { dcMplsTeMibEntityIndex }
      ::= { teMibEntityTable 1 }

  DcMplsTeMibEntityEntry ::= SEQUENCE {
          dcMplsTeMibEntityIndex                 DcTeMibEntityIndex,
          dcMplsTeMibLsrIndex                    DcLmgrIndex,
          dcMplsTeMibLraStatus                   PartnerStatus
      }

  dcMplsTeMibEntityIndex OBJECT-TYPE
      SYNTAX      DcTeMibEntityIndex
      MAX-ACCESS  not-accessible
      STATUS      current
      DESCRIPTION
          "dcMplsTeMibEntityIndex"
      ::= { dcMplsTeMibEntityEntry 1 }


  dcMplsTeMibLsrIndex OBJECT-TYPE
      SYNTAX      DcLmgrIndex
      MAX-ACCESS  read-create
      STATUS      current
      DESCRIPTION
          "dcMplsTeMibLsrIndex "
      DEFVAL      { 0 }
      ::= { dcMplsTeMibEntityEntry 2 }

   dcMplsTeMibLraStatus OBJECT-TYPE
       SYNTAX      PartnerStatus
       MAX-ACCESS  read-only
       STATUS      current
       DESCRIPTION
        "Diagnostic Field providing information about the status
         of the LRAPI user as seen by the TE-MIB entity."
      ::= { dcMplsTeMibEntityEntry 3 }



END
