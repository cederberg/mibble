REVEAL-NPE-MIB DEFINITIONS ::= BEGIN

revealNpeMib MODULE-IDENTITY
      LAST-UPDATED    "0701161535Z"
      ORGANIZATION    "NONE"
      CONTACT-INFO    "mbarchfeld"
      DESCRIPTION     "Shows a NullPointerException of mibble parser"
      ::= { iso 21 }
-- uncomment the following definition of Unsigned32 and the mibble parser will
-- parse this file just fine

-- Unsigned32 ::=
--   [APPLICATION 2]
--      IMPLICIT INTEGER (0..4294967295)
BasedOnUnknownSyntax ::= TEXTUAL-CONVENTION
      STATUS      current
      DESCRIPTION "None."
      SYNTAX      Unsigned32

-- if the revealNpeMibEntry definition is removed, the parser shows
-- Error: in C:\Temp\REVEAL-NPE-MIB.txt: line 20:
--    undefined symbol 'Unsigned32'
-- 
--       SYNTAX      Unsigned32
--                    ^

revealNpeMibEntry OBJECT-TYPE
      SYNTAX      NPESyntax        MAX-ACCESS  not-accessible
      STATUS      current
      DESCRIPTION "None."
          ::= { revealNpeMib 1 }

NPESyntax ::=
      SEQUENCE {
          entry          BasedOnUnknownSyntax
      }                     END
