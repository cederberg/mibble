TEST-INC-MIB DEFINITIONS ::= BEGIN

  IMPORTS
      MODULE-IDENTITY, OBJECT-TYPE, Unsigned32      FROM SNMPv2-SMI
      OBJECT-GROUP, MODULE-COMPLIANCE                          FROM SNMPv2-CONF
      TEXTUAL-CONVENTION, RowStatus, TruthValue                FROM SNMPv2-TC
      InetAddressType, InetAddress, InetAddressIPv4            FROM INET-ADDRESS-MIB;

  test1Inc  MODULE-IDENTITY
      LAST-UPDATED "200211260000Z" -- Tue Nov 26 00:00:00 GMT 2002
      ORGANIZATION "dk"
      CONTACT-INFO "dk"
      DESCRIPTION  "Test Inclusion module"

  ::= { iso member-body(2) gp(826) national (0) 1
        dataConnectionLtd(1578918) adg(5) lmgr (32) 1 }

  dcLmgrObjects OBJECT IDENTIFIER ::= { test1Inc 1 } -- tables

--  Textual Conventions.

  PartnerStatus ::= TEXTUAL-CONVENTION
      STATUS      current
      DESCRIPTION "The state of a Label Manager partner entity."
      SYNTAX      INTEGER {
                      initial(0),     -- partner not active
                      activating(1),  -- partner activating
                      active(2),      -- partner active
                      deactivating(3),-- partner deactivating
                      failedOver(4),  -- partner failed, but recovering
                      failed(5),      -- partner failed, but recovering
                      unavailable(6)  -- partner unavailable
                  }

  DcLmgrIndex ::= TEXTUAL-CONVENTION
      STATUS      current
      DESCRIPTION "The index value identifying a Label Manager
                   entity."
      SYNTAX      Unsigned32

  DcLmgrControlModes ::= TEXTUAL-CONVENTION
      STATUS      current
      DESCRIPTION "The Control Mode of Label Manager."
      SYNTAX      INTEGER {
                      ordered(1),     -- control is ordered
                      independent(2)  -- control is independent
                  }

-- End of textual conventions

END
